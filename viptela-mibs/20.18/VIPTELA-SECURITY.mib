-- Namespace: http://viptela.com/security

VIPTELA-SECURITY DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
    viptela, VpnIndex
        FROM VIPTELA-GLOBAL
;

viptela-security MODULE-IDENTITY
    LAST-UPDATED "202507010000Z"
    ORGANIZATION "Viptela, Inc."
    CONTACT-INFO "Viptela, Inc.  Email:support@viptela.com"
    DESCRIPTION "This module defines data model for Viptela security management"
    REVISION "202507010000Z"
    DESCRIPTION "Viptela Revision 20.18"
    REVISION "202503010000Z"
    DESCRIPTION "Viptela Revision 20.17"
    REVISION "202411010000Z"
    DESCRIPTION "Viptela Revision 20.16"
    REVISION "202407010000Z"
    DESCRIPTION "Viptela Revision 20.15"
    REVISION "202403010000Z"
    DESCRIPTION "Viptela Revision 20.14"
    REVISION "202311010000Z"
    DESCRIPTION "Viptela Revision 20.13"
    REVISION "202307010000Z"
    DESCRIPTION "Viptela Revision 20.12"
    REVISION "202303010000Z"
    DESCRIPTION "Viptela Revision 20.11"
    REVISION "202212150000Z"
    DESCRIPTION "Viptela Revision 20.10"
    REVISION "202206010000Z"
    DESCRIPTION "Viptela Revision 20.9"
    REVISION "202203010000Z"
    DESCRIPTION "Viptela Revision 20.8"
    REVISION "202111010000Z"
    DESCRIPTION "Viptela Revision 20.7"
    REVISION "202107010000Z"
    DESCRIPTION "Viptela Revision 20.6"
    REVISION "202103010000Z"
    DESCRIPTION "Viptela Revision 20.5"
    REVISION "202011010000Z"
    DESCRIPTION "Viptela Revision 20.4"
    REVISION "202007010000Z"
    DESCRIPTION "Viptela Revision 20.3"
    REVISION "202002240000Z"
    DESCRIPTION "Viptela Revision 20.1"
    REVISION "201911150000Z"
    DESCRIPTION "Viptela Revision 19.3"
    REVISION "201908150000Z"
    DESCRIPTION "Viptela Revision 19.2"
    REVISION "201811010000Z"
    DESCRIPTION "Viptela Revision 18.4"
    REVISION "201808200000Z"
    DESCRIPTION "Viptela Revision 18.3.1"
    REVISION "201806250000Z"
    DESCRIPTION "Viptela Revision 18.3"
    REVISION "201804250000Z"
    DESCRIPTION "Viptela Revision 18.2"
    REVISION "201803150000Z"
    DESCRIPTION "Viptela Revision 18.1.1"
    REVISION "201801160000Z"
    DESCRIPTION "Viptela Revision 17.2.3"
    REVISION "201711010000Z"
    DESCRIPTION "Viptela Revision 17.2.1"
    REVISION "201708010000Z"
    DESCRIPTION "Viptela Revision 17.2"
    REVISION "201705250000Z"
    DESCRIPTION "Viptela Revision 17.1.1"
    REVISION "201704060000Z"
    DESCRIPTION "Viptela Revision 17.1"
    REVISION "201702150000Z"
    DESCRIPTION "Viptela Revision 16.3.2"
    REVISION "201702060000Z"
    DESCRIPTION "Viptela Revision 16.3.1"
    REVISION "201611160000Z"
    DESCRIPTION "Viptela Revision 16.3"
    REVISION "201610250000Z"
    DESCRIPTION "Viptela Revision 16.2.10"
    REVISION "201610240000Z"
    DESCRIPTION "Viptela Revision 16.2.4"
    REVISION "201608100000Z"
    DESCRIPTION "Viptela Revision 16.2.2"
    REVISION "201608010000Z"
    DESCRIPTION "Viptela Revision 16.2.1"
    REVISION "201606090000Z"
    DESCRIPTION "Viptela Revision 16.2"
    REVISION "201604220000Z"
    DESCRIPTION "Viptela Revision 16.1.1"
    REVISION "201603150000Z"
    DESCRIPTION "Viptela Revision 16.1"
    REVISION "201601300000Z"
    DESCRIPTION "Viptela Revision 15.4.3"
    REVISION "201512280000Z"
    DESCRIPTION "Viptela Revision 15.4.1"
    REVISION "201512010000Z"
    DESCRIPTION "Viptela Revision 15.4.0"
    REVISION "201510310000Z"
    DESCRIPTION "Viptela Revision 15.3.5"
    REVISION "201509270000Z"
    DESCRIPTION "Viptela Revision 15.3.3"
    REVISION "201509010000Z"
    DESCRIPTION "Viptela Revision 15.3.1"
    REVISION "201507010000Z"
    DESCRIPTION "Viptela Revision 15.3"
    ::= { viptela 4 }

UnsignedByte ::= TEXTUAL-CONVENTION
    DISPLAY-HINT "d"
    STATUS      current
    DESCRIPTION "xs:unsignedByte"
    SYNTAX      Unsigned32 (0 .. 255)

UnsignedShort ::= TEXTUAL-CONVENTION
    DISPLAY-HINT "d"
    STATUS      current
    DESCRIPTION "xs:unsignedShort"
    SYNTAX      Unsigned32 (0 .. 65535)

ConfdString ::= TEXTUAL-CONVENTION
    DISPLAY-HINT "1t"
    STATUS      current
    DESCRIPTION "xs: and confd: types mapped to strings"
    SYNTAX      OCTET STRING

InetAddressIP ::= TEXTUAL-CONVENTION
    STATUS      current
    DESCRIPTION "confd:inetAddressIP"
    SYNTAX      OCTET STRING (SIZE (4|16))

String ::= TEXTUAL-CONVENTION
    DISPLAY-HINT "1t"
    STATUS      current
    DESCRIPTION "xs:string"
    SYNTAX      OCTET STRING

AuthenticationType1 ::= TEXTUAL-CONVENTION
    DISPLAY-HINT "1t"
    STATUS      current
    DESCRIPTION ""
    SYNTAX      OCTET STRING

StateEnum ::= TEXTUAL-CONVENTION
    STATUS      current
    DESCRIPTION "State"
    SYNTAX      INTEGER {unknown(0),up(1),down(2)}

ConnFlagEnum ::= TEXTUAL-CONVENTION
    STATUS      current
    DESCRIPTION "Connection error flags"
    SYNTAX      INTEGER
    {
        nOERR(0),
        aCSRREJ(1),
        sTENTRY(2),
        hSFAIL(3),
        dCERTFL(4),
        nLCERT(5),
        lISFD(6),
        sNOCHECK(7),
        iP-TOS(8),
        tMRALC(9),
        dCONFAIL(10),
        wRKRTO(11),
        vS-TMO(12),
        vB-TMO(13),
        vM-TMO(14),
        vP-TMO(15),
        dISTLOC(16),
        rMGSPR(17),
        pRCHAL(18),
        sYSPRCH(19),
        rECLEN0(20),
        tXCHTOBD(21),
        rDSIGFBD(22),
        sSLNFAIL(23),
        dHSTMO(24),
        nOVS(25),
        nOACTVB(26),
        oRPTMO(27),
        dEVALC(28),
        tUNALC(29),
        cRTREJSER(30),
        vBDEST(31),
        cRTREV(32),
        rXTRDWN(33),
        xTVSTRDN(34),
        nOSLPRCRT(35),
        dUPSER(36),
        sERNTPRES(37),
        cRTVERFL(38),
        bIDNTPR(39),
        bIDNTVRFD(40),
        bDSGVERFL(41),
        mEMALCFL(42),
        uNMSGBDRG(43),
        vSCRTREV(44),
        vECRTREV(45),
        uNAUTHEL(46),
        dISCVBD(47),
        cTORGNMMIS(48),
        nOZTPEN(49),
        nOVMCFG(50),
        cHVERFAIL(51),
        dUPCLHELO(52),
        cERTEXPRD(53),
        sYSIPCHNG(54),
        xTVMTRDN(55),
        mGRTBLCKD(56),
        nONCGN(57),
        xTMOS(58),
        iPTMISS(59),
        oPERDOWN(60),
        nTPRVMINT(61),
        sTNMODETD(62),
        lRNTPEER(63),
        cGNIDCHNGD(64),
        dUPSYSIPDEL(65),
        bIDSIG(66),
        iDREQDECFAIL(67),
        vEYIDBNDFAIL(68),
        cREDFAIL(69),
        rECCABLOBFAIL(70),
        eMBARGOFAIL(71),
        nEWVBNOVMNG(72),
        hWCERTREN(73),
        hWCERTREV(74),
        iNZTPENTRY(75),
        tENANTRM(76),
        rEGIDMIS(77),
        rEGIDCHG(78),
        nOTENPRST(79),
        cRTVERCRLFL(80),
        rESTRQFAIL(81),
        pSEV6DISC(82),
        mGMTREGCHG(83),
        rBDWNLD(84),
        hMEMREJ(85)
    }

AuthenticationEnum ::= TEXTUAL-CONVENTION
    STATUS      current
    DESCRIPTION ""
    SYNTAX      INTEGER {none(0),sha1-hmac(3),ah-sha1-hmac(4),ah-no-id(5)}

SessionState ::= TEXTUAL-CONVENTION
    STATUS      current
    DESCRIPTION "Session state"
    SYNTAX      INTEGER {down(0),connect(1),handshake(2),trying(3),challenge(4),challenge-resp(5),challenge-ack(6),up(7),tear-down(8)}

AuthenticationType ::= TEXTUAL-CONVENTION
    DISPLAY-HINT "1t"
    STATUS      current
    DESCRIPTION ""
    SYNTAX      OCTET STRING

-- Display control information
-- tagpath /control
control OBJECT IDENTIFIER ::= { viptela-security 2 }

-- Display configured control connection rate in PPS
-- tagpath /control/connections-info
controlConnectionsInfo OBJECT IDENTIFIER ::= { control 1 }

-- tagpath /control/connections-info/rate
controlConnectionsInfoRate OBJECT-TYPE
    SYNTAX      String
    MAX-ACCESS  read-only
    STATUS      current
    DESCRIPTION ""
    ::= { controlConnectionsInfo 1 }

-- Display control statistics
-- tagpath /control/statistics
controlStatistics OBJECT IDENTIFIER ::= { control 4 }

-- tagpath /control/statistics/tx_pkts
controlStatisticsTxPkts OBJECT-TYPE
    SYNTAX      Counter64
    MAX-ACCESS  read-only
    STATUS      current
    DESCRIPTION "Tx packets"
    ::= { controlStatistics 1 }

-- tagpath /control/statistics/tx_octets
controlStatisticsTxOctets OBJECT-TYPE
    SYNTAX      Unsigned32
    MAX-ACCESS  read-only
    STATUS      current
    DESCRIPTION "Tx octets"
    ::= { controlStatistics 2 }

-- tagpath /control/statistics/tx_error
controlStatisticsTxError OBJECT-TYPE
    SYNTAX      Unsigned32
    MAX-ACCESS  read-only
    STATUS      current
    DESCRIPTION "Tx error"
    ::= { controlStatistics 3 }

-- tagpath /control/statistics/tx_blocked
controlStatisticsTxBlocked OBJECT-TYPE
    SYNTAX      Unsigned32
    MAX-ACCESS  read-only
    STATUS      current
    DESCRIPTION "Tx blocked"
    ::= { controlStatistics 4 }

-- tagpath /control/statistics/tx_hello
controlStatisticsTxHello OBJECT-TYPE
    SYNTAX      Counter64
    MAX-ACCESS  read-only
    STATUS      current
    DESCRIPTION "Tx hello"
    ::= { controlStatistics 5 }

-- tagpath /control/statistics/tx_connects
controlStatisticsTxConnects OBJECT-TYPE
    SYNTAX      Unsigned32
    MAX-ACCESS  read-only
    STATUS      current
    DESCRIPTION "Tx connects"
    ::= { controlStatistics 6 }

-- tagpath /control/statistics/tx_registers
controlStatisticsTxRegisters OBJECT-TYPE
    SYNTAX      Unsigned32
    MAX-ACCESS  read-only
    STATUS      current
    DESCRIPTION "Tx registers"
    ::= { controlStatistics 7 }

-- tagpath /control/statistics/tx_register_replies
controlStatisticsTxRegisterReplies OBJECT-TYPE
    SYNTAX      Unsigned32
    MAX-ACCESS  read-only
    STATUS      current
    DESCRIPTION "Tx register replies"
    ::= { controlStatistics 8 }

-- tagpath /control/statistics/tx_dtls_handshake
controlStatisticsTxDtlsHandshake OBJECT-TYPE
    SYNTAX      Unsigned32
    MAX-ACCESS  read-only
    STATUS      current
    DESCRIPTION "Tx DTLS handshake"
    ::= { controlStatistics 9 }

-- tagpath /control/statistics/tx_dtls_handshake_failures
controlStatisticsTxDtlsHandshakeFailures OBJECT-TYPE
    SYNTAX      Unsigned32
    MAX-ACCESS  read-only
    STATUS      current
    DESCRIPTION "Tx DTLS handshake failures"
    ::= { controlStatistics 10 }

-- tagpath /control/statistics/tx_dtls_handshake_done
controlStatisticsTxDtlsHandshakeDone OBJECT-TYPE
    SYNTAX      Unsigned32
    MAX-ACCESS  read-only
    STATUS      current
    DESCRIPTION "Tx DTLS handshake done"
    ::= { controlStatistics 11 }

-- tagpath /control/statistics/tx_challenge
controlStatisticsTxChallenge OBJECT-TYPE
    SYNTAX      Unsigned32
    MAX-ACCESS  read-only
    STATUS      current
    DESCRIPTION "Tx challenge"
    ::= { controlStatistics 12 }

-- tagpath /control/statistics/tx_challenge_resp
controlStatisticsTxChallengeResp OBJECT-TYPE
    SYNTAX      Unsigned32
    MAX-ACCESS  read-only
    STATUS      current
    DESCRIPTION "Tx challenge response"
    ::= { controlStatistics 13 }

-- tagpath /control/statistics/tx_challenge_ack
controlStatisticsTxChallengeAck OBJECT-TYPE
    SYNTAX      Unsigned32
    MAX-ACCESS  read-only
    STATUS      current
    DESCRIPTION "Tx challenge ack"
    ::= { controlStatistics 14 }

-- tagpath /control/statistics/tx_challenge_error
controlStatisticsTxChallengeError OBJECT-TYPE
    SYNTAX      Unsigned32
    MAX-ACCESS  read-only
    STATUS      current
    DESCRIPTION "Tx challenge error"
    ::= { controlStatistics 15 }

-- tagpath /control/statistics/tx_challenge_resp_error
controlStatisticsTxChallengeRespError OBJECT-TYPE
    SYNTAX      Unsigned32
    MAX-ACCESS  read-only
    STATUS      current
    DESCRIPTION "Tx challenge response error"
    ::= { controlStatistics 16 }

-- tagpath /control/statistics/tx_challenge_ack_error
controlStatisticsTxChallengeAckError OBJECT-TYPE
    SYNTAX      Unsigned32
    MAX-ACCESS  read-only
    STATUS      current
    DESCRIPTION "Tx challenge ack error"
    ::= { controlStatistics 17 }

-- tagpath /control/statistics/tx_challenge_gen_error
controlStatisticsTxChallengeGenError OBJECT-TYPE
    SYNTAX      Unsigned32
    MAX-ACCESS  read-only
    STATUS      current
    DESCRIPTION "Tx challenge general errors"
    ::= { controlStatistics 18 }

-- tagpath /control/statistics/tx_vmanage_to_peer
controlStatisticsTxVmanageToPeer OBJECT-TYPE
    SYNTAX      Unsigned32
    MAX-ACCESS  read-only
    STATUS      current
    DESCRIPTION "Tx vManage to peer"
    ::= { controlStatistics 19 }

-- tagpath /control/statistics/tx_register_to_vmanage
controlStatisticsTxRegisterToVmanage OBJECT-TYPE
    SYNTAX      Unsigned32
    MAX-ACCESS  read-only
    STATUS      current
    DESCRIPTION "Tx register to vmanage"
    ::= { controlStatistics 20 }

-- tagpath /control/statistics/rx_pkts
controlStatisticsRxPkts OBJECT-TYPE
    SYNTAX      Counter64
    MAX-ACCESS  read-only
    STATUS      current
    DESCRIPTION "Rx packets"
    ::= { controlStatistics 21 }

-- tagpath /control/statistics/rx_octets
controlStatisticsRxOctets OBJECT-TYPE
    SYNTAX      Unsigned32
    MAX-ACCESS  read-only
    STATUS      current
    DESCRIPTION "Rx octets"
    ::= { controlStatistics 22 }

-- tagpath /control/statistics/rx_error
controlStatisticsRxError OBJECT-TYPE
    SYNTAX      Unsigned32
    MAX-ACCESS  read-only
    STATUS      current
    DESCRIPTION "Rx error"
    ::= { controlStatistics 23 }

-- tagpath /control/statistics/rx_hello
controlStatisticsRxHello OBJECT-TYPE
    SYNTAX      Counter64
    MAX-ACCESS  read-only
    STATUS      current
    DESCRIPTION "Rx hello"
    ::= { controlStatistics 24 }

-- tagpath /control/statistics/rx_connects
controlStatisticsRxConnects OBJECT-TYPE
    SYNTAX      Unsigned32
    MAX-ACCESS  read-only
    STATUS      current
    DESCRIPTION "Rx connects"
    ::= { controlStatistics 25 }

-- tagpath /control/statistics/rx_registers
controlStatisticsRxRegisters OBJECT-TYPE
    SYNTAX      Unsigned32
    MAX-ACCESS  read-only
    STATUS      current
    DESCRIPTION "Rx registers"
    ::= { controlStatistics 26 }

-- tagpath /control/statistics/rx_register_replies
controlStatisticsRxRegisterReplies OBJECT-TYPE
    SYNTAX      Unsigned32
    MAX-ACCESS  read-only
    STATUS      current
    DESCRIPTION "Rx register replies"
    ::= { controlStatistics 27 }

-- tagpath /control/statistics/rx_dtls_handshake
controlStatisticsRxDtlsHandshake OBJECT-TYPE
    SYNTAX      Unsigned32
    MAX-ACCESS  read-only
    STATUS      current
    DESCRIPTION "Rx DTLS handshake"
    ::= { controlStatistics 28 }

-- tagpath /control/statistics/rx_dtls_handshake_failures
controlStatisticsRxDtlsHandshakeFailures OBJECT-TYPE
    SYNTAX      Unsigned32
    MAX-ACCESS  read-only
    STATUS      current
    DESCRIPTION "Rx DTLS handshake failures"
    ::= { controlStatistics 29 }

-- tagpath /control/statistics/rx_dtls_handshake_done
controlStatisticsRxDtlsHandshakeDone OBJECT-TYPE
    SYNTAX      Unsigned32
    MAX-ACCESS  read-only
    STATUS      current
    DESCRIPTION "Rx DTLS handshake done"
    ::= { controlStatistics 30 }

-- tagpath /control/statistics/rx_challenge
controlStatisticsRxChallenge OBJECT-TYPE
    SYNTAX      Unsigned32
    MAX-ACCESS  read-only
    STATUS      current
    DESCRIPTION "Rx challenge"
    ::= { controlStatistics 31 }

-- tagpath /control/statistics/rx_challenge_resp
controlStatisticsRxChallengeResp OBJECT-TYPE
    SYNTAX      Unsigned32
    MAX-ACCESS  read-only
    STATUS      current
    DESCRIPTION "Rx challenge response"
    ::= { controlStatistics 32 }

-- tagpath /control/statistics/rx_challenge_ack
controlStatisticsRxChallengeAck OBJECT-TYPE
    SYNTAX      Unsigned32
    MAX-ACCESS  read-only
    STATUS      current
    DESCRIPTION "Rx challenge ack"
    ::= { controlStatistics 33 }

-- tagpath /control/statistics/challenge_failures
controlStatisticsChallengeFailures OBJECT-TYPE
    SYNTAX      Unsigned32
    MAX-ACCESS  read-only
    STATUS      current
    DESCRIPTION "Challenge failures"
    ::= { controlStatistics 34 }

-- tagpath /control/statistics/rx_vmanage_to_peer
controlStatisticsRxVmanageToPeer OBJECT-TYPE
    SYNTAX      Unsigned32
    MAX-ACCESS  read-only
    STATUS      current
    DESCRIPTION "Rx vManage to peer"
    ::= { controlStatistics 35 }

-- tagpath /control/statistics/rx_register_to_vmanage
controlStatisticsRxRegisterToVmanage OBJECT-TYPE
    SYNTAX      Unsigned32
    MAX-ACCESS  read-only
    STATUS      current
    DESCRIPTION "Rx register to vmanage"
    ::= { controlStatistics 36 }

-- tagpath /control/statistics/bid_failures_needing_reset
controlStatisticsBidFailuresNeedingReset OBJECT-TYPE
    SYNTAX      Unsigned32
    MAX-ACCESS  read-only
    STATUS      current
    DESCRIPTION "Board ID reset count"
    ::= { controlStatistics 37 }

-- Display local control properties
-- tagpath /control/local-properties
controlLocalProperties OBJECT IDENTIFIER ::= { control 5 }

-- tagpath /control/local-properties/device-type
controlLocalPropertiesDeviceType OBJECT-TYPE
    SYNTAX      INTEGER {unknown(0),vedge(1),vhub(2),vsmart(3),vbond(4),vmanage(5),ztp(6),vapigw(7)}
    MAX-ACCESS  read-only
    STATUS      current
    DESCRIPTION "Personality"
    ::= { controlLocalProperties 1 }

-- tagpath /control/local-properties/organization-name
controlLocalPropertiesOrganizationName OBJECT-TYPE
    SYNTAX      String (SIZE (1 .. 128))
    MAX-ACCESS  read-only
    STATUS      current
    DESCRIPTION "Organization name"
    ::= { controlLocalProperties 2 }

-- tagpath /control/local-properties/certificate-status
controlLocalPropertiesCertificateStatus OBJECT-TYPE
    SYNTAX      String
    MAX-ACCESS  read-only
    STATUS      current
    DESCRIPTION "Certificate status"
    ::= { controlLocalProperties 3 }

-- tagpath /control/local-properties/root-ca-chain-status
controlLocalPropertiesRootCaChainStatus OBJECT-TYPE
    SYNTAX      String
    MAX-ACCESS  read-only
    STATUS      current
    DESCRIPTION "Root CA chain status"
    ::= { controlLocalProperties 4 }

-- tagpath /control/local-properties/certificate-validity
controlLocalPropertiesCertificateValidity OBJECT-TYPE
    SYNTAX      String
    MAX-ACCESS  read-only
    STATUS      current
    DESCRIPTION "Certificate validity"
    ::= { controlLocalProperties 5 }

-- tagpath /control/local-properties/certificate-not-valid-before
controlLocalPropertiesCertificateNotValidBefore OBJECT-TYPE
    SYNTAX      String
    MAX-ACCESS  read-only
    STATUS      current
    DESCRIPTION "Certificate not valid before"
    ::= { controlLocalProperties 6 }

-- tagpath /control/local-properties/certificate-not-valid-after
controlLocalPropertiesCertificateNotValidAfter OBJECT-TYPE
    SYNTAX      String
    MAX-ACCESS  read-only
    STATUS      current
    DESCRIPTION "Certificate not valid after"
    ::= { controlLocalProperties 7 }

-- tagpath /control/local-properties/dns-name
controlLocalPropertiesDnsName OBJECT-TYPE
    SYNTAX      String
    MAX-ACCESS  read-only
    STATUS      current
    DESCRIPTION "DNS name"
    ::= { controlLocalProperties 8 }

-- tagpath /control/local-properties/site-id
controlLocalPropertiesSiteId OBJECT-TYPE
    SYNTAX      Unsigned32
    MAX-ACCESS  read-only
    STATUS      current
    DESCRIPTION "Site ID"
    ::= { controlLocalProperties 9 }

-- tagpath /control/local-properties/domain-id
controlLocalPropertiesDomainId OBJECT-TYPE
    SYNTAX      Unsigned32
    MAX-ACCESS  read-only
    STATUS      current
    DESCRIPTION "Domain ID"
    ::= { controlLocalProperties 10 }

-- tagpath /control/local-properties/protocol
controlLocalPropertiesProtocol OBJECT-TYPE
    SYNTAX      INTEGER {dtls(0),tls(1),tls-psk(2)}
    MAX-ACCESS  read-only
    STATUS      current
    DESCRIPTION "Protocol"
    ::= { controlLocalProperties 11 }

-- tagpath /control/local-properties/tls-port
controlLocalPropertiesTlsPort OBJECT-TYPE
    SYNTAX      Unsigned32
    MAX-ACCESS  read-only
    STATUS      current
    DESCRIPTION "TLS port"
    ::= { controlLocalProperties 12 }

-- tagpath /control/local-properties/system-ip
controlLocalPropertiesSystemIp OBJECT-TYPE
    SYNTAX      InetAddressIP
    MAX-ACCESS  read-only
    STATUS      current
    DESCRIPTION "System IP address"
    ::= { controlLocalProperties 13 }

-- tagpath /control/local-properties/uuid
controlLocalPropertiesUuid OBJECT-TYPE
    SYNTAX      String
    MAX-ACCESS  read-only
    STATUS      current
    DESCRIPTION "Unique device identifier"
    ::= { controlLocalProperties 14 }

-- tagpath /control/local-properties/board-serial
controlLocalPropertiesBoardSerial OBJECT-TYPE
    SYNTAX      String (SIZE (1 .. 40))
    MAX-ACCESS  read-only
    STATUS      current
    DESCRIPTION "Board ID serial number"
    ::= { controlLocalProperties 15 }

-- tagpath /control/local-properties/register-interval
controlLocalPropertiesRegisterInterval OBJECT-TYPE
    SYNTAX      String
    MAX-ACCESS  read-only
    STATUS      deprecated
    DESCRIPTION "Register interval - Deprecated in 15.4"
    ::= { controlLocalProperties 16 }

-- tagpath /control/local-properties/retry-interval
controlLocalPropertiesRetryInterval OBJECT-TYPE
    SYNTAX      String
    MAX-ACCESS  read-only
    STATUS      current
    DESCRIPTION "Retry interval"
    ::= { controlLocalProperties 17 }

-- tagpath /control/local-properties/no-activity
controlLocalPropertiesNoActivity OBJECT-TYPE
    SYNTAX      String
    MAX-ACCESS  read-only
    STATUS      current
    DESCRIPTION "No activity expiry interval"
    ::= { controlLocalProperties 18 }

-- tagpath /control/local-properties/dns-cache-flush-interval
controlLocalPropertiesDnsCacheFlushInterval OBJECT-TYPE
    SYNTAX      String
    MAX-ACCESS  read-only
    STATUS      current
    DESCRIPTION "DNS cache time to live"
    ::= { controlLocalProperties 19 }

-- tagpath /control/local-properties/port-hopped
controlLocalPropertiesPortHopped OBJECT-TYPE
    SYNTAX      String
    MAX-ACCESS  read-only
    STATUS      current
    DESCRIPTION "Device changed port"
    ::= { controlLocalProperties 20 }

-- tagpath /control/local-properties/time-since-port-hop
controlLocalPropertiesTimeSincePortHop OBJECT-TYPE
    SYNTAX      String
    MAX-ACCESS  read-only
    STATUS      current
    DESCRIPTION "Time since last port hop"
    ::= { controlLocalProperties 21 }

-- tagpath /control/local-properties/max-controllers
controlLocalPropertiesMaxControllers OBJECT-TYPE
    SYNTAX      UnsignedByte
    MAX-ACCESS  read-only
    STATUS      current
    DESCRIPTION "Maximum number of controllers"
    ::= { controlLocalProperties 22 }

-- tagpath /control/local-properties/keygen-interval
controlLocalPropertiesKeygenInterval OBJECT-TYPE
    SYNTAX      String
    MAX-ACCESS  read-only
    STATUS      current
    DESCRIPTION "Key generation interval"
    ::= { controlLocalProperties 23 }

-- tagpath /control/local-properties/number-vbond-peers
controlLocalPropertiesNumberVbondPeers OBJECT-TYPE
    SYNTAX      Unsigned32
    MAX-ACCESS  read-only
    STATUS      current
    DESCRIPTION "Number of vBond peers"
    ::= { controlLocalProperties 25 }

-- tagpath /control/local-properties/number-active-wan-interfaces
controlLocalPropertiesNumberActiveWanInterfaces OBJECT-TYPE
    SYNTAX      Unsigned32
    MAX-ACCESS  read-only
    STATUS      current
    DESCRIPTION "Number of WAN interfaces"
    ::= { controlLocalProperties 27 }


-- Display orchestrator information
-- tagpath /orchestrator
orchestrator OBJECT IDENTIFIER ::= { viptela-security 3 }

-- Display orchestrator statistics
-- tagpath /orchestrator/statistics
orchestratorStatistics OBJECT IDENTIFIER ::= { orchestrator 3 }

-- tagpath /orchestrator/statistics/tx_pkts
orchestratorStatisticsTxPkts OBJECT-TYPE
    SYNTAX      ConfdString
    MAX-ACCESS  read-only
    STATUS      current
    DESCRIPTION "Tx packets"
    ::= { orchestratorStatistics 1 }

-- tagpath /orchestrator/statistics/tx_octets
orchestratorStatisticsTxOctets OBJECT-TYPE
    SYNTAX      Unsigned32
    MAX-ACCESS  read-only
    STATUS      current
    DESCRIPTION "Tx octets"
    ::= { orchestratorStatistics 2 }

-- tagpath /orchestrator/statistics/tx_error
orchestratorStatisticsTxError OBJECT-TYPE
    SYNTAX      Unsigned32
    MAX-ACCESS  read-only
    STATUS      current
    DESCRIPTION "Tx error"
    ::= { orchestratorStatistics 3 }

-- tagpath /orchestrator/statistics/tx_blocked
orchestratorStatisticsTxBlocked OBJECT-TYPE
    SYNTAX      Unsigned32
    MAX-ACCESS  read-only
    STATUS      current
    DESCRIPTION "Tx blocked"
    ::= { orchestratorStatistics 4 }

-- tagpath /orchestrator/statistics/tx_connects
orchestratorStatisticsTxConnects OBJECT-TYPE
    SYNTAX      Unsigned32
    MAX-ACCESS  read-only
    STATUS      current
    DESCRIPTION "Tx connects"
    ::= { orchestratorStatistics 5 }

-- tagpath /orchestrator/statistics/tx_registers
orchestratorStatisticsTxRegisters OBJECT-TYPE
    SYNTAX      Unsigned32
    MAX-ACCESS  read-only
    STATUS      current
    DESCRIPTION "Tx registers"
    ::= { orchestratorStatistics 6 }

-- tagpath /orchestrator/statistics/tx_register_replies
orchestratorStatisticsTxRegisterReplies OBJECT-TYPE
    SYNTAX      Unsigned32
    MAX-ACCESS  read-only
    STATUS      current
    DESCRIPTION "Tx register replies"
    ::= { orchestratorStatistics 7 }

-- tagpath /orchestrator/statistics/tx_dtls_handshake
orchestratorStatisticsTxDtlsHandshake OBJECT-TYPE
    SYNTAX      Unsigned32
    MAX-ACCESS  read-only
    STATUS      current
    DESCRIPTION "Tx DTLS handshake"
    ::= { orchestratorStatistics 8 }

-- tagpath /orchestrator/statistics/tx_dtls_handshake_failures
orchestratorStatisticsTxDtlsHandshakeFailures OBJECT-TYPE
    SYNTAX      Unsigned32
    MAX-ACCESS  read-only
    STATUS      current
    DESCRIPTION "Tx DTLS handshake failures"
    ::= { orchestratorStatistics 9 }

-- tagpath /orchestrator/statistics/tx_dtls_handshake_done
orchestratorStatisticsTxDtlsHandshakeDone OBJECT-TYPE
    SYNTAX      Unsigned32
    MAX-ACCESS  read-only
    STATUS      current
    DESCRIPTION "Tx DTLS handshake done"
    ::= { orchestratorStatistics 10 }

-- tagpath /orchestrator/statistics/tx_challenge
orchestratorStatisticsTxChallenge OBJECT-TYPE
    SYNTAX      Unsigned32
    MAX-ACCESS  read-only
    STATUS      current
    DESCRIPTION "Tx challenge"
    ::= { orchestratorStatistics 11 }

-- tagpath /orchestrator/statistics/tx_challenge_resp
orchestratorStatisticsTxChallengeResp OBJECT-TYPE
    SYNTAX      Unsigned32
    MAX-ACCESS  read-only
    STATUS      current
    DESCRIPTION "Tx challenge response"
    ::= { orchestratorStatistics 12 }

-- tagpath /orchestrator/statistics/tx_challenge_ack
orchestratorStatisticsTxChallengeAck OBJECT-TYPE
    SYNTAX      Unsigned32
    MAX-ACCESS  read-only
    STATUS      current
    DESCRIPTION "Tx challenge ack"
    ::= { orchestratorStatistics 13 }

-- tagpath /orchestrator/statistics/tx_challenge_error
orchestratorStatisticsTxChallengeError OBJECT-TYPE
    SYNTAX      Unsigned32
    MAX-ACCESS  read-only
    STATUS      current
    DESCRIPTION "Tx challenge error"
    ::= { orchestratorStatistics 14 }

-- tagpath /orchestrator/statistics/tx_challenge_resp_error
orchestratorStatisticsTxChallengeRespError OBJECT-TYPE
    SYNTAX      Unsigned32
    MAX-ACCESS  read-only
    STATUS      current
    DESCRIPTION "Tx Challenge response error"
    ::= { orchestratorStatistics 15 }

-- tagpath /orchestrator/statistics/tx_challenge_ack_error
orchestratorStatisticsTxChallengeAckError OBJECT-TYPE
    SYNTAX      Unsigned32
    MAX-ACCESS  read-only
    STATUS      current
    DESCRIPTION "Tx Challenge ack error"
    ::= { orchestratorStatistics 16 }

-- tagpath /orchestrator/statistics/tx_challenge_gen_error
orchestratorStatisticsTxChallengeGenError OBJECT-TYPE
    SYNTAX      Unsigned32
    MAX-ACCESS  read-only
    STATUS      current
    DESCRIPTION "Tx Challenge general errors"
    ::= { orchestratorStatistics 17 }

-- tagpath /orchestrator/statistics/rx_pkts
orchestratorStatisticsRxPkts OBJECT-TYPE
    SYNTAX      ConfdString
    MAX-ACCESS  read-only
    STATUS      current
    DESCRIPTION "Rx packets"
    ::= { orchestratorStatistics 18 }

-- tagpath /orchestrator/statistics/rx_octets
orchestratorStatisticsRxOctets OBJECT-TYPE
    SYNTAX      Unsigned32
    MAX-ACCESS  read-only
    STATUS      current
    DESCRIPTION "Rx octets"
    ::= { orchestratorStatistics 19 }

-- tagpath /orchestrator/statistics/rx_error
orchestratorStatisticsRxError OBJECT-TYPE
    SYNTAX      Unsigned32
    MAX-ACCESS  read-only
    STATUS      current
    DESCRIPTION "Rx error"
    ::= { orchestratorStatistics 20 }

-- tagpath /orchestrator/statistics/rx_connects
orchestratorStatisticsRxConnects OBJECT-TYPE
    SYNTAX      Unsigned32
    MAX-ACCESS  read-only
    STATUS      current
    DESCRIPTION "Rx connects"
    ::= { orchestratorStatistics 21 }

-- tagpath /orchestrator/statistics/rx_registers
orchestratorStatisticsRxRegisters OBJECT-TYPE
    SYNTAX      Unsigned32
    MAX-ACCESS  read-only
    STATUS      current
    DESCRIPTION "Rx registers"
    ::= { orchestratorStatistics 22 }

-- tagpath /orchestrator/statistics/rx_register_replies
orchestratorStatisticsRxRegisterReplies OBJECT-TYPE
    SYNTAX      Unsigned32
    MAX-ACCESS  read-only
    STATUS      current
    DESCRIPTION "Rx register replies"
    ::= { orchestratorStatistics 23 }

-- tagpath /orchestrator/statistics/rx_dtls_handshake
orchestratorStatisticsRxDtlsHandshake OBJECT-TYPE
    SYNTAX      Unsigned32
    MAX-ACCESS  read-only
    STATUS      current
    DESCRIPTION "Rx DTLS handshake"
    ::= { orchestratorStatistics 24 }

-- tagpath /orchestrator/statistics/rx_dtls_handshake_failures
orchestratorStatisticsRxDtlsHandshakeFailures OBJECT-TYPE
    SYNTAX      Unsigned32
    MAX-ACCESS  read-only
    STATUS      current
    DESCRIPTION "Rx DTLS handshake failures"
    ::= { orchestratorStatistics 25 }

-- tagpath /orchestrator/statistics/rx_dtls_handshake_done
orchestratorStatisticsRxDtlsHandshakeDone OBJECT-TYPE
    SYNTAX      Unsigned32
    MAX-ACCESS  read-only
    STATUS      current
    DESCRIPTION "Rx DTLS handshake done"
    ::= { orchestratorStatistics 26 }

-- tagpath /orchestrator/statistics/rx_challenge
orchestratorStatisticsRxChallenge OBJECT-TYPE
    SYNTAX      Unsigned32
    MAX-ACCESS  read-only
    STATUS      current
    DESCRIPTION "Rx challenge"
    ::= { orchestratorStatistics 27 }

-- tagpath /orchestrator/statistics/rx_challenge_resp
orchestratorStatisticsRxChallengeResp OBJECT-TYPE
    SYNTAX      Unsigned32
    MAX-ACCESS  read-only
    STATUS      current
    DESCRIPTION "Rx challenge response"
    ::= { orchestratorStatistics 28 }

-- tagpath /orchestrator/statistics/rx_challenge_ack
orchestratorStatisticsRxChallengeAck OBJECT-TYPE
    SYNTAX      Unsigned32
    MAX-ACCESS  read-only
    STATUS      current
    DESCRIPTION "Rx challenge ack"
    ::= { orchestratorStatistics 29 }

-- tagpath /orchestrator/statistics/challenge_failures
orchestratorStatisticsChallengeFailures OBJECT-TYPE
    SYNTAX      Unsigned32
    MAX-ACCESS  read-only
    STATUS      current
    DESCRIPTION "Challenge failures"
    ::= { orchestratorStatistics 30 }

-- Display local control properties
-- tagpath /orchestrator/local-properties
orchestratorLocalProperties OBJECT IDENTIFIER ::= { orchestrator 4 }

-- tagpath /orchestrator/local-properties/device-type
orchestratorLocalPropertiesDeviceType OBJECT-TYPE
    SYNTAX      INTEGER {unknown(0),vedge(1),vhub(2),vsmart(3),vbond(4),vmanage(5),ztp(6),vapigw(7)}
    MAX-ACCESS  read-only
    STATUS      current
    DESCRIPTION "Personality"
    ::= { orchestratorLocalProperties 1 }

-- tagpath /orchestrator/local-properties/organization-name
orchestratorLocalPropertiesOrganizationName OBJECT-TYPE
    SYNTAX      String (SIZE (1 .. 128))
    MAX-ACCESS  read-only
    STATUS      current
    DESCRIPTION "Organization name"
    ::= { orchestratorLocalProperties 2 }

-- tagpath /orchestrator/local-properties/certificate-status
orchestratorLocalPropertiesCertificateStatus OBJECT-TYPE
    SYNTAX      String
    MAX-ACCESS  read-only
    STATUS      current
    DESCRIPTION "Certificate status"
    ::= { orchestratorLocalProperties 3 }

-- tagpath /orchestrator/local-properties/root-ca-chain-status
orchestratorLocalPropertiesRootCaChainStatus OBJECT-TYPE
    SYNTAX      String
    MAX-ACCESS  read-only
    STATUS      current
    DESCRIPTION "Root CA chain status"
    ::= { orchestratorLocalProperties 4 }

-- tagpath /orchestrator/local-properties/certificate-validity
orchestratorLocalPropertiesCertificateValidity OBJECT-TYPE
    SYNTAX      String
    MAX-ACCESS  read-only
    STATUS      current
    DESCRIPTION "Certificate validity"
    ::= { orchestratorLocalProperties 5 }

-- tagpath /orchestrator/local-properties/certificate-not-valid-before
orchestratorLocalPropertiesCertificateNotValidBefore OBJECT-TYPE
    SYNTAX      String
    MAX-ACCESS  read-only
    STATUS      current
    DESCRIPTION "Certificate not valid before"
    ::= { orchestratorLocalProperties 6 }

-- tagpath /orchestrator/local-properties/certificate-not-valid-after
orchestratorLocalPropertiesCertificateNotValidAfter OBJECT-TYPE
    SYNTAX      String
    MAX-ACCESS  read-only
    STATUS      current
    DESCRIPTION "Certificate not valid after"
    ::= { orchestratorLocalProperties 7 }

-- tagpath /orchestrator/local-properties/uuid
orchestratorLocalPropertiesUuid OBJECT-TYPE
    SYNTAX      String
    MAX-ACCESS  read-only
    STATUS      current
    DESCRIPTION "Unique device identifier"
    ::= { orchestratorLocalProperties 8 }

-- tagpath /orchestrator/local-properties/board-serial
orchestratorLocalPropertiesBoardSerial OBJECT-TYPE
    SYNTAX      String (SIZE (1 .. 40))
    MAX-ACCESS  read-only
    STATUS      current
    DESCRIPTION "Board ID serial number"
    ::= { orchestratorLocalProperties 9 }

-- tagpath /orchestrator/local-properties/number-active-wan-interfaces
orchestratorLocalPropertiesNumberActiveWanInterfaces OBJECT-TYPE
    SYNTAX      Unsigned32
    MAX-ACCESS  read-only
    STATUS      current
    DESCRIPTION "Number of WAN interfaces"
    ::= { orchestratorLocalProperties 10 }

-- tagpath /orchestrator/local-properties/protocol
orchestratorLocalPropertiesProtocol OBJECT-TYPE
    SYNTAX      INTEGER {dtls(0),tls(1),tls-psk(2)}
    MAX-ACCESS  read-only
    STATUS      current
    DESCRIPTION "Protocol"
    ::= { orchestratorLocalProperties 11 }

-- tagpath /orchestrator/local-properties/system-ip
orchestratorLocalPropertiesSystemIp OBJECT-TYPE
    SYNTAX      InetAddressIP
    MAX-ACCESS  read-only
    STATUS      current
    DESCRIPTION "System IP address"
    ::= { orchestratorLocalProperties 13 }

-- tagpath /orchestrator/local-properties/vedge-list-version
orchestratorLocalPropertiesVedgeListVersion OBJECT-TYPE
    SYNTAX      Counter64
    MAX-ACCESS  read-only
    STATUS      current
    DESCRIPTION "vEdge list version number"
    ::= { orchestratorLocalProperties 14 }

-- tagpath /orchestrator/local-properties/vsmart-list-version
orchestratorLocalPropertiesVsmartListVersion OBJECT-TYPE
    SYNTAX      Counter64
    MAX-ACCESS  read-only
    STATUS      current
    DESCRIPTION "vSmart list version number"
    ::= { orchestratorLocalProperties 15 }

-- tagpath /orchestrator/local-properties/sp-organization-name
orchestratorLocalPropertiesSPOrganizationName OBJECT-TYPE
    SYNTAX      String (SIZE (1 .. 128))
    MAX-ACCESS  read-only
    STATUS      current
    DESCRIPTION "SP Organization name"
    ::= { orchestratorLocalProperties 16 }

-- Display entries in the ZTP database
-- tagpath /ztp
ztp OBJECT IDENTIFIER ::= { viptela-security 7 }

-- tagpath /control/connections
controlConnectionsTable OBJECT-TYPE
    SYNTAX      SEQUENCE OF ControlConnectionsEntry
    MAX-ACCESS  not-accessible
    STATUS      current
    DESCRIPTION "Display control connections information"
    ::= { control 2 }

-- tagpath /control/connections
controlConnectionsEntry OBJECT-TYPE
    SYNTAX      ControlConnectionsEntry
    MAX-ACCESS  not-accessible
    STATUS      current
    DESCRIPTION ""
    INDEX { controlConnectionsInstance, controlConnectionsPeerType, controlConnectionsSiteId, controlConnectionsDomainId, controlConnectionsLocalPrivateIp, controlConnectionsLocalPrivatePort, controlConnectionsPublicIp, controlConnectionsPublicPort }
        ::= { controlConnectionsTable 1 }

ControlConnectionsEntry ::=
    SEQUENCE {
        controlConnectionsInstance Unsigned32,
        controlConnectionsPeerType INTEGER,
        controlConnectionsSiteId Unsigned32,
        controlConnectionsDomainId Unsigned32,
        controlConnectionsLocalPrivateIp InetAddressIP,
        controlConnectionsLocalPrivatePort Unsigned32,
        controlConnectionsPublicIp InetAddressIP,
        controlConnectionsPublicPort Unsigned32,
        controlConnectionsSystemIp InetAddressIP,
        controlConnectionsProtocol INTEGER,
        controlConnectionsLocalColor INTEGER,
        controlConnectionsRemoteColor INTEGER,
        controlConnectionsPrivateIp InetAddressIP,
        controlConnectionsPrivatePort Unsigned32,
        controlConnectionsState SessionState,
        controlConnectionsLocalEnum ConnFlagEnum,
        controlConnectionsRemoteEnum ConnFlagEnum,
        controlConnectionsLocalStateInfo String,
        controlConnectionsRemoteStateInfo String,
        controlConnectionsUptime String,
        controlConnectionsTxHello Unsigned32,
        controlConnectionsTxConnects Unsigned32,
        controlConnectionsTxRegisters Unsigned32,
        controlConnectionsTxRegisterReplies Unsigned32,
        controlConnectionsTxChallenge Unsigned32,
        controlConnectionsTxChallengeResp Unsigned32,
        controlConnectionsTxChallengeAck Unsigned32,
        controlConnectionsTxTeardown Unsigned32,
        controlConnectionsTxTeardownAll Unsigned32,
        controlConnectionsTxVmToPeer Unsigned32,
        controlConnectionsTxRegisterToVm Unsigned32,
        controlConnectionsRxHello Unsigned32,
        controlConnectionsRxConnects Unsigned32,
        controlConnectionsRxRegisters Unsigned32,
        controlConnectionsRxRegisterReplies Unsigned32,
        controlConnectionsRxChallenge Unsigned32,
        controlConnectionsRxChallengeResp Unsigned32,
        controlConnectionsRxChallengeAck Unsigned32,
        controlConnectionsRxTeardown Unsigned32,
        controlConnectionsRxVmToPeer Unsigned32,
        controlConnectionsRxRegisterToVm Unsigned32,
        controlConnectionsNegotiatedHelloInterval Unsigned32,
        controlConnectionsNegotiatedHelloTolerance Unsigned32,
        controlConnectionsConfiguredSystemIp InetAddressIP,
        controlConnectionsVOrgName String,
        controlConnectionsTxCreateCert Unsigned32,
        controlConnectionsRxCreateCert Unsigned32,
        controlConnectionsTxCreateCertReply Unsigned32,
        controlConnectionsRxCreateCertReply Unsigned32,
        controlConnectionsBehindProxy String,
        controlConnectionsPeerSessId Counter64,
        controlConnectionsProtocolVersion INTEGER,
        controlConnectionsCipherName String,
        controlConnectionsvDaemonHSLocalBidcertSerial String,
        controlConnectionsvDaemonHSLocalBidcertIssuer String,
        controlConnectionsvDaemonHSLocalBidcertSubject String,
        controlConnectionsvDaemonHSLocalBidcertKeyType String,
        controlConnectionsvDaemonHSLocalBidcertKeyLength INTEGER,
        controlConnectionsvDaemonHSLocalCertSerial String,
        controlConnectionsvDaemonHSLocalCertIssuer String,
        controlConnectionsvDaemonHSLocalCertSubject String,
        controlConnectionsvDaemonHSLocalCertKeyType String,
        controlConnectionsvDaemonHSLocalCertKeyLength INTEGER,
        controlConnectionsvDaemonHSPeerBidcertSerial String,
        controlConnectionsvDaemonHSPeerBidcertIssuer String,
        controlConnectionsvDaemonHSPeerBidcertSubject String,
        controlConnectionsvDaemonHSPeerBidcertKeyType String,
        controlConnectionsvDaemonHSPeerBidcertKeyLength INTEGER,
        controlConnectionsvDaemonHSPeerCertSerial String,
        controlConnectionsvDaemonHSPeerCertIssuer String,
        controlConnectionsvDaemonHSPeerCertSubject String,
        controlConnectionsvDaemonHSPeerCertKeyType String,
        controlConnectionsvDaemonHSPeerCertKeyLength INTEGER,
        controlConnectionsSSLHSLocalCertSerial String,
        controlConnectionsSSLHSLocalCertIssuer String,
        controlConnectionsSSLHSLocalCertSubject String,
        controlConnectionsSSLHSLocalCertKeyType String,
        controlConnectionsSSLHSLocalCertKeyLength INTEGER,
        controlConnectionsSSLHSPeerCertSerial String,
        controlConnectionsSSLHSPeerCertIssuer String,
        controlConnectionsSSLHSPeerCertSubject String,
        controlConnectionsSSLHSPeerCertKeyType String,
        controlConnectionsSSLHSPeerCertKeyLength INTEGER,
        controlConnectionsSSLHSPeerEphemeralGroup String
    }

-- tagpath /control/connections/instance
controlConnectionsInstance OBJECT-TYPE
    SYNTAX      Unsigned32
    MAX-ACCESS  not-accessible
    STATUS      current
    DESCRIPTION "vdaemon instance ID"
    ::= { controlConnectionsEntry 1 }

-- tagpath /control/connections/peer-type
controlConnectionsPeerType OBJECT-TYPE
    SYNTAX      INTEGER {unknown(0),vedge(1),vhub(2),vsmart(3),vbond(4),vmanage(5),ztp(6),vapigw(7)}
    MAX-ACCESS  not-accessible
    STATUS      current
    DESCRIPTION "Connection type"
    ::= { controlConnectionsEntry 2 }

-- tagpath /control/connections/site-id
controlConnectionsSiteId OBJECT-TYPE
    SYNTAX      Unsigned32
    MAX-ACCESS  not-accessible
    STATUS      current
    DESCRIPTION "Site ID"
    ::= { controlConnectionsEntry 3 }

-- tagpath /control/connections/domain-id
controlConnectionsDomainId OBJECT-TYPE
    SYNTAX      Unsigned32
    MAX-ACCESS  not-accessible
    STATUS      current
    DESCRIPTION "Domain ID"
    ::= { controlConnectionsEntry 4 }

-- tagpath /control/connections/local-private-ip
controlConnectionsLocalPrivateIp OBJECT-TYPE
    SYNTAX      InetAddressIP
    MAX-ACCESS  not-accessible
    STATUS      current
    DESCRIPTION "Private IP address"
    ::= { controlConnectionsEntry 5 }

-- tagpath /control/connections/local-private-port
controlConnectionsLocalPrivatePort OBJECT-TYPE
    SYNTAX      Unsigned32
    MAX-ACCESS  not-accessible
    STATUS      current
    DESCRIPTION "Private port number"
    ::= { controlConnectionsEntry 6 }

-- tagpath /control/connections/public-ip
controlConnectionsPublicIp OBJECT-TYPE
    SYNTAX      InetAddressIP
    MAX-ACCESS  not-accessible
    STATUS      current
    DESCRIPTION "Public IP address"
    ::= { controlConnectionsEntry 7 }

-- tagpath /control/connections/public-port
controlConnectionsPublicPort OBJECT-TYPE
    SYNTAX      Unsigned32
    MAX-ACCESS  not-accessible
    STATUS      current
    DESCRIPTION "Public port number"
    ::= { controlConnectionsEntry 8 }

-- tagpath /control/connections/system-ip
controlConnectionsSystemIp OBJECT-TYPE
    SYNTAX      InetAddressIP
    MAX-ACCESS  read-only
    STATUS      current
    DESCRIPTION "System IP address"
    ::= { controlConnectionsEntry 9 }

-- tagpath /control/connections/protocol
controlConnectionsProtocol OBJECT-TYPE
    SYNTAX      INTEGER {dtls(0),tls(1),tls-psk(2)}
    MAX-ACCESS  read-only
    STATUS      current
    DESCRIPTION "Protocol"
    DEFVAL { dtls }
    ::= { controlConnectionsEntry 10 }

-- tagpath /control/connections/local-color
controlConnectionsLocalColor OBJECT-TYPE
    SYNTAX      INTEGER {default(1),mpls(2),metro-ethernet(3),biz-internet(4),public-internet(5),lte(6),threeG(7),red(8),green(9),blue(10),gold(11),silver(12),bronze(13),custom1(14),custom2(15),custom3(16),private1(17),private2(18),private3(19),private4(20),private5(21),private6(22)}
    MAX-ACCESS  read-only
    STATUS      current
    DESCRIPTION "Local color"
    ::= { controlConnectionsEntry 11 }

-- tagpath /control/connections/remote-color
controlConnectionsRemoteColor OBJECT-TYPE
    SYNTAX      INTEGER {default(1),mpls(2),metro-ethernet(3),biz-internet(4),public-internet(5),lte(6),threeG(7),red(8),green(9),blue(10),gold(11),silver(12),bronze(13),custom1(14),custom2(15),custom3(16),private1(17),private2(18),private3(19),private4(20),private5(21),private6(22)}
    MAX-ACCESS  read-only
    STATUS      current
    DESCRIPTION "Remote color"
    ::= { controlConnectionsEntry 12 }

-- tagpath /control/connections/private-ip
controlConnectionsPrivateIp OBJECT-TYPE
    SYNTAX      InetAddressIP
    MAX-ACCESS  read-only
    STATUS      current
    DESCRIPTION "Private IP address"
    ::= { controlConnectionsEntry 13 }

-- tagpath /control/connections/private-port
controlConnectionsPrivatePort OBJECT-TYPE
    SYNTAX      Unsigned32
    MAX-ACCESS  read-only
    STATUS      current
    DESCRIPTION "Private port"
    ::= { controlConnectionsEntry 14 }

-- tagpath /control/connections/state
controlConnectionsState OBJECT-TYPE
    SYNTAX      SessionState
    MAX-ACCESS  read-only
    STATUS      current
    DESCRIPTION "State"
    ::= { controlConnectionsEntry 15 }

-- tagpath /control/connections/local_enum
controlConnectionsLocalEnum OBJECT-TYPE
    SYNTAX      ConnFlagEnum
    MAX-ACCESS  read-only
    STATUS      current
    DESCRIPTION "Local error reason"
    ::= { controlConnectionsEntry 16 }

-- tagpath /control/connections/remote_enum
controlConnectionsRemoteEnum OBJECT-TYPE
    SYNTAX      ConnFlagEnum
    MAX-ACCESS  read-only
    STATUS      current
    DESCRIPTION "Remote error reason"
    ::= { controlConnectionsEntry 17 }

-- tagpath /control/connections/local-state-info
controlConnectionsLocalStateInfo OBJECT-TYPE
    SYNTAX      String
    MAX-ACCESS  read-only
    STATUS      current
    DESCRIPTION "Local state information"
    ::= { controlConnectionsEntry 18 }

-- tagpath /control/connections/remote-state-info
controlConnectionsRemoteStateInfo OBJECT-TYPE
    SYNTAX      String
    MAX-ACCESS  read-only
    STATUS      current
    DESCRIPTION "Remote state information"
    ::= { controlConnectionsEntry 19 }

-- tagpath /control/connections/uptime
controlConnectionsUptime OBJECT-TYPE
    SYNTAX      String
    MAX-ACCESS  read-only
    STATUS      current
    DESCRIPTION "Uptime"
    ::= { controlConnectionsEntry 20 }

-- tagpath /control/connections/tx_hello
controlConnectionsTxHello OBJECT-TYPE
    SYNTAX      Unsigned32
    MAX-ACCESS  read-only
    STATUS      current
    DESCRIPTION "Tx hello"
    ::= { controlConnectionsEntry 21 }

-- tagpath /control/connections/tx_connects
controlConnectionsTxConnects OBJECT-TYPE
    SYNTAX      Unsigned32
    MAX-ACCESS  read-only
    STATUS      current
    DESCRIPTION "Tx connects"
    ::= { controlConnectionsEntry 22 }

-- tagpath /control/connections/tx_registers
controlConnectionsTxRegisters OBJECT-TYPE
    SYNTAX      Unsigned32
    MAX-ACCESS  read-only
    STATUS      current
    DESCRIPTION "Tx registers"
    ::= { controlConnectionsEntry 23 }

-- tagpath /control/connections/tx_register_replies
controlConnectionsTxRegisterReplies OBJECT-TYPE
    SYNTAX      Unsigned32
    MAX-ACCESS  read-only
    STATUS      current
    DESCRIPTION "Tx register replies"
    ::= { controlConnectionsEntry 24 }

-- tagpath /control/connections/tx_challenge
controlConnectionsTxChallenge OBJECT-TYPE
    SYNTAX      Unsigned32
    MAX-ACCESS  read-only
    STATUS      current
    DESCRIPTION "Tx challenge"
    ::= { controlConnectionsEntry 25 }

-- tagpath /control/connections/tx_challenge_resp
controlConnectionsTxChallengeResp OBJECT-TYPE
    SYNTAX      Unsigned32
    MAX-ACCESS  read-only
    STATUS      current
    DESCRIPTION "Tx challenge response"
    ::= { controlConnectionsEntry 26 }

-- tagpath /control/connections/tx_challenge_ack
controlConnectionsTxChallengeAck OBJECT-TYPE
    SYNTAX      Unsigned32
    MAX-ACCESS  read-only
    STATUS      current
    DESCRIPTION "Tx challenge ack"
    ::= { controlConnectionsEntry 27 }

-- tagpath /control/connections/tx_teardown
controlConnectionsTxTeardown OBJECT-TYPE
    SYNTAX      Unsigned32
    MAX-ACCESS  read-only
    STATUS      current
    DESCRIPTION "Tx teardown"
    ::= { controlConnectionsEntry 28 }

-- tagpath /control/connections/tx_teardown_all
controlConnectionsTxTeardownAll OBJECT-TYPE
    SYNTAX      Unsigned32
    MAX-ACCESS  read-only
    STATUS      current
    DESCRIPTION "Tx teardown all connections"
    ::= { controlConnectionsEntry 29 }

-- tagpath /control/connections/tx_vm_to_peer
controlConnectionsTxVmToPeer OBJECT-TYPE
    SYNTAX      Unsigned32
    MAX-ACCESS  read-only
    STATUS      current
    DESCRIPTION "Tx vManage to peer"
    ::= { controlConnectionsEntry 30 }

-- tagpath /control/connections/tx_register_to_vm
controlConnectionsTxRegisterToVm OBJECT-TYPE
    SYNTAX      Unsigned32
    MAX-ACCESS  read-only
    STATUS      current
    DESCRIPTION "Tx register to vManage"
    ::= { controlConnectionsEntry 31 }

-- tagpath /control/connections/rx_hello
controlConnectionsRxHello OBJECT-TYPE
    SYNTAX      Unsigned32
    MAX-ACCESS  read-only
    STATUS      current
    DESCRIPTION "Rx hello"
    ::= { controlConnectionsEntry 32 }

-- tagpath /control/connections/rx_connects
controlConnectionsRxConnects OBJECT-TYPE
    SYNTAX      Unsigned32
    MAX-ACCESS  read-only
    STATUS      current
    DESCRIPTION "Rx connects"
    ::= { controlConnectionsEntry 33 }

-- tagpath /control/connections/rx_registers
controlConnectionsRxRegisters OBJECT-TYPE
    SYNTAX      Unsigned32
    MAX-ACCESS  read-only
    STATUS      current
    DESCRIPTION "Rx registers"
    ::= { controlConnectionsEntry 34 }

-- tagpath /control/connections/rx_register_replies
controlConnectionsRxRegisterReplies OBJECT-TYPE
    SYNTAX      Unsigned32
    MAX-ACCESS  read-only
    STATUS      current
    DESCRIPTION "Rx register replies"
    ::= { controlConnectionsEntry 35 }

-- tagpath /control/connections/rx_challenge
controlConnectionsRxChallenge OBJECT-TYPE
    SYNTAX      Unsigned32
    MAX-ACCESS  read-only
    STATUS      current
    DESCRIPTION "Rx challenge"
    ::= { controlConnectionsEntry 36 }

-- tagpath /control/connections/rx_challenge_resp
controlConnectionsRxChallengeResp OBJECT-TYPE
    SYNTAX      Unsigned32
    MAX-ACCESS  read-only
    STATUS      current
    DESCRIPTION "Rx challenge response"
    ::= { controlConnectionsEntry 37 }

-- tagpath /control/connections/rx_challenge_ack
controlConnectionsRxChallengeAck OBJECT-TYPE
    SYNTAX      Unsigned32
    MAX-ACCESS  read-only
    STATUS      current
    DESCRIPTION "Rx challenge ack"
    ::= { controlConnectionsEntry 38 }

-- tagpath /control/connections/rx_teardown
controlConnectionsRxTeardown OBJECT-TYPE
    SYNTAX      Unsigned32
    MAX-ACCESS  read-only
    STATUS      current
    DESCRIPTION "Rx teardown"
    ::= { controlConnectionsEntry 39 }

-- tagpath /control/connections/rx_vm_to_peer
controlConnectionsRxVmToPeer OBJECT-TYPE
    SYNTAX      Unsigned32
    MAX-ACCESS  read-only
    STATUS      current
    DESCRIPTION "Rx vManage to peer"
    ::= { controlConnectionsEntry 40 }

-- tagpath /control/connections/rx_register_to_vm
controlConnectionsRxRegisterToVm OBJECT-TYPE
    SYNTAX      Unsigned32
    MAX-ACCESS  read-only
    STATUS      current
    DESCRIPTION "Rx register to vManage"
    ::= { controlConnectionsEntry 41 }

-- tagpath /control/connections/negotiated_hello_interval
controlConnectionsNegotiatedHelloInterval OBJECT-TYPE
    SYNTAX      Unsigned32
    MAX-ACCESS  read-only
    STATUS      current
    DESCRIPTION "Negotiated hello interval"
    ::= { controlConnectionsEntry 42 }

-- tagpath /control/connections/negotiated_hello_tolerance
controlConnectionsNegotiatedHelloTolerance OBJECT-TYPE
    SYNTAX      Unsigned32
    MAX-ACCESS  read-only
    STATUS      current
    DESCRIPTION "Negotiated hello tolerance"
    ::= { controlConnectionsEntry 43 }

-- tagpath /control/connections/cfg-system-ip
controlConnectionsConfiguredSystemIp OBJECT-TYPE
    SYNTAX      InetAddressIP
    MAX-ACCESS  read-only
    STATUS      current
    DESCRIPTION "Configured System IP address"
    ::= { controlConnectionsEntry 44 }

-- tagpath /control/connections/v-org-name
controlConnectionsVOrgName OBJECT-TYPE
    SYNTAX      String (SIZE (1 .. 128))
    MAX-ACCESS  read-only
    STATUS      current
    DESCRIPTION "Organization Name"
    ::= { controlConnectionsEntry 45 }

-- tagpath /control/connections/tx_create_cert
controlConnectionsTxCreateCert OBJECT-TYPE
    SYNTAX      Unsigned32
    MAX-ACCESS  read-only
    STATUS      current
    DESCRIPTION "Tx create certificate to vManage"
    ::= { controlConnectionsEntry 46 }

-- tagpath /control/connections/rx_create_cert
controlConnectionsRxCreateCert OBJECT-TYPE
    SYNTAX      Unsigned32
    MAX-ACCESS  read-only
    STATUS      current
    DESCRIPTION "Rx create certificate from vBond"
    ::= { controlConnectionsEntry 47 }

-- tagpath /control/connections/tx_create_cert_reply
controlConnectionsTxCreateCertReply OBJECT-TYPE
    SYNTAX      Unsigned32
    MAX-ACCESS  read-only
    STATUS      current
    DESCRIPTION "Tx create certificate reply to vBond"
    ::= { controlConnectionsEntry 48 }

-- tagpath /control/connections/rx_create_cert_reply
controlConnectionsRxCreateCertReply OBJECT-TYPE
    SYNTAX      Unsigned32
    MAX-ACCESS  read-only
    STATUS      current
    DESCRIPTION "Rx create certificate reply from vManage"
    ::= { controlConnectionsEntry 49 }

-- tagpath /control/connections/behind-proxy
controlConnectionsBehindProxy OBJECT-TYPE
    SYNTAX      String
    MAX-ACCESS  read-only
    STATUS      current
    DESCRIPTION "Whether controller is behind proxy"
    ::= { controlConnectionsEntry 50 }

-- tagpath /control/connections/peer-sess-id
controlConnectionsPeerSessId OBJECT-TYPE
    SYNTAX      Counter64
    MAX-ACCESS  read-only
    STATUS      current
    DESCRIPTION "Peer Session ID"
    ::= { controlConnectionsEntry 51 }

-- tagpath /control/connections/protocol-version
controlConnectionsProtocolVersion OBJECT-TYPE
    SYNTAX      INTEGER {unknown(0),sslv3(1),tls1(2),tls11(3),tls12(4),tls13(5),dtls1(6),dtls12(7)}
    MAX-ACCESS  read-only
    STATUS      current
    DESCRIPTION "Protocol Version"
    DEFVAL { unknown }
    ::= { controlConnectionsEntry 52 }

-- tagpath /control/connections/cipher-name
controlConnectionsCipherName OBJECT-TYPE
    SYNTAX      String
    MAX-ACCESS  read-only
    STATUS      current
    DESCRIPTION "Cipher Name"
    ::= { controlConnectionsEntry 53 }

-- tagpath /control/connections/vd_handshake_local_bidcert_serial
controlConnectionsvDaemonHSLocalBidcertSerial OBJECT-TYPE
    SYNTAX     String
    MAX-ACCESS  read-only
    STATUS      current
    DESCRIPTION "vDaemon Handshake Local Board-ID Certificate Serial"
    ::= { controlConnectionsEntry 54 }

-- tagpath /control/connections/vd_handshake_local_bidcert_issuer
controlConnectionsvDaemonHSLocalBidcertIssuer OBJECT-TYPE
    SYNTAX     String
    MAX-ACCESS  read-only
    STATUS      current
    DESCRIPTION "vDaemon Handshake Local Board-ID Certificate Issuer"
    ::= { controlConnectionsEntry 55 }

-- tagpath /control/connections/vd_handshake_local_bidcert_subject
controlConnectionsvDaemonHSLocalBidcertSubject OBJECT-TYPE
    SYNTAX     String
    MAX-ACCESS  read-only
    STATUS      current
    DESCRIPTION "vDaemon Handshake Local Board-ID Certificate Subject"
    ::= { controlConnectionsEntry 56 }

-- tagpath /control/connections/vd_handshake_local_bidcert_key_type
controlConnectionsvDaemonHSLocalBidcertKeyType OBJECT-TYPE
    SYNTAX     String
    MAX-ACCESS  read-only
    STATUS      current
    DESCRIPTION "vDaemon Handshake Local Board-ID Key Type"
    ::= { controlConnectionsEntry 57 }

-- tagpath /control/connections/vd_handshake_local_bidcert_key_length
controlConnectionsvDaemonHSLocalBidcertKeyLength OBJECT-TYPE
    SYNTAX     INTEGER
    MAX-ACCESS  read-only
    STATUS      current
    DESCRIPTION "vDaemon Handshake Local Board-ID Key Length"
    ::= { controlConnectionsEntry 58 }

-- tagpath /control/connections/vd_handshake_local_cert_serial
controlConnectionsvDaemonHSLocalCertSerial OBJECT-TYPE
    SYNTAX     String
    MAX-ACCESS  read-only
    STATUS      current
    DESCRIPTION "vDaemon Handshake Local Certificate Serial"
    ::= { controlConnectionsEntry 59 }

-- tagpath /control/connections/vd_handshake_local_cert_issuer
controlConnectionsvDaemonHSLocalCertIssuer OBJECT-TYPE
    SYNTAX     String
    MAX-ACCESS  read-only
    STATUS      current
    DESCRIPTION "vDaemon Handshake Local Certificate Issuer"
    ::= { controlConnectionsEntry 60 }

-- tagpath /control/connections/vd_handshake_local_cert_subject
controlConnectionsvDaemonHSLocalCertSubject OBJECT-TYPE
    SYNTAX     String
    MAX-ACCESS  read-only
    STATUS      current
    DESCRIPTION "vDaemon Handshake Local Certificate Subject"
    ::= { controlConnectionsEntry 61 }

-- tagpath /control/connections/vd_handshake_local_cert_key_type
controlConnectionsvDaemonHSLocalCertKeyType OBJECT-TYPE
    SYNTAX     String
    MAX-ACCESS  read-only
    STATUS      current
    DESCRIPTION "vDaemon Handshake Local Certificate Issuer"
    ::= { controlConnectionsEntry 62 }

-- tagpath /control/connections/vd_handshake_local_key_length
controlConnectionsvDaemonHSLocalCertKeyLength OBJECT-TYPE
    SYNTAX     INTEGER
    MAX-ACCESS  read-only
    STATUS      current
    DESCRIPTION "vDaemon Handshake Local Certificate Key Length"
    ::= { controlConnectionsEntry 63 }

-- tagpath /control/connections/vd_handshake_peer_bidcert_serial
controlConnectionsvDaemonHSPeerBidcertSerial OBJECT-TYPE
    SYNTAX     String
    MAX-ACCESS  read-only
    STATUS      current
    DESCRIPTION "vDaemon Handshake Peer Board-ID Certificate Serial"
    ::= { controlConnectionsEntry 64 }

-- tagpath /control/connections/vd_handshake_peer_bidcert_issuer
controlConnectionsvDaemonHSPeerBidcertIssuer OBJECT-TYPE
    SYNTAX     String
    MAX-ACCESS  read-only
    STATUS      current
    DESCRIPTION "vDaemon Handshake Peer Board-ID Certificate Issuer"
    ::= { controlConnectionsEntry 65 }

-- tagpath /control/connections/vd_handshake_peer_bidcert_subject
controlConnectionsvDaemonHSPeerBidcertSubject OBJECT-TYPE
    SYNTAX     String
    MAX-ACCESS  read-only
    STATUS      current
    DESCRIPTION "vDaemon Handshake Peer Board-ID Certificate Subject"
    ::= { controlConnectionsEntry 66 }

-- tagpath /control/connections/vd_handshake_peer_bidcert_key_type
controlConnectionsvDaemonHSPeerBidcertKeyType OBJECT-TYPE
    SYNTAX     String
    MAX-ACCESS  read-only
    STATUS      current
    DESCRIPTION "vDaemon Handshake Peer Board-ID Key Type"
    ::= { controlConnectionsEntry 67 }

-- tagpath /control/connections/vd_handshake_peer_bidcert_key_length
controlConnectionsvDaemonHSPeerBidcertKeyLength OBJECT-TYPE
    SYNTAX     INTEGER
    MAX-ACCESS  read-only
    STATUS      current
    DESCRIPTION "vDaemon Handshake Peer Board-ID Certificate Key Length"
    ::= { controlConnectionsEntry 68 }

-- tagpath /control/connections/vd_handshake_peer_cert_serial
controlConnectionsvDaemonHSPeerCertSerial OBJECT-TYPE
    SYNTAX     String
    MAX-ACCESS  read-only
    STATUS      current
    DESCRIPTION "vDaemon Handshake Peer Certificate Serial"
    ::= { controlConnectionsEntry 69 }

-- tagpath /control/connections/vd_handshake_peer_cert_issuer
controlConnectionsvDaemonHSPeerCertIssuer OBJECT-TYPE
    SYNTAX     String
    MAX-ACCESS  read-only
    STATUS      current
    DESCRIPTION "vDaemon Handshake Peer Certificate Issuer"
    ::= { controlConnectionsEntry 70 }

-- tagpath /control/connections/vd_handshake_peer_cert_subject
controlConnectionsvDaemonHSPeerCertSubject OBJECT-TYPE
    SYNTAX     String
    MAX-ACCESS  read-only
    STATUS      current
    DESCRIPTION "vDaemon Handshake Peer Certificate Subject"
    ::= { controlConnectionsEntry 71 }

-- tagpath /control/connections/vd_handshake_peer_cert_key_type
controlConnectionsvDaemonHSPeerCertKeyType OBJECT-TYPE
    SYNTAX     String
    MAX-ACCESS  read-only
    STATUS      current
    DESCRIPTION "vDaemon Handshake Peer Key Type"
    ::= { controlConnectionsEntry 72 }

-- tagpath /control/connections/vd_handshake_peer_cert_key_length
controlConnectionsvDaemonHSPeerCertKeyLength OBJECT-TYPE
    SYNTAX     INTEGER
    MAX-ACCESS  read-only
    STATUS      current
    DESCRIPTION "vDaemon Handshake Peer Certificate Key Length"
    ::= { controlConnectionsEntry 73 }

-- tagpath /control/connections/ssl_handshake_local_cert_serial
controlConnectionsSSLHSLocalCertSerial OBJECT-TYPE
    SYNTAX     String
    MAX-ACCESS  read-only
    STATUS      current
    DESCRIPTION "SSL Handshake Local Certificate Serial"
    ::= { controlConnectionsEntry 74 }

-- tagpath /control/connections/ssl_handshake_local_cert_issuer
controlConnectionsSSLHSLocalCertIssuer OBJECT-TYPE
    SYNTAX     String
    MAX-ACCESS  read-only
    STATUS      current
    DESCRIPTION "SSL Handshake Local Certificate Issuer"
    ::= { controlConnectionsEntry 75 }

-- tagpath /control/connections/ssl_handshake_local_cert_subject
controlConnectionsSSLHSLocalCertSubject OBJECT-TYPE
    SYNTAX     String
    MAX-ACCESS  read-only
    STATUS      current
    DESCRIPTION "SSL Handshake Local Certificate Subject"
    ::= { controlConnectionsEntry 76 }

-- tagpath /control/connections/ssl_handshake_local_cert_key_type
controlConnectionsSSLHSLocalCertKeyType OBJECT-TYPE
    SYNTAX     String
    MAX-ACCESS  read-only
    STATUS      current
    DESCRIPTION "SSL Handshake Local Certificate Key Type"
    ::= { controlConnectionsEntry 77 }

-- tagpath /control/connections/ssl_handshake_local_cert_key_length
controlConnectionsSSLHSLocalCertKeyLength OBJECT-TYPE
    SYNTAX     INTEGER
    MAX-ACCESS  read-only
    STATUS      current
    DESCRIPTION "SSL Handshake Local Certificate Key Length"
    ::= { controlConnectionsEntry 78 }

-- tagpath /control/connections/ssl_handshake_peer_cert_serial
controlConnectionsSSLHSPeerCertSerial OBJECT-TYPE
    SYNTAX     String
    MAX-ACCESS  read-only
    STATUS      current
    DESCRIPTION "SSL Handshake Peer Certificate Serial"
    ::= { controlConnectionsEntry 79 }

-- tagpath /control/connections/ssl_handshake_peer_cert_issuer
controlConnectionsSSLHSPeerCertIssuer OBJECT-TYPE
    SYNTAX     String
    MAX-ACCESS  read-only
    STATUS      current
    DESCRIPTION "SSL Handshake Peer Certificate Issuer"
    ::= { controlConnectionsEntry 80 }

-- tagpath /control/connections/ssl_handshake_peer_cert_subject
controlConnectionsSSLHSPeerCertSubject OBJECT-TYPE
    SYNTAX     String
    MAX-ACCESS  read-only
    STATUS      current
    DESCRIPTION "SSL Handshake Peer Certificate Subject"
    ::= { controlConnectionsEntry 81 }

-- tagpath /control/connections/ssl_handshake_peer_cert_key_type
controlConnectionsSSLHSPeerCertKeyType OBJECT-TYPE      
    SYNTAX     String                                  
    MAX-ACCESS  read-only                              
    STATUS      current                                
    DESCRIPTION "SSL Handshake Peer Certificate Key Type"
    ::= { controlConnectionsEntry 82} 

-- tagpath /control/connections/ssl_handshake_peer_cert_key_length
controlConnectionsSSLHSPeerCertKeyLength OBJECT-TYPE      
    SYNTAX     INTEGER                                  
    MAX-ACCESS  read-only                              
    STATUS      current                                
    DESCRIPTION "SSL Handshake Peer Certificate Key Length"
    ::= { controlConnectionsEntry 83 } 

-- tagpath /control/connections/ssl_handshake_ephemeral_group
controlConnectionsSSLHSPeerEphemeralGroup OBJECT-TYPE       
    SYNTAX     String                                
    MAX-ACCESS  read-only                            
    STATUS      current                              
    DESCRIPTION "SSL Handshake Ephemeral Group"        
    ::= { controlConnectionsEntry 84 }

-- tagpath /control/connections-history
controlConnectionsHistoryTable OBJECT-TYPE
    SYNTAX      SEQUENCE OF ControlConnectionsHistoryEntry
    MAX-ACCESS  not-accessible
    STATUS      current
    DESCRIPTION "Display control connections history"
    ::= { control 3 }

-- tagpath /control/connections-history
controlConnectionsHistoryEntry OBJECT-TYPE
    SYNTAX      ControlConnectionsHistoryEntry
    MAX-ACCESS  not-accessible
    STATUS      current
    DESCRIPTION ""
    INDEX { controlConnectionsHistoryInstance, controlConnectionsHistoryIndex }
        ::= { controlConnectionsHistoryTable 1 }

ControlConnectionsHistoryEntry ::=
    SEQUENCE {
        controlConnectionsHistoryInstance Unsigned32,
        controlConnectionsHistoryIndex Unsigned32,
        controlConnectionsHistoryPeerType INTEGER,
        controlConnectionsHistorySiteId Unsigned32,
        controlConnectionsHistoryDomainId Unsigned32,
        controlConnectionsHistoryPrivateIp InetAddressIP,
        controlConnectionsHistoryPrivatePort Unsigned32,
        controlConnectionsHistoryPublicIp InetAddressIP,
        controlConnectionsHistoryPublicPort Unsigned32,
        controlConnectionsHistorySystemIp InetAddressIP,
        controlConnectionsHistoryProtocol INTEGER,
        controlConnectionsHistoryLocalColor INTEGER,
        controlConnectionsHistoryRemoteColor INTEGER,
        controlConnectionsHistoryState SessionState,
        controlConnectionsHistoryLocalEnum ConnFlagEnum,
        controlConnectionsHistoryRemoteEnum ConnFlagEnum,
        controlConnectionsHistoryLocalStateInfo String,
        controlConnectionsHistoryRemoteStateInfo String,
        controlConnectionsHistoryDowntime String,
        controlConnectionsHistoryTxHello Unsigned32,
        controlConnectionsHistoryTxConnects Unsigned32,
        controlConnectionsHistoryTxRegisters Unsigned32,
        controlConnectionsHistoryTxRegisterReplies Unsigned32,
        controlConnectionsHistoryTxChallenge Unsigned32,
        controlConnectionsHistoryTxChallengeResp Unsigned32,
        controlConnectionsHistoryTxChallengeAck Unsigned32,
        controlConnectionsHistoryTxTeardown Unsigned32,
        controlConnectionsHistoryTxTeardownAll Unsigned32,
        controlConnectionsHistoryTxVmToPeer Unsigned32,
        controlConnectionsHistoryTxRegisterToVm Unsigned32,
        controlConnectionsHistoryRxHello Unsigned32,
        controlConnectionsHistoryRxConnects Unsigned32,
        controlConnectionsHistoryRxRegisters Unsigned32,
        controlConnectionsHistoryRxRegisterReplies Unsigned32,
        controlConnectionsHistoryRxChallenge Unsigned32,
        controlConnectionsHistoryRxChallengeResp Unsigned32,
        controlConnectionsHistoryRxChallengeAck Unsigned32,
        controlConnectionsHistoryRxTeardown Unsigned32,
        controlConnectionsHistoryRxVmToPeer Unsigned32,
        controlConnectionsHistoryRxRegisterToVm Unsigned32,
        controlConnectionsHistoryRepCount Unsigned32,
        controlConnectionsHistoryPrevDowntime String,
        controlConnectionsHistoryConfiguredSystemIp InetAddressIP,
        controlConnectionsHistoryVHOrgName String,
        controlConnectionsHistoryUuid String,
        controlConnectionsHistoryTxCreateCert Unsigned32,
        controlConnectionsHistoryRxCreateCert Unsigned32,
        controlConnectionsHistoryTxCreateCertReply Unsigned32,
        controlConnectionsHistoryRxCreateCertReply Unsigned32,
        controlConnectionsHistoryProtocolVersion INTEGER,
        controlConnectionsHistoryCipherName String,
        controlConnectionsHistoryvDaemonHSLocalBidcertSerial String,
        controlConnectionsHistoryvDaemonHSLocalBidcertIssuer String,
        controlConnectionsHistoryvDaemonHSLocalBidcertSubject String,
        controlConnectionsHistoryvDaemonHSLocalBidcertKeyType String,
        controlConnectionsHistoryvDaemonHSLocalBidcertKeyLength INTEGER,
        controlConnectionsHistoryvDaemonHSLocalCertSerial String,
        controlConnectionsHistoryvDaemonHSLocalCertIssuer String,
        controlConnectionsHistoryvDaemonHSLocalCertSubject String,
        controlConnectionsHistoryvDaemonHSLocalCertKeyType String,
        controlConnectionsHistoryvDaemonHSLocalCertKeyLength INTEGER,
        controlConnectionsHistoryvDaemonHSPeerBidcertSerial String,
        controlConnectionsHistoryvDaemonHSPeerBidcertIssuer String,
        controlConnectionsHistoryvDaemonHSPeerBidcertSubject String,
        controlConnectionsHistoryvDaemonHSPeerBidcertKeyType String,
        controlConnectionsHistoryvDaemonHSPeerBidcertKeyLength INTEGER,
        controlConnectionsHistoryvDaemonHSPeerCertSerial String,
        controlConnectionsHistoryvDaemonHSPeerCertIssuer String,
        controlConnectionsHistoryvDaemonHSPeerCertSubject String,
        controlConnectionsHistoryvDaemonHSPeerCertKeyType String,
        controlConnectionsHistoryvDaemonHSPeerCertKeyLength INTEGER,
        controlConnectionsHistorySSLHSLocalCertSerial String,
        controlConnectionsHistorySSLHSLocalCertIssuer String,
        controlConnectionsHistorySSLHSLocalCertSubject String,
        controlConnectionsHistorySSLHSLocalCertKeyType String,
        controlConnectionsHistorySSLHSLocalCertKeyLength INTEGER,
        controlConnectionsHistorySSLHSPeerCertSerial String,
        controlConnectionsHistorySSLHSPeerCertIssuer String,
        controlConnectionsHistorySSLHSPeerCertSubject String,
        controlConnectionsHistorySSLHSPeerCertKeyType String,
        controlConnectionsHistorySSLHSPeerCertKeyLength INTEGER,
        controlConnectionsHistorySSLHSPeerEphemeralGroup String
    }

-- tagpath /control/connections-history/instance
controlConnectionsHistoryInstance OBJECT-TYPE
    SYNTAX      Unsigned32
    MAX-ACCESS  not-accessible
    STATUS      current
    DESCRIPTION "vdaemon instance id"
    ::= { controlConnectionsHistoryEntry 1 }

-- tagpath /control/connections-history/index
controlConnectionsHistoryIndex OBJECT-TYPE
    SYNTAX      Unsigned32
    MAX-ACCESS  not-accessible
    STATUS      current
    DESCRIPTION "History index"
    ::= { controlConnectionsHistoryEntry 2 }

-- tagpath /control/connections-history/peer-type
controlConnectionsHistoryPeerType OBJECT-TYPE
    SYNTAX      INTEGER {unknown(0),vedge(1),vhub(2),vsmart(3),vbond(4),vmanage(5),ztp(6),vapigw(7)}
    MAX-ACCESS  read-only
    STATUS      current
    DESCRIPTION "Connection type"
    ::= { controlConnectionsHistoryEntry 3 }

-- tagpath /control/connections-history/site-id
controlConnectionsHistorySiteId OBJECT-TYPE
    SYNTAX      Unsigned32
    MAX-ACCESS  read-only
    STATUS      current
    DESCRIPTION "Site ID"
    ::= { controlConnectionsHistoryEntry 4 }

-- tagpath /control/connections-history/domain-id
controlConnectionsHistoryDomainId OBJECT-TYPE
    SYNTAX      Unsigned32
    MAX-ACCESS  read-only
    STATUS      current
    DESCRIPTION "Domain ID"
    ::= { controlConnectionsHistoryEntry 5 }

-- tagpath /control/connections-history/private-ip
controlConnectionsHistoryPrivateIp OBJECT-TYPE
    SYNTAX      InetAddressIP
    MAX-ACCESS  read-only
    STATUS      current
    DESCRIPTION "Private IP address"
    ::= { controlConnectionsHistoryEntry 6 }

-- tagpath /control/connections-history/private-port
controlConnectionsHistoryPrivatePort OBJECT-TYPE
    SYNTAX      Unsigned32
    MAX-ACCESS  read-only
    STATUS      current
    DESCRIPTION "Private port number"
    ::= { controlConnectionsHistoryEntry 7 }

-- tagpath /control/connections-history/public-ip
controlConnectionsHistoryPublicIp OBJECT-TYPE
    SYNTAX      InetAddressIP
    MAX-ACCESS  read-only
    STATUS      current
    DESCRIPTION "Public IP address"
    ::= { controlConnectionsHistoryEntry 8 }

-- tagpath /control/connections-history/public-port
controlConnectionsHistoryPublicPort OBJECT-TYPE
    SYNTAX      Unsigned32
    MAX-ACCESS  read-only
    STATUS      current
    DESCRIPTION "Public port number"
    ::= { controlConnectionsHistoryEntry 9 }

-- tagpath /control/connections-history/system-ip
controlConnectionsHistorySystemIp OBJECT-TYPE
    SYNTAX      InetAddressIP
    MAX-ACCESS  read-only
    STATUS      current
    DESCRIPTION "System IP address"
    ::= { controlConnectionsHistoryEntry 10 }

-- tagpath /control/connections-history/protocol
controlConnectionsHistoryProtocol OBJECT-TYPE
    SYNTAX      INTEGER {dtls(0),tls(1),tls-psk(2)}
    MAX-ACCESS  read-only
    STATUS      current
    DESCRIPTION "Protocol"
    DEFVAL { dtls }
    ::= { controlConnectionsHistoryEntry 11 }

-- tagpath /control/connections-history/local-color
controlConnectionsHistoryLocalColor OBJECT-TYPE
    SYNTAX      INTEGER {default(1),mpls(2),metro-ethernet(3),biz-internet(4),public-internet(5),lte(6),threeG(7),red(8),green(9),blue(10),gold(11),silver(12),bronze(13),custom1(14),custom2(15),custom3(16),private1(17),private2(18),private3(19),private4(20),private5(21),private6(22)}
    MAX-ACCESS  read-only
    STATUS      current
    DESCRIPTION "Local color"
    ::= { controlConnectionsHistoryEntry 12 }

-- tagpath /control/connections-history/remote-color
controlConnectionsHistoryRemoteColor OBJECT-TYPE
    SYNTAX      INTEGER {default(1),mpls(2),metro-ethernet(3),biz-internet(4),public-internet(5),lte(6),threeG(7),red(8),green(9),blue(10),gold(11),silver(12),bronze(13),custom1(14),custom2(15),custom3(16),private1(17),private2(18),private3(19),private4(20),private5(21),private6(22)}
    MAX-ACCESS  read-only
    STATUS      current
    DESCRIPTION "Remote color"
    ::= { controlConnectionsHistoryEntry 13 }

-- tagpath /control/connections-history/state
controlConnectionsHistoryState OBJECT-TYPE
    SYNTAX      SessionState
    MAX-ACCESS  read-only
    STATUS      current
    DESCRIPTION "State"
    ::= { controlConnectionsHistoryEntry 14 }

-- tagpath /control/connections-history/local_enum
controlConnectionsHistoryLocalEnum OBJECT-TYPE
    SYNTAX      ConnFlagEnum
    MAX-ACCESS  read-only
    STATUS      current
    DESCRIPTION "Local error reason"
    ::= { controlConnectionsHistoryEntry 15 }

-- tagpath /control/connections-history/remote_enum
controlConnectionsHistoryRemoteEnum OBJECT-TYPE
    SYNTAX      ConnFlagEnum
    MAX-ACCESS  read-only
    STATUS      current
    DESCRIPTION "Remote Error Reason"
    ::= { controlConnectionsHistoryEntry 16 }

-- tagpath /control/connections-history/local-state-info
controlConnectionsHistoryLocalStateInfo OBJECT-TYPE
    SYNTAX      String
    MAX-ACCESS  read-only
    STATUS      current
    DESCRIPTION "Local state information"
    ::= { controlConnectionsHistoryEntry 17 }

-- tagpath /control/connections-history/remote-state-info
controlConnectionsHistoryRemoteStateInfo OBJECT-TYPE
    SYNTAX      String
    MAX-ACCESS  read-only
    STATUS      current
    DESCRIPTION "Remote state information"
    ::= { controlConnectionsHistoryEntry 18 }

-- tagpath /control/connections-history/downtime
controlConnectionsHistoryDowntime OBJECT-TYPE
    SYNTAX      String
    MAX-ACCESS  read-only
    STATUS      current
    DESCRIPTION "Downtime"
    ::= { controlConnectionsHistoryEntry 19 }

-- tagpath /control/connections-history/tx_hello
controlConnectionsHistoryTxHello OBJECT-TYPE
    SYNTAX      Unsigned32
    MAX-ACCESS  read-only
    STATUS      current
    DESCRIPTION "Tx hello"
    ::= { controlConnectionsHistoryEntry 20 }

-- tagpath /control/connections-history/tx_connects
controlConnectionsHistoryTxConnects OBJECT-TYPE
    SYNTAX      Unsigned32
    MAX-ACCESS  read-only
    STATUS      current
    DESCRIPTION "Tx connects"
    ::= { controlConnectionsHistoryEntry 21 }

-- tagpath /control/connections-history/tx_registers
controlConnectionsHistoryTxRegisters OBJECT-TYPE
    SYNTAX      Unsigned32
    MAX-ACCESS  read-only
    STATUS      current
    DESCRIPTION "Tx registers"
    ::= { controlConnectionsHistoryEntry 22 }

-- tagpath /control/connections-history/tx_register_replies
controlConnectionsHistoryTxRegisterReplies OBJECT-TYPE
    SYNTAX      Unsigned32
    MAX-ACCESS  read-only
    STATUS      current
    DESCRIPTION "Tx register replies"
    ::= { controlConnectionsHistoryEntry 23 }

-- tagpath /control/connections-history/tx_challenge
controlConnectionsHistoryTxChallenge OBJECT-TYPE
    SYNTAX      Unsigned32
    MAX-ACCESS  read-only
    STATUS      current
    DESCRIPTION "Tx challenge"
    ::= { controlConnectionsHistoryEntry 24 }

-- tagpath /control/connections-history/tx_challenge_resp
controlConnectionsHistoryTxChallengeResp OBJECT-TYPE
    SYNTAX      Unsigned32
    MAX-ACCESS  read-only
    STATUS      current
    DESCRIPTION "Tx challenge response"
    ::= { controlConnectionsHistoryEntry 25 }

-- tagpath /control/connections-history/tx_challenge_ack
controlConnectionsHistoryTxChallengeAck OBJECT-TYPE
    SYNTAX      Unsigned32
    MAX-ACCESS  read-only
    STATUS      current
    DESCRIPTION "Tx challenge ack"
    ::= { controlConnectionsHistoryEntry 26 }

-- tagpath /control/connections-history/tx_teardown
controlConnectionsHistoryTxTeardown OBJECT-TYPE
    SYNTAX      Unsigned32
    MAX-ACCESS  read-only
    STATUS      current
    DESCRIPTION "Tx teardown"
    ::= { controlConnectionsHistoryEntry 27 }

-- tagpath /control/connections-history/tx_teardown_all
controlConnectionsHistoryTxTeardownAll OBJECT-TYPE
    SYNTAX      Unsigned32
    MAX-ACCESS  read-only
    STATUS      current
    DESCRIPTION "Tx teardown all connections"
    ::= { controlConnectionsHistoryEntry 28 }

-- tagpath /control/connections-history/tx_vm_to_peer
controlConnectionsHistoryTxVmToPeer OBJECT-TYPE
    SYNTAX      Unsigned32
    MAX-ACCESS  read-only
    STATUS      current
    DESCRIPTION "Tx vManage to peer"
    ::= { controlConnectionsHistoryEntry 29 }

-- tagpath /control/connections-history/tx_register_to_vm
controlConnectionsHistoryTxRegisterToVm OBJECT-TYPE
    SYNTAX      Unsigned32
    MAX-ACCESS  read-only
    STATUS      current
    DESCRIPTION "Tx register to vManage"
    ::= { controlConnectionsHistoryEntry 30 }

-- tagpath /control/connections-history/rx_hello
controlConnectionsHistoryRxHello OBJECT-TYPE
    SYNTAX      Unsigned32
    MAX-ACCESS  read-only
    STATUS      current
    DESCRIPTION "Rx hello"
    ::= { controlConnectionsHistoryEntry 31 }

-- tagpath /control/connections-history/rx_connects
controlConnectionsHistoryRxConnects OBJECT-TYPE
    SYNTAX      Unsigned32
    MAX-ACCESS  read-only
    STATUS      current
    DESCRIPTION "Rx connects"
    ::= { controlConnectionsHistoryEntry 32 }

-- tagpath /control/connections-history/rx_registers
controlConnectionsHistoryRxRegisters OBJECT-TYPE
    SYNTAX      Unsigned32
    MAX-ACCESS  read-only
    STATUS      current
    DESCRIPTION "Rx registers"
    ::= { controlConnectionsHistoryEntry 33 }

-- tagpath /control/connections-history/rx_register_replies
controlConnectionsHistoryRxRegisterReplies OBJECT-TYPE
    SYNTAX      Unsigned32
    MAX-ACCESS  read-only
    STATUS      current
    DESCRIPTION "Rx register replies"
    ::= { controlConnectionsHistoryEntry 34 }

-- tagpath /control/connections-history/rx_challenge
controlConnectionsHistoryRxChallenge OBJECT-TYPE
    SYNTAX      Unsigned32
    MAX-ACCESS  read-only
    STATUS      current
    DESCRIPTION "Rx challenge"
    ::= { controlConnectionsHistoryEntry 35 }

-- tagpath /control/connections-history/rx_challenge_resp
controlConnectionsHistoryRxChallengeResp OBJECT-TYPE
    SYNTAX      Unsigned32
    MAX-ACCESS  read-only
    STATUS      current
    DESCRIPTION "Rx challenge response"
    ::= { controlConnectionsHistoryEntry 36 }

-- tagpath /control/connections-history/rx_challenge_ack
controlConnectionsHistoryRxChallengeAck OBJECT-TYPE
    SYNTAX      Unsigned32
    MAX-ACCESS  read-only
    STATUS      current
    DESCRIPTION "Rx challenge ack"
    ::= { controlConnectionsHistoryEntry 37 }

-- tagpath /control/connections-history/rx_teardown
controlConnectionsHistoryRxTeardown OBJECT-TYPE
    SYNTAX      Unsigned32
    MAX-ACCESS  read-only
    STATUS      current
    DESCRIPTION "Rx teardown"
    ::= { controlConnectionsHistoryEntry 38 }

-- tagpath /control/connections-history/rx_vm_to_peer
controlConnectionsHistoryRxVmToPeer OBJECT-TYPE
    SYNTAX      Unsigned32
    MAX-ACCESS  read-only
    STATUS      current
    DESCRIPTION "Rx vManage to peer"
    ::= { controlConnectionsHistoryEntry 39 }

-- tagpath /control/connections-history/rx_register_to_vm
controlConnectionsHistoryRxRegisterToVm OBJECT-TYPE
    SYNTAX      Unsigned32
    MAX-ACCESS  read-only
    STATUS      current
    DESCRIPTION "Rx register to vManage"
    ::= { controlConnectionsHistoryEntry 40 }

-- tagpath /control/connections-history/rep-count
controlConnectionsHistoryRepCount OBJECT-TYPE
    SYNTAX      Unsigned32
    MAX-ACCESS  read-only
    STATUS      current
    DESCRIPTION "Repeat count"
    ::= { controlConnectionsHistoryEntry 41 }

-- tagpath /control/connections-history/prev-downtime
controlConnectionsHistoryPrevDowntime OBJECT-TYPE
    SYNTAX      String
    MAX-ACCESS  read-only
    STATUS      current
    DESCRIPTION "Previous downtime"
    ::= { controlConnectionsHistoryEntry 42 }

-- tagpath /control/connections-history/cfg-system-ip
controlConnectionsHistoryConfiguredSystemIp OBJECT-TYPE
    SYNTAX      InetAddressIP
    MAX-ACCESS  read-only
    STATUS      current
    DESCRIPTION "Configured System IP address"
    ::= { controlConnectionsHistoryEntry 43 }

-- tagpath /control/connections-history/vh-org-name
controlConnectionsHistoryVHOrgName OBJECT-TYPE
    SYNTAX      String (SIZE (1 .. 128))
    MAX-ACCESS  read-only
    STATUS      current
    DESCRIPTION "Organization Name"
    ::= { controlConnectionsHistoryEntry 44 }

-- tagpath /control/connections-history/uuid
controlConnectionsHistoryUuid OBJECT-TYPE
    SYNTAX      String
    MAX-ACCESS  read-only
    STATUS      current
    DESCRIPTION "Peer's unique device identifier"
    ::= { controlConnectionsHistoryEntry 45 }

-- tagpath /control/connections-history/tx_create_cert
controlConnectionsHistoryTxCreateCert OBJECT-TYPE
    SYNTAX      Unsigned32
    MAX-ACCESS  read-only
    STATUS      current
    DESCRIPTION "Tx create certificate to vManage"
    ::= { controlConnectionsHistoryEntry 46 }

-- tagpath /control/connections-history/rx_create_cert
controlConnectionsHistoryRxCreateCert OBJECT-TYPE
    SYNTAX      Unsigned32
    MAX-ACCESS  read-only
    STATUS      current
    DESCRIPTION "Rx create certificate from vBond"
    ::= { controlConnectionsHistoryEntry 47 }

-- tagpath /control/connections-history/tx_create_cert_reply
controlConnectionsHistoryTxCreateCertReply OBJECT-TYPE
    SYNTAX      Unsigned32
    MAX-ACCESS  read-only
    STATUS      current
    DESCRIPTION "Tx create certificate reply to vBond"
    ::= { controlConnectionsHistoryEntry 48 }

-- tagpath /control/connections-history/rx_create_cert_reply
controlConnectionsHistoryRxCreateCertReply OBJECT-TYPE
    SYNTAX      Unsigned32
    MAX-ACCESS  read-only
    STATUS      current
    DESCRIPTION "Rx create certificate reply from vManage"
    ::= { controlConnectionsHistoryEntry 49 }

-- tagpath /control/connections-history/protocol-version
controlConnectionsHistoryProtocolVersion OBJECT-TYPE
    SYNTAX      INTEGER {unknown(0),sslv3(1),tls1(2),tls11(3),tls12(4),tls13(5),dtls1(6),dtls12(7)}
    MAX-ACCESS  read-only
    STATUS      current
    DESCRIPTION "Protocol Version"
    DEFVAL { unknown }
    ::= { controlConnectionsHistoryEntry 50 }

-- tagpath /control/connections-history/cipher-name
controlConnectionsHistoryCipherName OBJECT-TYPE
    SYNTAX      String
    MAX-ACCESS  read-only
    STATUS      current
    DESCRIPTION "Cipher Name"
    ::= { controlConnectionsHistoryEntry 51 }

-- tagpath /control/connections-history/vd_handshake_local_bidcert_serial
controlConnectionsHistoryvDaemonHSLocalBidcertSerial OBJECT-TYPE
    SYNTAX     String
    MAX-ACCESS  read-only
    STATUS      current
    DESCRIPTION "vDaemon Handshake Local Board-ID Certificate Serial"
    ::= { controlConnectionsHistoryEntry 52 }

-- tagpath /control/connections-history/vd_handshake_local_bidcert_issuer
controlConnectionsHistoryvDaemonHSLocalBidcertIssuer OBJECT-TYPE
    SYNTAX     String
    MAX-ACCESS  read-only
    STATUS      current
    DESCRIPTION "vDaemon Handshake Local Board-ID Certificate Issuer"
    ::= { controlConnectionsHistoryEntry 53 }

-- tagpath /control/connections-history/vd_handshake_local_bidcert_subject
controlConnectionsHistoryvDaemonHSLocalBidcertSubject OBJECT-TYPE
    SYNTAX     String
    MAX-ACCESS  read-only
    STATUS      current
    DESCRIPTION "vDaemon Handshake Local Board-ID Certificate Subject"
    ::= { controlConnectionsHistoryEntry 54 }

-- tagpath /control/connections-history/vd_handshake_local_bidcert_key_type
controlConnectionsHistoryvDaemonHSLocalBidcertKeyType OBJECT-TYPE
    SYNTAX     String
    MAX-ACCESS  read-only
    STATUS      current
    DESCRIPTION "vDaemon Handshake Local Board-ID Key Type"
    ::= { controlConnectionsHistoryEntry 55 }

-- tagpath /control/connections-history/vd_handshake_local_bidcert_key_length
controlConnectionsHistoryvDaemonHSLocalBidcertKeyLength OBJECT-TYPE
    SYNTAX     INTEGER
    MAX-ACCESS  read-only
    STATUS      current
    DESCRIPTION "vDaemon Handshake Local Board-ID Key Length"
    ::= { controlConnectionsHistoryEntry 56 }

-- tagpath /control/connections-history/vd_handshake_local_cert_serial
controlConnectionsHistoryvDaemonHSLocalCertSerial OBJECT-TYPE
    SYNTAX     String
    MAX-ACCESS  read-only
    STATUS      current
    DESCRIPTION "vDaemon Handshake Local Certificate Serial"
    ::= { controlConnectionsHistoryEntry 57 }

-- tagpath /control/connections-history/vd_handshake_local_cert_issuer
controlConnectionsHistoryvDaemonHSLocalCertIssuer OBJECT-TYPE
    SYNTAX     String
    MAX-ACCESS  read-only
    STATUS      current
    DESCRIPTION "vDaemon Handshake Local Certificate Issuer"
    ::= { controlConnectionsHistoryEntry 58 }

-- tagpath /control/connections-history/vd_handshake_local_cert_subject
controlConnectionsHistoryvDaemonHSLocalCertSubject OBJECT-TYPE
    SYNTAX     String
    MAX-ACCESS  read-only
    STATUS      current
    DESCRIPTION "vDaemon Handshake Local Certificate Subject"
    ::= { controlConnectionsHistoryEntry 59 }

-- tagpath /control/connections-history/vd_handshake_local_cert_key_type
controlConnectionsHistoryvDaemonHSLocalCertKeyType OBJECT-TYPE
    SYNTAX     String
    MAX-ACCESS  read-only
    STATUS      current
    DESCRIPTION "vDaemon Handshake Local Certificate Key Type"
    ::= { controlConnectionsHistoryEntry 60 }

-- tagpath /control/connections-history/vd_handshake_local_key_length
controlConnectionsHistoryvDaemonHSLocalCertKeyLength OBJECT-TYPE
    SYNTAX     INTEGER
    MAX-ACCESS  read-only
    STATUS      current
    DESCRIPTION "vDaemon Handshake Local Certificate Key Length"
    ::= { controlConnectionsHistoryEntry 61 }

-- tagpath /control/connections-history/vd_handshake_peer_bidcert_serial
controlConnectionsHistoryvDaemonHSPeerBidcertSerial OBJECT-TYPE
    SYNTAX     String
    MAX-ACCESS  read-only
    STATUS      current
    DESCRIPTION "vDaemon Handshake Peer Board-ID Certificate Serial"
    ::= { controlConnectionsHistoryEntry 62 }

-- tagpath /control/connections-history/vd_handshake_peer_bidcert_issuer
controlConnectionsHistoryvDaemonHSPeerBidcertIssuer OBJECT-TYPE
    SYNTAX     String
    MAX-ACCESS  read-only
    STATUS      current
    DESCRIPTION "vDaemon Handshake Peer Board-ID Certificate Issuer"
    ::= { controlConnectionsHistoryEntry 63 }

-- tagpath /control/connections-history/vd_handshake_peer_bidcert_subject
controlConnectionsHistoryvDaemonHSPeerBidcertSubject OBJECT-TYPE
    SYNTAX     String
    MAX-ACCESS  read-only
    STATUS      current
    DESCRIPTION "vDaemon Handshake Peer Board-ID Certificate Issuer"
    ::= { controlConnectionsHistoryEntry 64 }

-- tagpath /control/connections-history/vd_handshake_peer_bidcert_key_type
controlConnectionsHistoryvDaemonHSPeerBidcertKeyType OBJECT-TYPE
    SYNTAX     String
    MAX-ACCESS  read-only
    STATUS      current
    DESCRIPTION "vDaemon Handshake Peer Board-ID Key Type"
    ::= { controlConnectionsHistoryEntry 65 }

-- tagpath /control/connections-history/vd_handshake_peer_bidcert_key_length
controlConnectionsHistoryvDaemonHSPeerBidcertKeyLength OBJECT-TYPE
    SYNTAX     INTEGER
    MAX-ACCESS  read-only
    STATUS      current
    DESCRIPTION "vDaemon Handshake Peer Board-ID Certificate Key Length"
    ::= { controlConnectionsHistoryEntry 66 }

-- tagpath /control/connections-history/vd_handshake_peer_cert_serial
controlConnectionsHistoryvDaemonHSPeerCertSerial OBJECT-TYPE
    SYNTAX     String
    MAX-ACCESS  read-only
    STATUS      current
    DESCRIPTION "vDaemon Handshake Peer Certificate Serial"
    ::= { controlConnectionsHistoryEntry 67 }

-- tagpath /control/connections-history/vd_handshake_peer_cert_issuer
controlConnectionsHistoryvDaemonHSPeerCertIssuer OBJECT-TYPE
    SYNTAX     String
    MAX-ACCESS  read-only
    STATUS      current
    DESCRIPTION "vDaemon Handshake Peer Certificate Issuer"
    ::= { controlConnectionsHistoryEntry 68 }

-- tagpath /control/connections-history/vd_handshake_peer_cert_subject
controlConnectionsHistoryvDaemonHSPeerCertSubject OBJECT-TYPE
    SYNTAX     String
    MAX-ACCESS  read-only
    STATUS      current
    DESCRIPTION "vDaemon Handshake Peer Certificate Subject"
    ::= { controlConnectionsHistoryEntry 69 }

-- tagpath /control/connections-history/vd_handshake_peer_cert_key_type
controlConnectionsHistoryvDaemonHSPeerCertKeyType OBJECT-TYPE
    SYNTAX     String
    MAX-ACCESS  read-only
    STATUS      current
    DESCRIPTION "vDaemon Handshake Peer Certficate Key Type"
    ::= { controlConnectionsHistoryEntry 70 }

-- tagpath /control/connections-history/vd_handshake_peer_cert_key_length
controlConnectionsHistoryvDaemonHSPeerCertKeyLength OBJECT-TYPE
    SYNTAX     INTEGER
    MAX-ACCESS  read-only
    STATUS      current
    DESCRIPTION "vDaemon Handshake Peer Certificate Key Length"
    ::= { controlConnectionsHistoryEntry 71 }

-- tagpath /control/connections-history/ssl_handshake_local_cert_serial
controlConnectionsHistorySSLHSLocalCertSerial OBJECT-TYPE
    SYNTAX     String
    MAX-ACCESS  read-only
    STATUS      current
    DESCRIPTION "SSL Handshake Local Certificate Serial"
    ::= { controlConnectionsHistoryEntry 72 }

-- tagpath /control/connections-history/ssl_handshake_local_cert_issuer
controlConnectionsHistorySSLHSLocalCertIssuer OBJECT-TYPE
    SYNTAX     String
    MAX-ACCESS  read-only
    STATUS      current
    DESCRIPTION "SSL Handshake Local Certificate Issuer"
    ::= { controlConnectionsHistoryEntry 73 }

-- tagpath /control/connections-history/ssl_handshake_local_cert_subject
controlConnectionsHistorySSLHSLocalCertSubject OBJECT-TYPE
    SYNTAX     String
    MAX-ACCESS  read-only
    STATUS      current
    DESCRIPTION "SSL Handshake Local Certificate Subject"
    ::= { controlConnectionsHistoryEntry 74 }

-- tagpath /control/connections-history/ssl_handshake_local_cert_key_type
controlConnectionsHistorySSLHSLocalCertKeyType OBJECT-TYPE
    SYNTAX     String
    MAX-ACCESS  read-only
    STATUS      current
    DESCRIPTION "SSL Handshake Local Certificate Key type"
    ::= { controlConnectionsHistoryEntry 75 }

-- tagpath /control/connections-history/ssl_handshake_local_cert_key_length
controlConnectionsHistorySSLHSLocalCertKeyLength OBJECT-TYPE
    SYNTAX     INTEGER
    MAX-ACCESS  read-only
    STATUS      current
    DESCRIPTION "SSL Handshake Local Certificate Key Length"
    ::= { controlConnectionsHistoryEntry 76 }

-- tagpath /control/connections-history/ssl_handshake_peer_cert_serial
controlConnectionsHistorySSLHSPeerCertSerial OBJECT-TYPE
    SYNTAX     String
    MAX-ACCESS  read-only
    STATUS      current
    DESCRIPTION "SSL Handshake Peer Certificate Serial"
    ::= { controlConnectionsHistoryEntry 77 }

-- tagpath /control/connections-history/ssl_handshake_peer_cert_issuer
controlConnectionsHistorySSLHSPeerCertIssuer OBJECT-TYPE
    SYNTAX     String
    MAX-ACCESS  read-only
    STATUS      current
    DESCRIPTION "SSL Handshake Peer Certificate Issuer"
    ::= { controlConnectionsHistoryEntry 78 }

-- tagpath /control/connections-history/ssl_handshake_peer_cert_subject
controlConnectionsHistorySSLHSPeerCertSubject OBJECT-TYPE
    SYNTAX     String
    MAX-ACCESS  read-only
    STATUS      current
    DESCRIPTION "SSL Handshake Peer Certificate Subject"
    ::= { controlConnectionsHistoryEntry 79 }

-- tagpath /control/connections-history/ssl_handshake_peer_cert_key_type
controlConnectionsHistorySSLHSPeerCertKeyType OBJECT-TYPE      
    SYNTAX     String                                  
    MAX-ACCESS  read-only                              
    STATUS      current                                
    DESCRIPTION "SSL Handshake Peer Certificate Key Type"
    ::= { controlConnectionsHistoryEntry 80 } 

-- tagpath /control/connections-history/ssl_handshake_peer_cert_key_length
controlConnectionsHistorySSLHSPeerCertKeyLength OBJECT-TYPE      
    SYNTAX     INTEGER                                  
    MAX-ACCESS  read-only                              
    STATUS      current                                
    DESCRIPTION "SSL Handshake Peer Certificate Key Length"
    ::= { controlConnectionsHistoryEntry 81 } 

-- tagpath /control/connections-history/ssl_handshake_ephemeral_group
controlConnectionsHistorySSLHSPeerEphemeralGroup OBJECT-TYPE       
    SYNTAX     String                                
    MAX-ACCESS  read-only                            
    STATUS      current                              
    DESCRIPTION "SSL Handshake Ephemeral Group"        
    ::= { controlConnectionsHistoryEntry 82 }


-- tagpath /control/local-properties/ip-address-list
controlLocalPropertiesIpAddressListTable OBJECT-TYPE
    SYNTAX      SEQUENCE OF ControlLocalPropertiesIpAddressListEntry
    MAX-ACCESS  not-accessible
    STATUS      current
    DESCRIPTION "List of IP addresses"
    ::= { controlLocalProperties 24 }

-- tagpath /control/local-properties/ip-address-list
controlLocalPropertiesIpAddressListEntry OBJECT-TYPE
    SYNTAX      ControlLocalPropertiesIpAddressListEntry
    MAX-ACCESS  not-accessible
    STATUS      current
    DESCRIPTION ""
    INDEX { controlLocalPropertiesIpAddressListIndex }
        ::= { controlLocalPropertiesIpAddressListTable 1 }

ControlLocalPropertiesIpAddressListEntry ::=
    SEQUENCE {
        controlLocalPropertiesIpAddressListIndex Unsigned32,
        controlLocalPropertiesIpAddressListIp InetAddressIP,
        controlLocalPropertiesIpAddressListPort Unsigned32
    }

-- tagpath /control/local-properties/ip-address-list/index
controlLocalPropertiesIpAddressListIndex OBJECT-TYPE
    SYNTAX      Unsigned32
    MAX-ACCESS  not-accessible
    STATUS      current
    DESCRIPTION "IP index"
    ::= { controlLocalPropertiesIpAddressListEntry 1 }

-- tagpath /control/local-properties/ip-address-list/ip
controlLocalPropertiesIpAddressListIp OBJECT-TYPE
    SYNTAX      InetAddressIP
    MAX-ACCESS  read-only
    STATUS      current
    DESCRIPTION "IP"
    ::= { controlLocalPropertiesIpAddressListEntry 2 }

-- tagpath /control/local-properties/ip-address-list/port
controlLocalPropertiesIpAddressListPort OBJECT-TYPE
    SYNTAX      Unsigned32
    MAX-ACCESS  read-only
    STATUS      current
    DESCRIPTION "Port"
    ::= { controlLocalPropertiesIpAddressListEntry 3 }

-- tagpath /control/local-properties/vbond-address-list
controlLocalPropertiesVbondAddressListTable OBJECT-TYPE
    SYNTAX      SEQUENCE OF ControlLocalPropertiesVbondAddressListEntry
    MAX-ACCESS  not-accessible
    STATUS      current
    DESCRIPTION "List of vBond peers"
    ::= { controlLocalProperties 26 }

-- tagpath /control/local-properties/vbond-address-list
controlLocalPropertiesVbondAddressListEntry OBJECT-TYPE
    SYNTAX      ControlLocalPropertiesVbondAddressListEntry
    MAX-ACCESS  not-accessible
    STATUS      current
    DESCRIPTION ""
    INDEX { controlLocalPropertiesVbondAddressListIndex }
        ::= { controlLocalPropertiesVbondAddressListTable 1 }

ControlLocalPropertiesVbondAddressListEntry ::=
    SEQUENCE {
        controlLocalPropertiesVbondAddressListIndex Unsigned32,
        controlLocalPropertiesVbondAddressListIp InetAddressIP,
        controlLocalPropertiesVbondAddressListPort Unsigned32
    }

-- tagpath /control/local-properties/vbond-address-list/index
controlLocalPropertiesVbondAddressListIndex OBJECT-TYPE
    SYNTAX      Unsigned32
    MAX-ACCESS  not-accessible
    STATUS      current
    DESCRIPTION "IP index"
    ::= { controlLocalPropertiesVbondAddressListEntry 1 }

-- tagpath /control/local-properties/vbond-address-list/ip
controlLocalPropertiesVbondAddressListIp OBJECT-TYPE
    SYNTAX      InetAddressIP
    MAX-ACCESS  read-only
    STATUS      current
    DESCRIPTION "IP address"
    ::= { controlLocalPropertiesVbondAddressListEntry 2 }

-- tagpath /control/local-properties/vbond-address-list/port
controlLocalPropertiesVbondAddressListPort OBJECT-TYPE
    SYNTAX      Unsigned32
    MAX-ACCESS  read-only
    STATUS      current
    DESCRIPTION "Port"
    ::= { controlLocalPropertiesVbondAddressListEntry 3 }

-- tagpath /control/local-properties/wan-interface-list
controlLocalPropertiesWanInterfaceListTable OBJECT-TYPE
    SYNTAX      SEQUENCE OF ControlLocalPropertiesWanInterfaceListEntry
    MAX-ACCESS  not-accessible
    STATUS      current
    DESCRIPTION "List of WAN interfaces"
    ::= { controlLocalProperties 28 }

-- tagpath /control/local-properties/vedge-list-version
controlLocalPropertiesVedgeListVersion OBJECT-TYPE
    SYNTAX      Counter64
    MAX-ACCESS  read-only
    STATUS      current
    DESCRIPTION "vEdge list version number"
    ::= { controlLocalProperties 29 }

-- tagpath /control/local-properties/vsmart-list-version
controlLocalPropertiesVsmartListVersion OBJECT-TYPE
    SYNTAX      Counter64
    MAX-ACCESS  read-only
    STATUS      current
    DESCRIPTION "vSmart list version number"
    ::= { controlLocalProperties 30 }

-- tagpath /control/local-properties/sp-organization-name
controlLocalPropertiesSPOrganizationName OBJECT-TYPE
    SYNTAX      String (SIZE (1 .. 128))
    MAX-ACCESS  read-only
    STATUS      current
    DESCRIPTION "SP Organization name"
    ::= { controlLocalProperties 31 }

-- tagpath /control/local-properties/token
controlLocalPropertiesToken OBJECT-TYPE
    SYNTAX      String (SIZE (1 .. 40))
    MAX-ACCESS  read-only
    STATUS      current
    DESCRIPTION "Token information"
    ::= { controlLocalProperties 32 }

-- tagpath /control/local-properties/cloud-hosted
controlLocalPropertiesCloudHosted OBJECT-TYPE
    SYNTAX      String
    MAX-ACCESS  read-only
    STATUS      current
    DESCRIPTION "vManage is hosted in the Cisco cloud"
    ::= { controlLocalProperties 33 }

-- tagpath /control/local-properties/embargo-check
controlLocalPropertiesEmbargoCheck OBJECT-TYPE
    SYNTAX      String
    MAX-ACCESS  read-only
    STATUS      current
    DESCRIPTION "Embargo check status"
    ::= { controlLocalProperties 34 }

-- tagpath /control/local-properties/enterprise-serial
controlLocalPropertiesEnterpriseSerial OBJECT-TYPE
    SYNTAX      String (SIZE (1 .. 40))
    MAX-ACCESS  read-only
    STATUS      current
    DESCRIPTION "Enterprise certificate serial number"
    ::= { controlLocalProperties 35 }

-- tagpath /control/local-properties/enterprise-certificate-status
controlLocalPropertiesEnterpriseCertificateStatus OBJECT-TYPE
    SYNTAX      String
    MAX-ACCESS  read-only
    STATUS      current
    DESCRIPTION "Enterprise certificate status"
    ::= { controlLocalProperties 36 }

-- tagpath /control/local-properties/enterprise-certificate-validity
controlLocalPropertiesEnterpriseCertificateValidity OBJECT-TYPE
    SYNTAX      String
    MAX-ACCESS  read-only
    STATUS      current
    DESCRIPTION "Enterprise certificate validity"
    ::= { controlLocalProperties 37 }

-- tagpath /control/local-properties/enterprise-certificate-not-valid-before
controlLocalPropertiesEnterpriseCertificateNotValidBefore OBJECT-TYPE
    SYNTAX      String
    MAX-ACCESS  read-only
    STATUS      current
    DESCRIPTION "Enterprise certificate not valid before"
    ::= { controlLocalProperties 38 }

-- tagpath /control/local-properties/enterprise-certificate-not-valid-after
controlLocalPropertiesEnterpriseCertificateNotValidAfter OBJECT-TYPE
    SYNTAX      String
    MAX-ACCESS  read-only
    STATUS      current
    DESCRIPTION "Enterprise certificate not valid after"
    ::= { controlLocalProperties 39 }

-- tagpath /control/local-properties/pairwise-keying
controlLocalPropertiesPairwiseKeying OBJECT-TYPE
    SYNTAX      String
    MAX-ACCESS  read-only
    STATUS      current
    DESCRIPTION "Pairwise keying enabled"
    ::= { controlLocalProperties 40 }

-- tagpath /control/local-properties/cdb-locked
controlLocalPropertiesCdbLocked OBJECT-TYPE
    SYNTAX      TruthValue
    MAX-ACCESS  read-only
    STATUS      current
    DESCRIPTION "CDB is locked"
    ::= { controlLocalProperties 41 }

-- tagpath /control/local-properties/subject-serial-number
controlLocalPropertiesSubjectSerialNumber OBJECT-TYPE
    SYNTAX      String (SIZE (1 .. 12))
    MAX-ACCESS  read-only
    STATUS      current
    DESCRIPTION "Subject Name Serial Number "
    ::= { controlLocalProperties 42 }

-- tagpath /control/local-properties/wan-interface-list
controlLocalPropertiesWanInterfaceListEntry OBJECT-TYPE
    SYNTAX      ControlLocalPropertiesWanInterfaceListEntry
    MAX-ACCESS  not-accessible
    STATUS      current
    DESCRIPTION ""
    INDEX { controlLocalPropertiesWanInterfaceListInstance, controlLocalPropertiesWanInterfaceListIndex }
        ::= { controlLocalPropertiesWanInterfaceListTable 1 }

ControlLocalPropertiesWanInterfaceListEntry ::=
    SEQUENCE {
        controlLocalPropertiesWanInterfaceListIndex Unsigned32,
        controlLocalPropertiesWanInterfaceListInterface String,
        controlLocalPropertiesWanInterfaceListPublicIp InetAddressIP,
        controlLocalPropertiesWanInterfaceListPublicPort Unsigned32,
        controlLocalPropertiesWanInterfaceListPrivateIp InetAddressIP,
        controlLocalPropertiesWanInterfaceListPrivatePort Unsigned32,
        controlLocalPropertiesWanInterfaceListNumVsmarts Unsigned32,
        controlLocalPropertiesWanInterfaceListNumVmanages Unsigned32,
        controlLocalPropertiesWanInterfaceListWeight Unsigned32,
        controlLocalPropertiesWanInterfaceListColor INTEGER,
        controlLocalPropertiesWanInterfaceListCarrier INTEGER,
        controlLocalPropertiesWanInterfaceListPreference Unsigned32,
        controlLocalPropertiesWanInterfaceListAdminState StateEnum,
        controlLocalPropertiesWanInterfaceListOperationState StateEnum,
        controlLocalPropertiesWanInterfaceListLastConnTime String,
        controlLocalPropertiesWanInterfaceListRestrictStr String,
        controlLocalPropertiesWanInterfaceListControlStr String,
        controlLocalPropertiesWanInterfaceListPerWanMaxControllers UnsignedByte,
        controlLocalPropertiesWanInterfaceListInstance Unsigned32,
        controlLocalPropertiesWanInterfaceListPrivateIpv6 InetAddressIP,
        controlLocalPropertiesWanInterfaceListSpiChange String,
        controlLocalPropertiesWanInterfaceListLastResort String,
        controlLocalPropertiesWanInterfaceListWanPortHopped String,
        controlLocalPropertiesWanInterfaceListWanTimeSincePortHop String,
        controlLocalPropertiesWanInterfaceListVbondAsStunServer String,
        controlLocalPropertiesWanInterfaceListVmanageConnectionPreference UnsignedByte,
        controlLocalPropertiesWanInterfaceListLowBandwidthLink String,
        controlLocalPropertiesWanInterfaceListNatType String,
        controlLocalPropertiesWanInterfaceListInterfaceAdminState StateEnum,
        controlLocalPropertiesWanInterfaceListInterfaceOperState StateEnum,
        controlLocalPropertiesWanInterfaceListRegionId String
    }

-- tagpath /control/local-properties/wan-interface-list/index
controlLocalPropertiesWanInterfaceListIndex OBJECT-TYPE
    SYNTAX      Unsigned32
    MAX-ACCESS  not-accessible
    STATUS      current
    DESCRIPTION "WAN index"
    ::= { controlLocalPropertiesWanInterfaceListEntry 1 }

-- tagpath /control/local-properties/wan-interface-list/interface
controlLocalPropertiesWanInterfaceListInterface OBJECT-TYPE
    SYNTAX      String (SIZE (1 .. 32))
    MAX-ACCESS  read-only
    STATUS      current
    DESCRIPTION "Interface name"
    ::= { controlLocalPropertiesWanInterfaceListEntry 2 }

-- tagpath /control/local-properties/wan-interface-list/public-ip
controlLocalPropertiesWanInterfaceListPublicIp OBJECT-TYPE
    SYNTAX      InetAddressIP
    MAX-ACCESS  read-only
    STATUS      current
    DESCRIPTION "Public IP address"
    ::= { controlLocalPropertiesWanInterfaceListEntry 3 }

-- tagpath /control/local-properties/wan-interface-list/public-port
controlLocalPropertiesWanInterfaceListPublicPort OBJECT-TYPE
    SYNTAX      Unsigned32
    MAX-ACCESS  read-only
    STATUS      current
    DESCRIPTION "Public port"
    ::= { controlLocalPropertiesWanInterfaceListEntry 4 }

-- tagpath /control/local-properties/wan-interface-list/private-ip
controlLocalPropertiesWanInterfaceListPrivateIp OBJECT-TYPE
    SYNTAX      InetAddressIP
    MAX-ACCESS  read-only
    STATUS      current
    DESCRIPTION "Private IP"
    ::= { controlLocalPropertiesWanInterfaceListEntry 5 }

-- tagpath /control/local-properties/wan-interface-list/private-port
controlLocalPropertiesWanInterfaceListPrivatePort OBJECT-TYPE
    SYNTAX      Unsigned32
    MAX-ACCESS  read-only
    STATUS      current
    DESCRIPTION "Private port"
    ::= { controlLocalPropertiesWanInterfaceListEntry 6 }

-- tagpath /control/local-properties/wan-interface-list/num-vsmarts
controlLocalPropertiesWanInterfaceListNumVsmarts OBJECT-TYPE
    SYNTAX      Unsigned32
    MAX-ACCESS  read-only
    STATUS      current
    DESCRIPTION "Number of vSmarts"
    ::= { controlLocalPropertiesWanInterfaceListEntry 7 }

-- tagpath /control/local-properties/wan-interface-list/num-vmanages
controlLocalPropertiesWanInterfaceListNumVmanages OBJECT-TYPE
    SYNTAX      Unsigned32
    MAX-ACCESS  read-only
    STATUS      current
    DESCRIPTION "Number of vManages"
    ::= { controlLocalPropertiesWanInterfaceListEntry 8 }

-- tagpath /control/local-properties/wan-interface-list/weight
controlLocalPropertiesWanInterfaceListWeight OBJECT-TYPE
    SYNTAX      Unsigned32
    MAX-ACCESS  read-only
    STATUS      current
    DESCRIPTION "Weight"
    ::= { controlLocalPropertiesWanInterfaceListEntry 9 }

-- tagpath /control/local-properties/wan-interface-list/color
controlLocalPropertiesWanInterfaceListColor OBJECT-TYPE
    SYNTAX      INTEGER {default(1),mpls(2),metro-ethernet(3),biz-internet(4),public-internet(5),lte(6),threeG(7),red(8),green(9),blue(10),gold(11),silver(12),bronze(13),custom1(14),custom2(15),custom3(16),private1(17),private2(18),private3(19),private4(20),private5(21),private6(22)}
    MAX-ACCESS  read-only
    STATUS      current
    DESCRIPTION "Color"
    ::= { controlLocalPropertiesWanInterfaceListEntry 10 }

-- tagpath /control/local-properties/wan-interface-list/carrier
controlLocalPropertiesWanInterfaceListCarrier OBJECT-TYPE
    SYNTAX      INTEGER {default(1),carrier1(2),carrier2(3),carrier3(4),carrier4(5),carrier5(6),carrier6(7),carrier7(8),carrier8(9)}
    MAX-ACCESS  read-only
    STATUS      current
    DESCRIPTION "Carrier"
    ::= { controlLocalPropertiesWanInterfaceListEntry 11 }

-- tagpath /control/local-properties/wan-interface-list/preference
controlLocalPropertiesWanInterfaceListPreference OBJECT-TYPE
    SYNTAX      Unsigned32
    MAX-ACCESS  read-only
    STATUS      current
    DESCRIPTION "Preference"
    ::= { controlLocalPropertiesWanInterfaceListEntry 12 }

-- tagpath /control/local-properties/wan-interface-list/admin-state
controlLocalPropertiesWanInterfaceListAdminState OBJECT-TYPE
    SYNTAX      StateEnum
    MAX-ACCESS  read-only
    STATUS      current
    DESCRIPTION "Administrative state"
    ::= { controlLocalPropertiesWanInterfaceListEntry 13 }

-- tagpath /control/local-properties/wan-interface-list/operation-state
controlLocalPropertiesWanInterfaceListOperationState OBJECT-TYPE
    SYNTAX      StateEnum
    MAX-ACCESS  read-only
    STATUS      current
    DESCRIPTION "Operational state"
    ::= { controlLocalPropertiesWanInterfaceListEntry 14 }

-- tagpath /control/local-properties/wan-interface-list/last-conn-time
controlLocalPropertiesWanInterfaceListLastConnTime OBJECT-TYPE
    SYNTAX      String
    MAX-ACCESS  read-only
    STATUS      current
    DESCRIPTION "Time since last connection"
    ::= { controlLocalPropertiesWanInterfaceListEntry 15 }

-- tagpath /control/local-properties/wan-interface-list/restrict-str
controlLocalPropertiesWanInterfaceListRestrictStr OBJECT-TYPE
    SYNTAX      String
    MAX-ACCESS  read-only
    STATUS      current
    DESCRIPTION "Restrict"
    ::= { controlLocalPropertiesWanInterfaceListEntry 16 }

-- tagpath /control/local-properties/wan-interface-list/control-str
controlLocalPropertiesWanInterfaceListControlStr OBJECT-TYPE
    SYNTAX      String
    MAX-ACCESS  read-only
    STATUS      current
    DESCRIPTION "Control connections required"
    ::= { controlLocalPropertiesWanInterfaceListEntry 17 }

-- tagpath /control/local-properties/wan-interface-list/per-wan-max-controllers
controlLocalPropertiesWanInterfaceListPerWanMaxControllers OBJECT-TYPE
    SYNTAX      UnsignedByte
    MAX-ACCESS  read-only
    STATUS      current
    DESCRIPTION "Maximum number of controllers on this WAN interface"
    ::= { controlLocalPropertiesWanInterfaceListEntry 18 }

-- tagpath /control/local-properties/wan-interface-list/instance
controlLocalPropertiesWanInterfaceListInstance OBJECT-TYPE
    SYNTAX      Unsigned32
    MAX-ACCESS  not-accessible
    STATUS      current
    DESCRIPTION "vdaemon instance ID"
    ::= { controlLocalPropertiesWanInterfaceListEntry 19 }

-- tagpath /control/local-properties/wan-interface-list/private-ipv6
controlLocalPropertiesWanInterfaceListPrivateIpv6 OBJECT-TYPE
    SYNTAX      InetAddressIP
    MAX-ACCESS  read-only
    STATUS      current
    DESCRIPTION "Private IPv6 address"
    ::= { controlLocalPropertiesWanInterfaceListEntry 20 }

-- tagpath /control/local-properties/wan-interface-list/spi-change
controlLocalPropertiesWanInterfaceListSpiChange OBJECT-TYPE
    SYNTAX      String
    MAX-ACCESS  read-only
    STATUS      current
    DESCRIPTION "Time left until SPI change"
    ::= { controlLocalPropertiesWanInterfaceListEntry 21 }

-- tagpath /control/local-properties/wan-interface-list/last-resort
controlLocalPropertiesWanInterfaceListLastResort OBJECT-TYPE
    SYNTAX      String
    MAX-ACCESS  read-only
    STATUS      current
    DESCRIPTION "Last-resort Interface"
    ::= { controlLocalPropertiesWanInterfaceListEntry 22 }

-- tagpath /control/local-properties/wan-interface-list/wan-port-hopped
controlLocalPropertiesWanInterfaceListWanPortHopped OBJECT-TYPE
    SYNTAX      String
    MAX-ACCESS  read-only
    STATUS      current
    DESCRIPTION "Interface changed port"
    ::= { controlLocalPropertiesWanInterfaceListEntry 23 }

-- tagpath /control/local-properties/wan-interface-list/wan-time-since-port-hop
controlLocalPropertiesWanInterfaceListWanTimeSincePortHop OBJECT-TYPE
    SYNTAX      String
    MAX-ACCESS  read-only
    STATUS      current
    DESCRIPTION "Time since the interface changed port"
    ::= { controlLocalPropertiesWanInterfaceListEntry 24 }

-- tagpath /control/local-properties/wan-interface-list/vbond-as-stun-server
controlLocalPropertiesWanInterfaceListVbondAsStunServer OBJECT-TYPE
    SYNTAX      String
    MAX-ACCESS  read-only
    STATUS      current
    DESCRIPTION "Vbond As Stun Server"
    ::= { controlLocalPropertiesWanInterfaceListEntry 25 }

-- tagpath /control/local-properties/wan-interface-list/vmanage-connection-preference
controlLocalPropertiesWanInterfaceListVmanageConnectionPreference OBJECT-TYPE
    SYNTAX      UnsignedByte
    MAX-ACCESS  read-only
    STATUS      current
    DESCRIPTION "Interface preference for control connection to vManage"
    ::= { controlLocalPropertiesWanInterfaceListEntry 26 }

-- tagpath /control/local-properties/wan-interface-list/low-bandwidth-link
controlLocalPropertiesWanInterfaceListLowBandwidthLink OBJECT-TYPE
    SYNTAX      String
    MAX-ACCESS  read-only
    STATUS      current
    DESCRIPTION "Low bandwidth interface"
    ::= { controlLocalPropertiesWanInterfaceListEntry 27 }

-- tagpath /control/local-properties/wan-interface-list/nat-type
controlLocalPropertiesWanInterfaceListNatType OBJECT-TYPE
    SYNTAX      String
    MAX-ACCESS  read-only
    STATUS      current
    DESCRIPTION "NAT Type"
    ::= { controlLocalPropertiesWanInterfaceListEntry 31 }

-- tagpath /control/local-properties/wan-interface-list/interface-admin-state
controlLocalPropertiesWanInterfaceListInterfaceAdminState OBJECT-TYPE
    SYNTAX      StateEnum
    MAX-ACCESS  read-only
    STATUS      current
    DESCRIPTION "Interface administrative state"
    ::= { controlLocalPropertiesWanInterfaceListEntry 32 }

-- tagpath /control/local-properties/wan-interface-list/interface-oper-state
controlLocalPropertiesWanInterfaceListInterfaceOperState OBJECT-TYPE
    SYNTAX      StateEnum
    MAX-ACCESS  read-only
    STATUS      current
    DESCRIPTION "Interface operational state"
    ::= { controlLocalPropertiesWanInterfaceListEntry 33 }

-- tagpath /control/local-properties/wan-interface-list/region-id
controlLocalPropertiesWanInterfaceListRegionId OBJECT-TYPE
    SYNTAX      String
    MAX-ACCESS  read-only
    STATUS      current
    DESCRIPTION "Region id"
    ::= { controlLocalPropertiesWanInterfaceListEntry 34 }

-- tagpath /control/valid-vsmarts
controlValidVsmartsTable OBJECT-TYPE
    SYNTAX      SEQUENCE OF ControlValidVsmartsEntry
    MAX-ACCESS  not-accessible
    STATUS      current
    DESCRIPTION "Display valid vSmarts"
    ::= { control 6 }

-- tagpath /control/valid-vsmarts
controlValidVsmartsEntry OBJECT-TYPE
    SYNTAX      ControlValidVsmartsEntry
    MAX-ACCESS  not-accessible
    STATUS      current
    DESCRIPTION ""
    INDEX { controlValidVsmartsSerialNumber, controlValidVsmartsOrg }
        ::= { controlValidVsmartsTable 1 }

ControlValidVsmartsEntry ::=
    SEQUENCE {
        controlValidVsmartsSerialNumber String,
        controlValidVsmartsOrg          String,
        controlValidVsmartsDeviceState  INTEGER
    }

-- tagpath /control/valid-vsmarts/serial-number
controlValidVsmartsSerialNumber OBJECT-TYPE
    SYNTAX      String (SIZE (1 .. 40))
    MAX-ACCESS  read-only
    STATUS      current
    DESCRIPTION "Serial number of the device"
    ::= { controlValidVsmartsEntry 1 }

-- tagpath /control/valid-vsmarts/org
controlValidVsmartsOrg OBJECT-TYPE
    SYNTAX      String (SIZE (1 .. 128))
    MAX-ACCESS  read-only
    STATUS      current
    DESCRIPTION "Organization that the controller belongs to"
    ::= { controlValidVsmartsEntry 2 }

-- tagpath /control/valid-vsmarts/device-state
controlValidVsmartsDeviceState OBJECT-TYPE
    SYNTAX      INTEGER {invalid(0),valid(1),config-init(2)}
    MAX-ACCESS  read-only
    STATUS      current
    DESCRIPTION "The state that the controller currently has"
    ::= { controlValidVsmartsEntry 3 }

-- tagpath /control/valid-vedges
controlValidVedgesTable OBJECT-TYPE
    SYNTAX      SEQUENCE OF ControlValidVedgesEntry
    MAX-ACCESS  not-accessible
    STATUS      current
    DESCRIPTION "Display valid vedges"
    ::= { control 7 }

-- tagpath /control/valid-vedges
controlValidVedgesEntry OBJECT-TYPE
    SYNTAX      ControlValidVedgesEntry
    MAX-ACCESS  not-accessible
    STATUS      current
    DESCRIPTION ""
    INDEX { IMPLIED controlValidVedgesChassisNumber }
        ::= { controlValidVedgesTable 1 }

ControlValidVedgesEntry ::=
    SEQUENCE {
        controlValidVedgesChassisNumber String,
        controlValidVedgesSerialNumber String,
        controlValidVedgesValidity INTEGER,
        controlValidVedgesOrg String,
        controlValidVedgesHardwareInstalledSerialNumber String,
        controlValidVedgesSubjectSerialNumber String
    }

-- tagpath /control/valid-vedges/chassis-number
controlValidVedgesChassisNumber OBJECT-TYPE
    SYNTAX      String (SIZE (1 .. 40))
    MAX-ACCESS  not-accessible
    STATUS      current
    DESCRIPTION "Chassis number of the device"
    ::= { controlValidVedgesEntry 1 }

-- tagpath /control/valid-vedges/serial-number
controlValidVedgesSerialNumber OBJECT-TYPE
    SYNTAX      String (SIZE (1 .. 40))
    MAX-ACCESS  read-only
    STATUS      current
    DESCRIPTION "Serial number of the device"
    ::= { controlValidVedgesEntry 2 }

-- tagpath /control/valid-vedges/validity
controlValidVedgesValidity OBJECT-TYPE
    SYNTAX      INTEGER {valid(1),invalid(2),staging(3)}
    MAX-ACCESS  read-only
    STATUS      current
    DESCRIPTION "Device valid or staging"
    ::= { controlValidVedgesEntry 3 }

-- tagpath /control/valid-vedges/org
controlValidVedgesOrg OBJECT-TYPE
    SYNTAX      String (SIZE (1 .. 128))
    MAX-ACCESS  read-only
    STATUS      current
    DESCRIPTION "Organization that the vedge belongs to"
    ::= { controlValidVedgesEntry 4 }

-- tagpath /control/valid-vedges/hardware-installed-serial-number
controlValidVedgesHardwareInstalledSerialNumber OBJECT-TYPE
    SYNTAX      String (SIZE (1 .. 40))
    MAX-ACCESS  read-only
    STATUS      current
    DESCRIPTION "Installed Serial number of the device"
    ::= { controlValidVedgesEntry 5 }

-- tagpath /control/valid-vedges/subject-serial-number
controlValidVedgesSubjectSerialNumber OBJECT-TYPE
    SYNTAX      String (SIZE (1 .. 12))
    MAX-ACCESS  read-only
    STATUS      current
    DESCRIPTION "Subject Serial number of the device"
    ::= { controlValidVedgesEntry 6 }

-- tagpath /control/summary
controlSummaryTable OBJECT-TYPE
    SYNTAX      SEQUENCE OF ControlSummaryEntry
    MAX-ACCESS  not-accessible
    STATUS      current
    DESCRIPTION "Display control summary"
    ::= { control 8 }

-- tagpath /control/summary
controlSummaryEntry OBJECT-TYPE
    SYNTAX      ControlSummaryEntry
    MAX-ACCESS  not-accessible
    STATUS      current
    DESCRIPTION ""
    INDEX { controlSummaryInstance }
        ::= { controlSummaryTable 1 }

ControlSummaryEntry ::=
    SEQUENCE {
        controlSummaryInstance Unsigned32,
        controlSummaryVbondCounts UnsignedShort,
        controlSummaryVmanageCounts UnsignedShort,
        controlSummaryVsmartCounts UnsignedShort,
        controlSummaryVedgeCounts UnsignedShort,
        controlSummaryProtocol INTEGER,
        controlSummaryListeningIp InetAddressIP,
        controlSummaryListeningPort Unsigned32,
        controlSummaryListeningIpv6 InetAddressIP,
        controlSummaryValidControllerCounts UnsignedShort
    }

-- tagpath /control/summary/instance
controlSummaryInstance OBJECT-TYPE
    SYNTAX      Unsigned32
    MAX-ACCESS  not-accessible
    STATUS      current
    DESCRIPTION "vdaemon instance id"
    ::= { controlSummaryEntry 1 }

-- tagpath /control/summary/vbond_counts
controlSummaryVbondCounts OBJECT-TYPE
    SYNTAX      UnsignedShort
    MAX-ACCESS  read-only
    STATUS      current
    DESCRIPTION ""
    ::= { controlSummaryEntry 2 }

-- tagpath /control/summary/vmanage_counts
controlSummaryVmanageCounts OBJECT-TYPE
    SYNTAX      UnsignedShort
    MAX-ACCESS  read-only
    STATUS      current
    DESCRIPTION ""
    ::= { controlSummaryEntry 3 }

-- tagpath /control/summary/vsmart_counts
controlSummaryVsmartCounts OBJECT-TYPE
    SYNTAX      UnsignedShort
    MAX-ACCESS  read-only
    STATUS      current
    DESCRIPTION ""
    ::= { controlSummaryEntry 4 }

-- tagpath /control/summary/vedge_counts
controlSummaryVedgeCounts OBJECT-TYPE
    SYNTAX      UnsignedShort
    MAX-ACCESS  read-only
    STATUS      current
    DESCRIPTION ""
    ::= { controlSummaryEntry 5 }

-- tagpath /control/summary/protocol
controlSummaryProtocol OBJECT-TYPE
    SYNTAX      INTEGER {dtls(0),tls(1),tls-psk(2)}
    MAX-ACCESS  read-only
    STATUS      current
    DESCRIPTION "Protocol"
    ::= { controlSummaryEntry 6 }

-- tagpath /control/summary/listening_ip
controlSummaryListeningIp OBJECT-TYPE
    SYNTAX      InetAddressIP
    MAX-ACCESS  not-accessible
    STATUS      current
    DESCRIPTION "Listening IP address"
    ::= { controlSummaryEntry 7 }

-- tagpath /control/summary/listening_port
controlSummaryListeningPort OBJECT-TYPE
    SYNTAX      Unsigned32
    MAX-ACCESS  not-accessible
    STATUS      current
    DESCRIPTION "Listening port number"
    ::= { controlSummaryEntry 8 }

-- tagpath /control/summary/listening_ipv6
controlSummaryListeningIpv6 OBJECT-TYPE
    SYNTAX      InetAddressIP
    MAX-ACCESS  not-accessible
    STATUS      current
    DESCRIPTION "Listening IPv6 address"
    ::= { controlSummaryEntry 9 }

-- tagpath /control/summary/valid_controller_counts
controlSummaryValidControllerCounts OBJECT-TYPE
    SYNTAX      UnsignedShort
    MAX-ACCESS  read-only
    STATUS      current
    DESCRIPTION "Valid Controller Counts"
    ::= { controlSummaryEntry 10 }

-- tagpath /control/valid-vmanage-id
controlValidVmanageIdTable OBJECT-TYPE
    SYNTAX      SEQUENCE OF ControlValidVmanageIdEntry
    MAX-ACCESS  not-accessible
    STATUS      current
    DESCRIPTION "Display valid vManage CA id"
    ::= { control 10 }

-- tagpath /control/valid-vmanage-id
controlValidVmanageIdEntry OBJECT-TYPE
    SYNTAX      ControlValidVmanageIdEntry
    MAX-ACCESS  not-accessible
    STATUS      current
    DESCRIPTION ""
    INDEX { IMPLIED controlValidVManageIdChassisNumbers }
        ::= { controlValidVmanageIdTable 1 }

ControlValidVmanageIdEntry ::=
    SEQUENCE {
        controlValidVManageIdChassisNumbers String
    }

-- tagpath /control/valid-vmanage-id/chassis-number
controlValidVManageIdChassisNumbers OBJECT-TYPE
    SYNTAX      String (SIZE (1 .. 40))
    MAX-ACCESS  read-only
    STATUS      current
    DESCRIPTION "Chassis number of the device"
    ::= { controlValidVmanageIdEntry 1 }

-- tagpath /control/tenant-connections
controlTenantConnectionsTable OBJECT-TYPE
    SYNTAX      SEQUENCE OF ControlTenantConnectionsEntry
    MAX-ACCESS  not-accessible
    STATUS      current
    DESCRIPTION "Display tenant control connections information"
    ::= { control 11 }

-- tagpath /control/tenant-connections
controlTenantConnectionsEntry OBJECT-TYPE
    SYNTAX      ControlTenantConnectionsEntry
    MAX-ACCESS  not-accessible
    STATUS      current
    DESCRIPTION ""
    INDEX { controlTenantConnectionsInstance, controlTenantConnectionsSiteId, controlTenantConnectionsDomainId,
            controlTenantConnectionsLocalPrivateIp, controlTenantConnectionsLocalPrivatePort,
            controlTenantConnectionsPublicIp, controlTenantConnectionsPublicPort, controlTenantConnectionsTenantIdx }
        ::= { controlTenantConnectionsTable 1 }

ControlTenantConnectionsEntry ::=
    SEQUENCE {
        controlTenantConnectionsInstance Unsigned32,
        controlTenantConnectionsSiteId Unsigned32,
        controlTenantConnectionsDomainId Unsigned32,
        controlTenantConnectionsLocalPrivateIp InetAddressIP,
        controlTenantConnectionsLocalPrivatePort Unsigned32,
        controlTenantConnectionsPublicIp InetAddressIP,
        controlTenantConnectionsPublicPort Unsigned32,
        controlTenantConnectionsTenantIdx Unsigned32,
        controlTenantConnectionsPeerSystemIp InetAddressIP,
        controlTenantConnectionsColor INTEGER,
        controlTenantConnectionsTenantName String
    }

-- tagpath /control/tenant-connections/instance
controlTenantConnectionsInstance OBJECT-TYPE
    SYNTAX      Unsigned32
    MAX-ACCESS  not-accessible
    STATUS      current
    DESCRIPTION "vdaemon instance ID"
    ::= { controlTenantConnectionsEntry 1 }

-- tagpath /control/tenant-connections/site-id
controlTenantConnectionsSiteId OBJECT-TYPE
    SYNTAX      Unsigned32
    MAX-ACCESS  not-accessible
    STATUS      current
    DESCRIPTION "Site ID"
    ::= { controlTenantConnectionsEntry 2 }

-- tagpath /control/tenant-connections/domain-id
controlTenantConnectionsDomainId OBJECT-TYPE
    SYNTAX      Unsigned32
    MAX-ACCESS  not-accessible
    STATUS      current
    DESCRIPTION "Domain ID"
    ::= { controlTenantConnectionsEntry 3 }

-- tagpath /control/tenant-connections/local-private-ip
controlTenantConnectionsLocalPrivateIp OBJECT-TYPE
    SYNTAX      InetAddressIP
    MAX-ACCESS  not-accessible
    STATUS      current
    DESCRIPTION "Private IP address"
    ::= { controlTenantConnectionsEntry 4 }

-- tagpath /control/tenant-connections/local-private-port
controlTenantConnectionsLocalPrivatePort OBJECT-TYPE
    SYNTAX      Unsigned32
    MAX-ACCESS  not-accessible
    STATUS      current
    DESCRIPTION "Private port number"
    ::= { controlTenantConnectionsEntry 5 }

-- tagpath /control/tenant-connections/public-ip
controlTenantConnectionsPublicIp OBJECT-TYPE
    SYNTAX      InetAddressIP
    MAX-ACCESS  not-accessible
    STATUS      current
    DESCRIPTION "Public IP address"
    ::= { controlTenantConnectionsEntry 6 }

-- tagpath /control/tenant-connections/public-port
controlTenantConnectionsPublicPort OBJECT-TYPE
    SYNTAX      Unsigned32
    MAX-ACCESS  not-accessible
    STATUS      current
    DESCRIPTION "Public port number"
    ::= { controlTenantConnectionsEntry 7 }

-- tagpath /control/tenant-connections/tenant-idx
controlTenantConnectionsTenantIdx OBJECT-TYPE
    SYNTAX      Unsigned32 (0 .. 65535)
    MAX-ACCESS  not-accessible
    STATUS      current
    DESCRIPTION "Internal Tenant index"
    ::= { controlTenantConnectionsEntry 8 }

-- tagpath /control/tenant-connections/peer-system-ip
controlTenantConnectionsPeerSystemIp OBJECT-TYPE
    SYNTAX      InetAddressIP
    MAX-ACCESS  read-only
    STATUS      current
    DESCRIPTION "Peer System IP address"
    ::= { controlTenantConnectionsEntry 9 }

-- tagpath /control/tenant-connections/color
controlTenantConnectionsColor OBJECT-TYPE
    SYNTAX      INTEGER {default(1),mpls(2),metro-ethernet(3),biz-internet(4),public-internet(5),lte(6),threeG(7),red(8),green(9),blue(10),gold(11),silver(12),bronze(13),custom1(14),custom2(15),custom3(16),private1(17),private2(18),private3(19),private4(20),private5(21),private6(22)}
    MAX-ACCESS  read-only
    STATUS      current
    DESCRIPTION "color"
    ::= { controlTenantConnectionsEntry 10 }

-- tagpath /control/tenant-connections/tenant-name
controlTenantConnectionsTenantName OBJECT-TYPE
    SYNTAX      String (SIZE (1 .. 128))
    MAX-ACCESS  read-only
    STATUS      current
    DESCRIPTION "Tenant name"
    ::= { controlTenantConnectionsEntry 11 }


-- tagpath /orchestrator/connections
orchestratorConnectionsTable OBJECT-TYPE
    SYNTAX      SEQUENCE OF OrchestratorConnectionsEntry
    MAX-ACCESS  not-accessible
    STATUS      current
    DESCRIPTION "Display orchestrator connection information"
    ::= { orchestrator 1 }

-- tagpath /orchestrator/connections
orchestratorConnectionsEntry OBJECT-TYPE
    SYNTAX      OrchestratorConnectionsEntry
    MAX-ACCESS  not-accessible
    STATUS      current
    DESCRIPTION ""
    INDEX { orchestratorConnectionsInstance, orchestratorConnectionsPeerType, orchestratorConnectionsSiteId, orchestratorConnectionsDomainId, orchestratorConnectionsLocalPrivateIp, orchestratorConnectionsLocalPrivatePort, orchestratorConnectionsPublicIp, orchestratorConnectionsPublicPort }
        ::= { orchestratorConnectionsTable 1 }

OrchestratorConnectionsEntry ::=
    SEQUENCE {
        orchestratorConnectionsInstance Unsigned32,
        orchestratorConnectionsPeerType INTEGER,
        orchestratorConnectionsSiteId Unsigned32,
        orchestratorConnectionsDomainId Unsigned32,
        orchestratorConnectionsProtocol INTEGER,
        orchestratorConnectionsLocalPrivateIp InetAddressIP,
        orchestratorConnectionsLocalPrivatePort Unsigned32,
        orchestratorConnectionsPublicIp InetAddressIP,
        orchestratorConnectionsPublicPort Unsigned32,
        orchestratorConnectionsSystemIp InetAddressIP,
        orchestratorConnectionsLocalColor INTEGER,
        orchestratorConnectionsRemoteColor INTEGER,
        orchestratorConnectionsPrivateIp InetAddressIP,
        orchestratorConnectionsPrivatePort Unsigned32,
        orchestratorConnectionsState SessionState,
        orchestratorConnectionsLocalEnum ConnFlagEnum,
        orchestratorConnectionsRemoteEnum ConnFlagEnum,
        orchestratorConnectionsLocalStateInfo String,
        orchestratorConnectionsRemoteStateInfo String,
        orchestratorConnectionsUptime String,
        orchestratorConnectionsTxHello Unsigned32,
        orchestratorConnectionsTxConnects Unsigned32,
        orchestratorConnectionsTxRegisters Unsigned32,
        orchestratorConnectionsTxRegisterReplies Unsigned32,
        orchestratorConnectionsTxChallenge Unsigned32,
        orchestratorConnectionsTxChallengeResp Unsigned32,
        orchestratorConnectionsTxChallengeAck Unsigned32,
        orchestratorConnectionsTxTeardown Unsigned32,
        orchestratorConnectionsTxTeardownAll Unsigned32,
        orchestratorConnectionsTxVmToPeer Unsigned32,
        orchestratorConnectionsTxRegisterToVm Unsigned32,
        orchestratorConnectionsRxHello Unsigned32,
        orchestratorConnectionsRxConnects Unsigned32,
        orchestratorConnectionsRxRegisters Unsigned32,
        orchestratorConnectionsRxRegisterReplies Unsigned32,
        orchestratorConnectionsRxChallenge Unsigned32,
        orchestratorConnectionsRxChallengeResp Unsigned32,
        orchestratorConnectionsRxChallengeAck Unsigned32,
        orchestratorConnectionsRxTeardown Unsigned32,
        orchestratorConnectionsRxVmToPeer Unsigned32,
        orchestratorConnectionsRxRegisterToVm Unsigned32,
        orchestratorConnectionsNegotiatedHelloInterval Unsigned32,
        orchestratorConnectionsNegotiatedHelloTolerance Unsigned32,
        orchestratorConnectionsOrgname String,
        orchestratorConnectionsSporgname String,
        orchestratorConnectionsTxCreateCert Unsigned32,
        orchestratorConnectionsRxCreateCert Unsigned32,
        orchestratorConnectionsTxCreateCertReply Unsigned32,
        orchestratorConnectionsRxCreateCertReply Unsigned32,
        orchestratorConnectionsCloudHosted TruthValue,
        orchestratorConnectionsPeerRegionIdSet String,
        orchestratorConnectionsPeerSessId Counter64,
        orchestratorConnectionsProtocolVersion INTEGER,
        orchestratorConnectionsCipherName String,
        orchestratorConnectionsvDaemonHSLocalBidcertSerial String,
        orchestratorConnectionsvDaemonHSLocalBidcertIssuer String,
        orchestratorConnectionsvDaemonHSLocalBidcertSubject String,
        orchestratorConnectionsvDaemonHSLocalBidcertKeyType String,
        orchestratorConnectionsvDaemonHSLocalBidcertKeyLength INTEGER,
        orchestratorConnectionsvDaemonHSLocalCertSerial String,
        orchestratorConnectionsvDaemonHSLocalCertIssuer String,
        orchestratorConnectionsvDaemonHSLocalCertSubject String,
        orchestratorConnectionsvDaemonHSLocalCertKeyType String,
        orchestratorConnectionsvDaemonHSLocalCertKeyLength INTEGER,
        orchestratorConnectionsvDaemonHSPeerBidcertSerial String,
        orchestratorConnectionsvDaemonHSPeerBidcertIssuer String,
        orchestratorConnectionsvDaemonHSPeerBidcertSubject String,
        orchestratorConnectionsvDaemonHSPeerBidcertKeyType String,
        orchestratorConnectionsvDaemonHSPeerBidcertKeyLength INTEGER,
        orchestratorConnectionsvDaemonHSPeerCertSerial String,
        orchestratorConnectionsvDaemonHSPeerCertIssuer String,
        orchestratorConnectionsvDaemonHSPeerCertSubject String,
        orchestratorConnectionsvDaemonHSPeerCertKeyType String,
        orchestratorConnectionsvDaemonHSPeerCertKeyLength INTEGER,
        orchestratorConnectionsSSLHSLocalCertSerial String,
        orchestratorConnectionsSSLHSLocalCertIssuer String,
        orchestratorConnectionsSSLHSLocalCertSubject String,
        orchestratorConnectionsSSLHSLocalCertKeyType String,
        orchestratorConnectionsSSLHSLocalCertKeyLength INTEGER,
        orchestratorConnectionsSSLHSPeerCertSerial String,
        orchestratorConnectionsSSLHSPeerCertIssuer String,
        orchestratorConnectionsSSLHSPeerCertSubject String,
        orchestratorConnectionsSSLHSPeerCertKeyType String,
        orchestratorConnectionsSSLHSPeerCertKeyLength INTEGER,
        orchestratorConnectionsSSLHSPeerEphemeralGroup String
    }

-- tagpath /orchestrator/connections/instance
orchestratorConnectionsInstance OBJECT-TYPE
    SYNTAX      Unsigned32
    MAX-ACCESS  not-accessible
    STATUS      current
    DESCRIPTION "vdaemon instance id"
    ::= { orchestratorConnectionsEntry 1 }

-- tagpath /orchestrator/connections/peer-type
orchestratorConnectionsPeerType OBJECT-TYPE
    SYNTAX      INTEGER {unknown(0),vedge(1),vhub(2),vsmart(3),vbond(4),vmanage(5),ztp(6),vapigw(7)}
    MAX-ACCESS  not-accessible
    STATUS      current
    DESCRIPTION "Connection type"
    ::= { orchestratorConnectionsEntry 2 }

-- tagpath /orchestrator/connections/site-id
orchestratorConnectionsSiteId OBJECT-TYPE
    SYNTAX      Unsigned32
    MAX-ACCESS  not-accessible
    STATUS      current
    DESCRIPTION "Site ID"
    ::= { orchestratorConnectionsEntry 3 }

-- tagpath /orchestrator/connections/domain-id
orchestratorConnectionsDomainId OBJECT-TYPE
    SYNTAX      Unsigned32
    MAX-ACCESS  not-accessible
    STATUS      current
    DESCRIPTION "Domain ID"
    ::= { orchestratorConnectionsEntry 4 }

-- tagpath /orchestrator/connections/protocol
orchestratorConnectionsProtocol OBJECT-TYPE
    SYNTAX      INTEGER {dtls(0),tls(1),tls-psk(2)}
    MAX-ACCESS  read-only
    STATUS      current
    DESCRIPTION "Protocol"
    DEFVAL { dtls }
    ::= { orchestratorConnectionsEntry 5 }

-- tagpath /orchestrator/connections/local-private-ip
orchestratorConnectionsLocalPrivateIp OBJECT-TYPE
    SYNTAX      InetAddressIP
    MAX-ACCESS  not-accessible
    STATUS      current
    DESCRIPTION "Private IP address"
    ::= { orchestratorConnectionsEntry 6 }

-- tagpath /orchestrator/connections/local-private-port
orchestratorConnectionsLocalPrivatePort OBJECT-TYPE
    SYNTAX      Unsigned32
    MAX-ACCESS  not-accessible
    STATUS      current
    DESCRIPTION "Private port number"
    ::= { orchestratorConnectionsEntry 7 }

-- tagpath /orchestrator/connections/public-ip
orchestratorConnectionsPublicIp OBJECT-TYPE
    SYNTAX      InetAddressIP
    MAX-ACCESS  not-accessible
    STATUS      current
    DESCRIPTION "Public IP address"
    ::= { orchestratorConnectionsEntry 8 }

-- tagpath /orchestrator/connections/public-port
orchestratorConnectionsPublicPort OBJECT-TYPE
    SYNTAX      Unsigned32
    MAX-ACCESS  not-accessible
    STATUS      current
    DESCRIPTION "Public port number"
    ::= { orchestratorConnectionsEntry 9 }

-- tagpath /orchestrator/connections/system-ip
orchestratorConnectionsSystemIp OBJECT-TYPE
    SYNTAX      InetAddressIP
    MAX-ACCESS  read-only
    STATUS      current
    DESCRIPTION "System IP address"
    ::= { orchestratorConnectionsEntry 10 }

-- tagpath /orchestrator/connections/local-color
orchestratorConnectionsLocalColor OBJECT-TYPE
    SYNTAX      INTEGER {default(1),mpls(2),metro-ethernet(3),biz-internet(4),public-internet(5),lte(6),threeG(7),red(8),green(9),blue(10),gold(11),silver(12),bronze(13),custom1(14),custom2(15),custom3(16),private1(17),private2(18),private3(19),private4(20),private5(21),private6(22)}
    MAX-ACCESS  read-only
    STATUS      current
    DESCRIPTION "Local color"
    ::= { orchestratorConnectionsEntry 11 }

-- tagpath /orchestrator/connections/remote-color
orchestratorConnectionsRemoteColor OBJECT-TYPE
    SYNTAX      INTEGER {default(1),mpls(2),metro-ethernet(3),biz-internet(4),public-internet(5),lte(6),threeG(7),red(8),green(9),blue(10),gold(11),silver(12),bronze(13),custom1(14),custom2(15),custom3(16),private1(17),private2(18),private3(19),private4(20),private5(21),private6(22)}
    MAX-ACCESS  read-only
    STATUS      current
    DESCRIPTION "Remote color"
    ::= { orchestratorConnectionsEntry 12 }

-- tagpath /orchestrator/connections/private-ip
orchestratorConnectionsPrivateIp OBJECT-TYPE
    SYNTAX      InetAddressIP
    MAX-ACCESS  read-only
    STATUS      current
    DESCRIPTION "Private IP address"
    ::= { orchestratorConnectionsEntry 13 }

-- tagpath /orchestrator/connections/private-port
orchestratorConnectionsPrivatePort OBJECT-TYPE
    SYNTAX      Unsigned32
    MAX-ACCESS  read-only
    STATUS      current
    DESCRIPTION "Private port"
    ::= { orchestratorConnectionsEntry 14 }

-- tagpath /orchestrator/connections/state
orchestratorConnectionsState OBJECT-TYPE
    SYNTAX      SessionState
    MAX-ACCESS  read-only
    STATUS      current
    DESCRIPTION "State"
    ::= { orchestratorConnectionsEntry 15 }

-- tagpath /orchestrator/connections/local_enum
orchestratorConnectionsLocalEnum OBJECT-TYPE
    SYNTAX      ConnFlagEnum
    MAX-ACCESS  read-only
    STATUS      current
    DESCRIPTION "Local error reason"
    ::= { orchestratorConnectionsEntry 16 }

-- tagpath /orchestrator/connections/remote_enum
orchestratorConnectionsRemoteEnum OBJECT-TYPE
    SYNTAX      ConnFlagEnum
    MAX-ACCESS  read-only
    STATUS      current
    DESCRIPTION "Remote error reason"
    ::= { orchestratorConnectionsEntry 17 }

-- tagpath /orchestrator/connections/local-state-info
orchestratorConnectionsLocalStateInfo OBJECT-TYPE
    SYNTAX      String
    MAX-ACCESS  read-only
    STATUS      current
    DESCRIPTION "Local state information"
    ::= { orchestratorConnectionsEntry 18 }

-- tagpath /orchestrator/connections/remote-state-info
orchestratorConnectionsRemoteStateInfo OBJECT-TYPE
    SYNTAX      String
    MAX-ACCESS  read-only
    STATUS      current
    DESCRIPTION "Remote state information"
    ::= { orchestratorConnectionsEntry 19 }

-- tagpath /orchestrator/connections/uptime
orchestratorConnectionsUptime OBJECT-TYPE
    SYNTAX      String
    MAX-ACCESS  read-only
    STATUS      current
    DESCRIPTION "Uptime"
    ::= { orchestratorConnectionsEntry 20 }

-- tagpath /orchestrator/connections/tx_hello
orchestratorConnectionsTxHello OBJECT-TYPE
    SYNTAX      Unsigned32
    MAX-ACCESS  read-only
    STATUS      current
    DESCRIPTION "Tx hello"
    ::= { orchestratorConnectionsEntry 21 }

-- tagpath /orchestrator/connections/tx_connects
orchestratorConnectionsTxConnects OBJECT-TYPE
    SYNTAX      Unsigned32
    MAX-ACCESS  read-only
    STATUS      current
    DESCRIPTION "Tx connects"
    ::= { orchestratorConnectionsEntry 22 }

-- tagpath /orchestrator/connections/tx_registers
orchestratorConnectionsTxRegisters OBJECT-TYPE
    SYNTAX      Unsigned32
    MAX-ACCESS  read-only
    STATUS      current
    DESCRIPTION "Tx registers"
    ::= { orchestratorConnectionsEntry 23 }

-- tagpath /orchestrator/connections/tx_register_replies
orchestratorConnectionsTxRegisterReplies OBJECT-TYPE
    SYNTAX      Unsigned32
    MAX-ACCESS  read-only
    STATUS      current
    DESCRIPTION "Tx register replies"
    ::= { orchestratorConnectionsEntry 24 }

-- tagpath /orchestrator/connections/tx_challenge
orchestratorConnectionsTxChallenge OBJECT-TYPE
    SYNTAX      Unsigned32
    MAX-ACCESS  read-only
    STATUS      current
    DESCRIPTION "Tx challenge"
    ::= { orchestratorConnectionsEntry 25 }

-- tagpath /orchestrator/connections/tx_challenge_resp
orchestratorConnectionsTxChallengeResp OBJECT-TYPE
    SYNTAX      Unsigned32
    MAX-ACCESS  read-only
    STATUS      current
    DESCRIPTION "Tx challenge response"
    ::= { orchestratorConnectionsEntry 26 }

-- tagpath /orchestrator/connections/tx_challenge_ack
orchestratorConnectionsTxChallengeAck OBJECT-TYPE
    SYNTAX      Unsigned32
    MAX-ACCESS  read-only
    STATUS      current
    DESCRIPTION "Tx challenge ack"
    ::= { orchestratorConnectionsEntry 27 }

-- tagpath /orchestrator/connections/tx_teardown
orchestratorConnectionsTxTeardown OBJECT-TYPE
    SYNTAX      Unsigned32
    MAX-ACCESS  read-only
    STATUS      current
    DESCRIPTION "Tx teardown"
    ::= { orchestratorConnectionsEntry 28 }

-- tagpath /orchestrator/connections/tx_teardown_all
orchestratorConnectionsTxTeardownAll OBJECT-TYPE
    SYNTAX      Unsigned32
    MAX-ACCESS  read-only
    STATUS      current
    DESCRIPTION "Tx teardown all connections"
    ::= { orchestratorConnectionsEntry 29 }

-- tagpath /orchestrator/connections/tx_vm_to_peer
orchestratorConnectionsTxVmToPeer OBJECT-TYPE
    SYNTAX      Unsigned32
    MAX-ACCESS  read-only
    STATUS      current
    DESCRIPTION "Tx vManage to peer"
    ::= { orchestratorConnectionsEntry 30 }

-- tagpath /orchestrator/connections/tx_register_to_vm
orchestratorConnectionsTxRegisterToVm OBJECT-TYPE
    SYNTAX      Unsigned32
    MAX-ACCESS  read-only
    STATUS      current
    DESCRIPTION "Tx register to vManage"
    ::= { orchestratorConnectionsEntry 31 }

-- tagpath /orchestrator/connections/rx_hello
orchestratorConnectionsRxHello OBJECT-TYPE
    SYNTAX      Unsigned32
    MAX-ACCESS  read-only
    STATUS      current
    DESCRIPTION "Rx hello"
    ::= { orchestratorConnectionsEntry 32 }

-- tagpath /orchestrator/connections/rx_connects
orchestratorConnectionsRxConnects OBJECT-TYPE
    SYNTAX      Unsigned32
    MAX-ACCESS  read-only
    STATUS      current
    DESCRIPTION "Rx connects"
    ::= { orchestratorConnectionsEntry 33 }

-- tagpath /orchestrator/connections/rx_registers
orchestratorConnectionsRxRegisters OBJECT-TYPE
    SYNTAX      Unsigned32
    MAX-ACCESS  read-only
    STATUS      current
    DESCRIPTION "Rx registers"
    ::= { orchestratorConnectionsEntry 34 }

-- tagpath /orchestrator/connections/rx_register_replies
orchestratorConnectionsRxRegisterReplies OBJECT-TYPE
    SYNTAX      Unsigned32
    MAX-ACCESS  read-only
    STATUS      current
    DESCRIPTION "Rx register replies"
    ::= { orchestratorConnectionsEntry 35 }

-- tagpath /orchestrator/connections/rx_challenge
orchestratorConnectionsRxChallenge OBJECT-TYPE
    SYNTAX      Unsigned32
    MAX-ACCESS  read-only
    STATUS      current
    DESCRIPTION "Rx challenge"
    ::= { orchestratorConnectionsEntry 36 }

-- tagpath /orchestrator/connections/rx_challenge_resp
orchestratorConnectionsRxChallengeResp OBJECT-TYPE
    SYNTAX      Unsigned32
    MAX-ACCESS  read-only
    STATUS      current
    DESCRIPTION "Rx challenge response"
    ::= { orchestratorConnectionsEntry 37 }

-- tagpath /orchestrator/connections/rx_challenge_ack
orchestratorConnectionsRxChallengeAck OBJECT-TYPE
    SYNTAX      Unsigned32
    MAX-ACCESS  read-only
    STATUS      current
    DESCRIPTION "Rx challenge ack"
    ::= { orchestratorConnectionsEntry 38 }

-- tagpath /orchestrator/connections/rx_teardown
orchestratorConnectionsRxTeardown OBJECT-TYPE
    SYNTAX      Unsigned32
    MAX-ACCESS  read-only
    STATUS      current
    DESCRIPTION "Rx teardown"
    ::= { orchestratorConnectionsEntry 39 }

-- tagpath /orchestrator/connections/rx_vm_to_peer
orchestratorConnectionsRxVmToPeer OBJECT-TYPE
    SYNTAX      Unsigned32
    MAX-ACCESS  read-only
    STATUS      current
    DESCRIPTION "Rx vManage to peer"
    ::= { orchestratorConnectionsEntry 40 }

-- tagpath /orchestrator/connections/rx_register_to_vm
orchestratorConnectionsRxRegisterToVm OBJECT-TYPE
    SYNTAX      Unsigned32
    MAX-ACCESS  read-only
    STATUS      current
    DESCRIPTION "Rx register to vManage"
    ::= { orchestratorConnectionsEntry 41 }

-- tagpath /orchestrator/connections/negotiated_hello_interval
orchestratorConnectionsNegotiatedHelloInterval OBJECT-TYPE
    SYNTAX      Unsigned32
    MAX-ACCESS  read-only
    STATUS      current
    DESCRIPTION "Negotiated hello interval"
    ::= { orchestratorConnectionsEntry 42 }

-- tagpath /orchestrator/connections/negotiated_hello_tolerance
orchestratorConnectionsNegotiatedHelloTolerance OBJECT-TYPE
    SYNTAX      Unsigned32
    MAX-ACCESS  read-only
    STATUS      current
    DESCRIPTION "Negotiated hello tolerance"
    ::= { orchestratorConnectionsEntry 43 }

-- tagpath /orchestrator/connections/orgname
orchestratorConnectionsOrgname OBJECT-TYPE
    SYNTAX      String (SIZE (1 .. 128))
    MAX-ACCESS  read-only
    STATUS      current
    DESCRIPTION "Organization Name"
    ::= { orchestratorConnectionsEntry 44 }

-- tagpath /orchestrator/connections/sporgname
orchestratorConnectionsSporgname OBJECT-TYPE
    SYNTAX      String (SIZE (1 .. 128))
    MAX-ACCESS  read-only
    STATUS      current
    DESCRIPTION "SP Organization Name"
    ::= { orchestratorConnectionsEntry 45 }

-- tagpath /orchestrator/connections/tx_create_cert
orchestratorConnectionsTxCreateCert OBJECT-TYPE
    SYNTAX      Unsigned32
    MAX-ACCESS  read-only
    STATUS      current
    DESCRIPTION "Tx create certificate to vManage"
    ::= { orchestratorConnectionsEntry 46 }

-- tagpath /orchestrator/connections/rx_create_cert
orchestratorConnectionsRxCreateCert OBJECT-TYPE
    SYNTAX      Unsigned32
    MAX-ACCESS  read-only
    STATUS      current
    DESCRIPTION "Rx create certificate from vBond"
    ::= { orchestratorConnectionsEntry 47 }

-- tagpath /orchestrator/connections/tx_create_cert_reply
orchestratorConnectionsTxCreateCertReply OBJECT-TYPE
    SYNTAX      Unsigned32
    MAX-ACCESS  read-only
    STATUS      current
    DESCRIPTION "Tx create certificate reply to vBond"
    ::= { orchestratorConnectionsEntry 48 }

-- tagpath /orchestrator/connections/rx_create_cert_reply
orchestratorConnectionsRxCreateCertReply OBJECT-TYPE
    SYNTAX      Unsigned32
    MAX-ACCESS  read-only
    STATUS      current
    DESCRIPTION "Rx create certificate reply from vManage"
    ::= { orchestratorConnectionsEntry 49 }

-- tagpath /orchestrator/connections/cloud-hosted
orchestratorConnectionsCloudHosted OBJECT-TYPE
    SYNTAX      TruthValue
    MAX-ACCESS  read-only
    STATUS      current
    DESCRIPTION "Controller hosted in Cisco cloud"
    ::= { orchestratorConnectionsEntry 50 }

-- tagpath /orchestrator/connections/peer-region-id-set
orchestratorConnectionsPeerRegionIdSet OBJECT-TYPE
    SYNTAX      String
    MAX-ACCESS  read-only
    STATUS      current
    DESCRIPTION "Peer region id set"
    ::= { orchestratorConnectionsEntry 51 }

-- tagpath /orchestrator/connections/peer-sess-id
orchestratorConnectionsPeerSessId OBJECT-TYPE
    SYNTAX      Counter64
    MAX-ACCESS  read-only
    STATUS      current
    DESCRIPTION "Peer Session ID"
    ::= { orchestratorConnectionsEntry 52 }

-- tagpath /orchestrator/connections/protocol-version
orchestratorConnectionsProtocolVersion OBJECT-TYPE
    SYNTAX      INTEGER {unknown(0),sslv3(1),tls1(2),tls11(3),tls12(4),tls13(5),dtls1(6),dtls12(7)}
    MAX-ACCESS  read-only
    STATUS      current
    DESCRIPTION "Protocol Version"
    DEFVAL { unknown }
    ::= { orchestratorConnectionsEntry 53 }

-- tagpath /orchestrator/connections/cipher-name
orchestratorConnectionsCipherName OBJECT-TYPE
    SYNTAX      String
    MAX-ACCESS  read-only
    STATUS      current
    DESCRIPTION "Cipher Name"
    ::= { orchestratorConnectionsEntry 54 }

-- tagpath /orchestrator/connections/vd_handshake_local_bidcert_serial
orchestratorConnectionsvDaemonHSLocalBidcertSerial OBJECT-TYPE
    SYNTAX     String
    MAX-ACCESS  read-only
    STATUS      current
    DESCRIPTION "vDaemon Handshake Local Board-ID Certificate Serial"
    ::= { orchestratorConnectionsEntry 55 }

-- tagpath /orchestrator/connections/vd_handshake_local_bidcert_issuer
orchestratorConnectionsvDaemonHSLocalBidcertIssuer OBJECT-TYPE
    SYNTAX     String
    MAX-ACCESS  read-only
    STATUS      current
    DESCRIPTION "vDaemon Handshake Local Board-ID Certificate Issuer"
    ::= { orchestratorConnectionsEntry 56 }

-- tagpath /orchestrator/connections/vd_handshake_local_bidcert_subject
orchestratorConnectionsvDaemonHSLocalBidcertSubject OBJECT-TYPE
    SYNTAX     String
    MAX-ACCESS  read-only
    STATUS      current
    DESCRIPTION "vDaemon Handshake Local Board-ID Certificate Subject"
    ::= { orchestratorConnectionsEntry 57 }

-- tagpath /orchestrator/connections/vd_handshake_local_bidcert_key_type
orchestratorConnectionsvDaemonHSLocalBidcertKeyType OBJECT-TYPE
    SYNTAX     String
    MAX-ACCESS  read-only
    STATUS      current
    DESCRIPTION "vDaemon Handshake Local Board-ID Certificate Key Type"
    ::= { orchestratorConnectionsEntry 58 }

-- tagpath /orchestrator/connections/vd_handshake_local_bidcert_key_length
orchestratorConnectionsvDaemonHSLocalBidcertKeyLength OBJECT-TYPE
    SYNTAX     INTEGER
    MAX-ACCESS  read-only
    STATUS      current
    DESCRIPTION "vDaemon Handshake Local Board-ID Certificate Key Length"
    ::= { orchestratorConnectionsEntry 59 }

-- tagpath /orchestrator/connections/vd_handshake_local_cert_serial
orchestratorConnectionsvDaemonHSLocalCertSerial OBJECT-TYPE
    SYNTAX     String
    MAX-ACCESS  read-only
    STATUS      current
    DESCRIPTION "vDaemon Handshake Local Certificate Serial"
    ::= { orchestratorConnectionsEntry 60 }

-- tagpath /orchestrator/connections/vd_handshake_local_cert_issuer
orchestratorConnectionsvDaemonHSLocalCertIssuer OBJECT-TYPE
    SYNTAX     String
    MAX-ACCESS  read-only
    STATUS      current
    DESCRIPTION "vDaemon Handshake Local Certificate Issuer"
    ::= { orchestratorConnectionsEntry 61 }

-- tagpath /orchestrator/connections/vd_handshake_local_cert_subject
orchestratorConnectionsvDaemonHSLocalCertSubject OBJECT-TYPE
    SYNTAX     String
    MAX-ACCESS  read-only
    STATUS      current
    DESCRIPTION "vDaemon Handshake Local Certificate Subject"
    ::= { orchestratorConnectionsEntry 62 }

-- tagpath /orchestrator/connections/vd_handshake_local_cert_key_type
orchestratorConnectionsvDaemonHSLocalCertKeyType OBJECT-TYPE
    SYNTAX     String
    MAX-ACCESS  read-only
    STATUS      current
    DESCRIPTION "vDaemon Handshake Local Certificate Key Type"
    ::= { orchestratorConnectionsEntry 63 }

-- tagpath /orchestrator/connections/vd_handshake_local_cert_key_length
orchestratorConnectionsvDaemonHSLocalCertKeyLength OBJECT-TYPE
    SYNTAX     INTEGER
    MAX-ACCESS  read-only
    STATUS      current
    DESCRIPTION "vDaemon Handshake Local Certificate Key Length"
    ::= { orchestratorConnectionsEntry 64 }

-- tagpath /orchestrator/connections/vd_handshake_peer_bidcert_serial
orchestratorConnectionsvDaemonHSPeerBidcertSerial OBJECT-TYPE
    SYNTAX     String
    MAX-ACCESS  read-only
    STATUS      current
    DESCRIPTION "vDaemon Handshake Peer Board-ID Certificate Serial"
    ::= { orchestratorConnectionsEntry 65 }

-- tagpath /orchestrator/connections/vd_handshake_peer_bidcert_issuer
orchestratorConnectionsvDaemonHSPeerBidcertIssuer OBJECT-TYPE
    SYNTAX     String
    MAX-ACCESS  read-only
    STATUS      current
    DESCRIPTION "vDaemon Handshake Peer Board-ID Certificate Issuer"
    ::= { orchestratorConnectionsEntry 66 }

-- tagpath /orchestrator/connections/vd_handshake_peer_bidcert_subject
orchestratorConnectionsvDaemonHSPeerBidcertSubject OBJECT-TYPE
    SYNTAX     String
    MAX-ACCESS  read-only
    STATUS      current
    DESCRIPTION "vDaemon Handshake Peer Board-ID Certificate Subject"
    ::= { orchestratorConnectionsEntry 67 }

-- tagpath /orchestrator/connections/vd_handshake_peer_bidcert_key_type
orchestratorConnectionsvDaemonHSPeerBidcertKeyType OBJECT-TYPE
    SYNTAX     String
    MAX-ACCESS  read-only
    STATUS      current
    DESCRIPTION "vDaemon Handshake Peer Board-ID Certificate Key Type"
    ::= { orchestratorConnectionsEntry 68 }

-- tagpath /orchestrator/connections/vd_handshake_peer_bidcert_key_length
orchestratorConnectionsvDaemonHSPeerBidcertKeyLength OBJECT-TYPE
    SYNTAX     INTEGER
    MAX-ACCESS  read-only
    STATUS      current
    DESCRIPTION "vDaemon Handshake Peer Board-ID Certificate Key Length"
    ::= { orchestratorConnectionsEntry 69 }

-- tagpath /orchestrator/connections/vd_handshake_peer_cert_serial
orchestratorConnectionsvDaemonHSPeerCertSerial OBJECT-TYPE
    SYNTAX     String
    MAX-ACCESS  read-only
    STATUS      current
    DESCRIPTION "vDaemon Handshake Peer Certificate Serial"
    ::= { orchestratorConnectionsEntry 70 }

-- tagpath /orchestrator/connections/vd_handshake_peer_cert_issuer
orchestratorConnectionsvDaemonHSPeerCertIssuer OBJECT-TYPE
    SYNTAX     String
    MAX-ACCESS  read-only
    STATUS      current
    DESCRIPTION "vDaemon Handshake Peer Certificate Issuer"
    ::= { orchestratorConnectionsEntry 71 }

-- tagpath /orchestrator/connections/vd_handshake_peer_cert_subject
orchestratorConnectionsvDaemonHSPeerCertSubject OBJECT-TYPE
    SYNTAX     String
    MAX-ACCESS  read-only
    STATUS      current
    DESCRIPTION "vDaemon Handshake Peer Certificate Subject"
    ::= { orchestratorConnectionsEntry 72 }

-- tagpath /orchestrator/connections/vd_handshake_peer_cert_key_type
orchestratorConnectionsvDaemonHSPeerCertKeyType OBJECT-TYPE
    SYNTAX     String
    MAX-ACCESS  read-only
    STATUS      current
    DESCRIPTION "vDaemon Handshake Peer Certificate Key Type"
    ::= { orchestratorConnectionsEntry 73 }

-- tagpath /orchestrator/connections/vd_handshake_peer_cert_key_length
orchestratorConnectionsvDaemonHSPeerCertKeyLength OBJECT-TYPE
    SYNTAX     INTEGER
    MAX-ACCESS  read-only
    STATUS      current
    DESCRIPTION "vDaemon Handshake Peer Certificate Key Length"
    ::= { orchestratorConnectionsEntry 74 }

-- tagpath /orchestrator/connections/ssl_handshake_local_cert_serial
orchestratorConnectionsSSLHSLocalCertSerial OBJECT-TYPE
    SYNTAX     String
    MAX-ACCESS  read-only
    STATUS      current
    DESCRIPTION "SSL Handshake Local Certificate Serial"
    ::= { orchestratorConnectionsEntry 75 }

-- tagpath /orchestrator/connections/ssl_handshake_local_cert_issuer
orchestratorConnectionsSSLHSLocalCertIssuer OBJECT-TYPE
    SYNTAX     String
    MAX-ACCESS  read-only
    STATUS      current
    DESCRIPTION "SSL Handshake Local Certificate Issuer"
    ::= { orchestratorConnectionsEntry 76 }

-- tagpath /orchestrator/connections/ssl_handshake_local_cert_subject
orchestratorConnectionsSSLHSLocalCertSubject OBJECT-TYPE
    SYNTAX     String
    MAX-ACCESS  read-only
    STATUS      current
    DESCRIPTION "SSL Handshake Local Certificate Subject"
    ::= { orchestratorConnectionsEntry 77 }

-- tagpath /orchestrator/connections/ssl_handshake_local_cert_key_type
orchestratorConnectionsSSLHSLocalCertKeyType OBJECT-TYPE
    SYNTAX     String
    MAX-ACCESS  read-only
    STATUS      current
    DESCRIPTION "SSL Handshake Local Certificate Key Type"
    ::= { orchestratorConnectionsEntry 78 }

-- tagpath /orchestrator/connections/ssl_handshake_local_cert_key_length
orchestratorConnectionsSSLHSLocalCertKeyLength OBJECT-TYPE
    SYNTAX     INTEGER
    MAX-ACCESS  read-only
    STATUS      current
    DESCRIPTION "SSL Handshake Local Certificate Key Length"
    ::= { orchestratorConnectionsEntry 79 }

-- tagpath /orchestrator/connections/ssl_handshake_peer_cert_serial
orchestratorConnectionsSSLHSPeerCertSerial OBJECT-TYPE
    SYNTAX     String
    MAX-ACCESS  read-only
    STATUS      current
    DESCRIPTION "SSL Handshake Peer Certificate Serial"
    ::= { orchestratorConnectionsEntry 80 }

-- tagpath /orchestrator/connections/ssl_handshake_peer_cert_issuer
orchestratorConnectionsSSLHSPeerCertIssuer OBJECT-TYPE
    SYNTAX     String
    MAX-ACCESS  read-only
    STATUS      current
    DESCRIPTION "SSL Handshake Peer Certificate Issuer"
    ::= { orchestratorConnectionsEntry 81 }

-- tagpath /orchestrator/connections/ssl_handshake_peer_cert_subject
orchestratorConnectionsSSLHSPeerCertSubject OBJECT-TYPE
    SYNTAX     String
    MAX-ACCESS  read-only
    STATUS      current
    DESCRIPTION "SSL Handshake Peer Certificate Subject"
    ::= { orchestratorConnectionsEntry 82 }

-- tagpath /orchestrator/connections/ssl_handshake_peer_cert_key_type
orchestratorConnectionsSSLHSPeerCertKeyType OBJECT-TYPE
    SYNTAX     String
    MAX-ACCESS  read-only
    STATUS      current
    DESCRIPTION "SSL Handshake Peer Key Type"
    ::= { orchestratorConnectionsEntry 83 }

-- tagpath /orchestrator/connections/ssl_handshake_peer_cert_key_length
orchestratorConnectionsSSLHSPeerCertKeyLength OBJECT-TYPE
    SYNTAX     INTEGER
    MAX-ACCESS  read-only
    STATUS      current
    DESCRIPTION "SSL Handshake Peer Certificate Key Length"
    ::= { orchestratorConnectionsEntry 84 }

-- tagpath /orchestrator/connections/ssl_handshake_ephemeral_group
orchestratorConnectionsSSLHSPeerEphemeralGroup OBJECT-TYPE  
    SYNTAX     String                                
    MAX-ACCESS  read-only                            
    STATUS      current                              
    DESCRIPTION "SSL Handshake Ephemeral Group"        
    ::= { orchestratorConnectionsEntry 85 }

-- tagpath /orchestrator/connections-history
orchestratorConnectionsHistoryTable OBJECT-TYPE
    SYNTAX      SEQUENCE OF OrchestratorConnectionsHistoryEntry
    MAX-ACCESS  not-accessible
    STATUS      current
    DESCRIPTION "Display orchestrator connection history"
    ::= { orchestrator 2 }

-- tagpath /orchestrator/connections-history
orchestratorConnectionsHistoryEntry OBJECT-TYPE
    SYNTAX      OrchestratorConnectionsHistoryEntry
    MAX-ACCESS  not-accessible
    STATUS      current
    DESCRIPTION ""
    INDEX { orchestratorConnectionsHistoryInstance, orchestratorConnectionsHistoryIndex }
        ::= { orchestratorConnectionsHistoryTable 1 }

OrchestratorConnectionsHistoryEntry ::=
    SEQUENCE {
        orchestratorConnectionsHistoryInstance Unsigned32,
        orchestratorConnectionsHistoryIndex Unsigned32,
        orchestratorConnectionsHistoryPeerType INTEGER,
        orchestratorConnectionsHistorySiteId Unsigned32,
        orchestratorConnectionsHistoryDomainId Unsigned32,
        orchestratorConnectionsHistoryProtocol INTEGER,
        orchestratorConnectionsHistoryPrivateIp InetAddressIP,
        orchestratorConnectionsHistoryPrivatePort Unsigned32,
        orchestratorConnectionsHistoryPublicIp InetAddressIP,
        orchestratorConnectionsHistoryPublicPort Unsigned32,
        orchestratorConnectionsHistorySystemIp InetAddressIP,
        orchestratorConnectionsHistoryLocalColor INTEGER,
        orchestratorConnectionsHistoryRemoteColor INTEGER,
        orchestratorConnectionsHistoryState SessionState,
        orchestratorConnectionsHistoryLocalEnum ConnFlagEnum,
        orchestratorConnectionsHistoryRemoteEnum ConnFlagEnum,
        orchestratorConnectionsHistoryLocalStateInfo String,
        orchestratorConnectionsHistoryRemoteStateInfo String,
        orchestratorConnectionsHistoryLocalPrivateIp InetAddressIP,
        orchestratorConnectionsHistoryLocalPrivatePort Unsigned32,
        orchestratorConnectionsHistoryDowntime String,
        orchestratorConnectionsHistoryTxHello Unsigned32,
        orchestratorConnectionsHistoryTxConnects Unsigned32,
        orchestratorConnectionsHistoryTxRegisters Unsigned32,
        orchestratorConnectionsHistoryTxRegisterReplies Unsigned32,
        orchestratorConnectionsHistoryTxChallenge Unsigned32,
        orchestratorConnectionsHistoryTxChallengeResp Unsigned32,
        orchestratorConnectionsHistoryTxChallengeAck Unsigned32,
        orchestratorConnectionsHistoryTxTeardown Unsigned32,
        orchestratorConnectionsHistoryTxTeardownAll Unsigned32,
        orchestratorConnectionsHistoryTxVmToPeer Unsigned32,
        orchestratorConnectionsHistoryTxRegisterToVm Unsigned32,
        orchestratorConnectionsHistoryRxHello Unsigned32,
        orchestratorConnectionsHistoryRxConnects Unsigned32,
        orchestratorConnectionsHistoryRxRegisters Unsigned32,
        orchestratorConnectionsHistoryRxRegisterReplies Unsigned32,
        orchestratorConnectionsHistoryRxChallenge Unsigned32,
        orchestratorConnectionsHistoryRxChallengeResp Unsigned32,
        orchestratorConnectionsHistoryRxChallengeAck Unsigned32,
        orchestratorConnectionsHistoryRxTeardown Unsigned32,
        orchestratorConnectionsHistoryRxVmToPeer Unsigned32,
        orchestratorConnectionsHistoryRxRegisterToVm Unsigned32,
        orchestratorConnectionsHistoryRepCount Unsigned32,
        orchestratorConnectionsHistoryPrevDowntime String,
        orchestratorConnectionsHistoryHOrgname String,
        orchestratorConnectionsHistoryHSporgname String,
        orchestratorConnectionsHistoryUuid String,
        orchestratorConnectionsHistoryTxCreateCert Unsigned32,
        orchestratorConnectionsHistoryRxCreateCert Unsigned32,
        orchestratorConnectionsHistoryTxCreateCertReply Unsigned32,
        orchestratorConnectionsHistoryRxCreateCertReply Unsigned32,
        orchestratorConnectionsHistoryProtocolVersion INTEGER,
        orchestratorConnectionsHistoryCipherName String,
        orchestratorConnectionsHistoryvDaemonHSLocalBidcertSerial String,
        orchestratorConnectionsHistoryvDaemonHSLocalBidcertIssuer String,
        orchestratorConnectionsHistoryvDaemonHSLocalBidcertSubject String,
        orchestratorConnectionsHistoryvDaemonHSLocalBidcertKeyType String,
        orchestratorConnectionsHistoryvDaemonHSLocalBidcertKeyLength INTEGER,
        orchestratorConnectionsHistoryvDaemonHSLocalCertSerial String,
        orchestratorConnectionsHistoryvDaemonHSLocalCertIssuer String,
        orchestratorConnectionsHistoryvDaemonHSLocalCertSubject String,
        orchestratorConnectionsHistoryvDaemonHSLocalCertKeyType String,
        orchestratorConnectionsHistoryvDaemonHSLocalCertKeyLength INTEGER,
        orchestratorConnectionsHistoryvDaemonHSPeerBidcertSerial String,
        orchestratorConnectionsHistoryvDaemonHSPeerBidcertIssuer String,
        orchestratorConnectionsHistoryvDaemonHSPeerBidcertSubject String,
        orchestratorConnectionsHistoryvDaemonHSPeerBidcertKeyType String,
        orchestratorConnectionsHistoryvDaemonHSPeerBidcertKeyLength INTEGER,
        orchestratorConnectionsHistoryvDaemonHSPeerCertSerial String,
        orchestratorConnectionsHistoryvDaemonHSPeerCertIssuer String,
        orchestratorConnectionsHistoryvDaemonHSPeerCertSubject String,
        orchestratorConnectionsHistoryvDaemonHSPeerCertKeyType String,
        orchestratorConnectionsHistoryvDaemonHSPeerCertKeyLength INTEGER,
        orchestratorConnectionsHistorySSLHSLocalCertSerial String,
        orchestratorConnectionsHistorySSLHSLocalCertIssuer String,
        orchestratorConnectionsHistorySSLHSLocalCertSubject String,
        orchestratorConnectionsHistorySSLHSLocalCertKeyType String,
        orchestratorConnectionsHistorySSLHSLocalCertKeyLength INTEGER,
        orchestratorConnectionsHistorySSLHSPeerCertSerial String,
        orchestratorConnectionsHistorySSLHSPeerCertIssuer String,
        orchestratorConnectionsHistorySSLHSPeerCertSubject String,
        orchestratorConnectionsHistorySSLHSPeerCertKeyType String,
        orchestratorConnectionsHistorySSLHSPeerCertKeyLength INTEGER,
        orchestratorConnectionsHistorySSLHSPeerEphemeralGroup String
   }       

-- tagpath /orchestrator/connections-history/instance
orchestratorConnectionsHistoryInstance OBJECT-TYPE
    SYNTAX      Unsigned32
    MAX-ACCESS  not-accessible
    STATUS      current
    DESCRIPTION "vdaemon instance id"
    ::= { orchestratorConnectionsHistoryEntry 1 }

-- tagpath /orchestrator/connections-history/index
orchestratorConnectionsHistoryIndex OBJECT-TYPE
    SYNTAX      Unsigned32
    MAX-ACCESS  not-accessible
    STATUS      current
    DESCRIPTION "History index"
    ::= { orchestratorConnectionsHistoryEntry 2 }

-- tagpath /orchestrator/connections-history/peer-type
orchestratorConnectionsHistoryPeerType OBJECT-TYPE
    SYNTAX      INTEGER {unknown(0),vedge(1),vhub(2),vsmart(3),vbond(4),vmanage(5),ztp(6),vapigw(7)}
    MAX-ACCESS  read-only
    STATUS      current
    DESCRIPTION "Connection type"
    ::= { orchestratorConnectionsHistoryEntry 3 }

-- tagpath /orchestrator/connections-history/site-id
orchestratorConnectionsHistorySiteId OBJECT-TYPE
    SYNTAX      Unsigned32
    MAX-ACCESS  read-only
    STATUS      current
    DESCRIPTION "Site ID"
    ::= { orchestratorConnectionsHistoryEntry 4 }

-- tagpath /orchestrator/connections-history/domain-id
orchestratorConnectionsHistoryDomainId OBJECT-TYPE
    SYNTAX      Unsigned32
    MAX-ACCESS  read-only
    STATUS      current
    DESCRIPTION "Domain ID"
    ::= { orchestratorConnectionsHistoryEntry 5 }

-- tagpath /orchestrator/connections-history/protocol
orchestratorConnectionsHistoryProtocol OBJECT-TYPE
    SYNTAX      INTEGER {dtls(0),tls(1),tls-psk(2)}
    MAX-ACCESS  read-only
    STATUS      current
    DESCRIPTION "Protocol"
    DEFVAL { dtls }
    ::= { orchestratorConnectionsHistoryEntry 6 }

-- tagpath /orchestrator/connections-history/private-ip
orchestratorConnectionsHistoryPrivateIp OBJECT-TYPE
    SYNTAX      InetAddressIP
    MAX-ACCESS  read-only
    STATUS      current
    DESCRIPTION "Private IP address"
    ::= { orchestratorConnectionsHistoryEntry 7 }

-- tagpath /orchestrator/connections-history/private-port
orchestratorConnectionsHistoryPrivatePort OBJECT-TYPE
    SYNTAX      Unsigned32
    MAX-ACCESS  read-only
    STATUS      current
    DESCRIPTION "Private port number"
    ::= { orchestratorConnectionsHistoryEntry 8 }

-- tagpath /orchestrator/connections-history/public-ip
orchestratorConnectionsHistoryPublicIp OBJECT-TYPE
    SYNTAX      InetAddressIP
    MAX-ACCESS  read-only
    STATUS      current
    DESCRIPTION "Public IP address"
    ::= { orchestratorConnectionsHistoryEntry 9 }

-- tagpath /orchestrator/connections-history/public-port
orchestratorConnectionsHistoryPublicPort OBJECT-TYPE
    SYNTAX      Unsigned32
    MAX-ACCESS  read-only
    STATUS      current
    DESCRIPTION "Public port number"
    ::= { orchestratorConnectionsHistoryEntry 10 }

-- tagpath /orchestrator/connections-history/system-ip
orchestratorConnectionsHistorySystemIp OBJECT-TYPE
    SYNTAX      InetAddressIP
    MAX-ACCESS  read-only
    STATUS      current
    DESCRIPTION "System IP address"
    ::= { orchestratorConnectionsHistoryEntry 11 }

-- tagpath /orchestrator/connections-history/local-color
orchestratorConnectionsHistoryLocalColor OBJECT-TYPE
    SYNTAX      INTEGER {default(1),mpls(2),metro-ethernet(3),biz-internet(4),public-internet(5),lte(6),threeG(7),red(8),green(9),blue(10),gold(11),silver(12),bronze(13),custom1(14),custom2(15),custom3(16),private1(17),private2(18),private3(19),private4(20),private5(21),private6(22)}
    MAX-ACCESS  read-only
    STATUS      current
    DESCRIPTION "Local color"
    ::= { orchestratorConnectionsHistoryEntry 12 }

-- tagpath /orchestrator/connections-history/remote-color
orchestratorConnectionsHistoryRemoteColor OBJECT-TYPE
    SYNTAX      INTEGER {default(1),mpls(2),metro-ethernet(3),biz-internet(4),public-internet(5),lte(6),threeG(7),red(8),green(9),blue(10),gold(11),silver(12),bronze(13),custom1(14),custom2(15),custom3(16),private1(17),private2(18),private3(19),private4(20),private5(21),private6(22)}
    MAX-ACCESS  read-only
    STATUS      current
    DESCRIPTION "Remote color"
    ::= { orchestratorConnectionsHistoryEntry 13 }

-- tagpath /orchestrator/connections-history/state
orchestratorConnectionsHistoryState OBJECT-TYPE
    SYNTAX      SessionState
    MAX-ACCESS  read-only
    STATUS      current
    DESCRIPTION "State"
    ::= { orchestratorConnectionsHistoryEntry 14 }

-- tagpath /orchestrator/connections-history/local_enum
orchestratorConnectionsHistoryLocalEnum OBJECT-TYPE
    SYNTAX      ConnFlagEnum
    MAX-ACCESS  read-only
    STATUS      current
    DESCRIPTION "Local error reason"
    ::= { orchestratorConnectionsHistoryEntry 15 }

-- tagpath /orchestrator/connections-history/remote_enum
orchestratorConnectionsHistoryRemoteEnum OBJECT-TYPE
    SYNTAX      ConnFlagEnum
    MAX-ACCESS  read-only
    STATUS      current
    DESCRIPTION "Remote error reason"
    ::= { orchestratorConnectionsHistoryEntry 16 }

-- tagpath /orchestrator/connections-history/local-state-info
orchestratorConnectionsHistoryLocalStateInfo OBJECT-TYPE
    SYNTAX      String
    MAX-ACCESS  read-only
    STATUS      current
    DESCRIPTION "Local state information"
    ::= { orchestratorConnectionsHistoryEntry 17 }

-- tagpath /orchestrator/connections-history/remote-state-info
orchestratorConnectionsHistoryRemoteStateInfo OBJECT-TYPE
    SYNTAX      String
    MAX-ACCESS  read-only
    STATUS      current
    DESCRIPTION "Remote state information"
    ::= { orchestratorConnectionsHistoryEntry 18 }

-- tagpath /orchestrator/connections-history/local-private-ip
orchestratorConnectionsHistoryLocalPrivateIp OBJECT-TYPE
    SYNTAX      InetAddressIP
    MAX-ACCESS  read-only
    STATUS      current
    DESCRIPTION "Private IP address"
    ::= { orchestratorConnectionsHistoryEntry 19 }

-- tagpath /orchestrator/connections-history/local-private-port
orchestratorConnectionsHistoryLocalPrivatePort OBJECT-TYPE
    SYNTAX      Unsigned32
    MAX-ACCESS  read-only
    STATUS      current
    DESCRIPTION "Private port"
    ::= { orchestratorConnectionsHistoryEntry 20 }

-- tagpath /orchestrator/connections-history/downtime
orchestratorConnectionsHistoryDowntime OBJECT-TYPE
    SYNTAX      String
    MAX-ACCESS  read-only
    STATUS      current
    DESCRIPTION "Downtime"
    ::= { orchestratorConnectionsHistoryEntry 21 }

-- tagpath /orchestrator/connections-history/tx_hello
orchestratorConnectionsHistoryTxHello OBJECT-TYPE
    SYNTAX      Unsigned32
    MAX-ACCESS  read-only
    STATUS      current
    DESCRIPTION "Tx hello"
    ::= { orchestratorConnectionsHistoryEntry 22 }

-- tagpath /orchestrator/connections-history/tx_connects
orchestratorConnectionsHistoryTxConnects OBJECT-TYPE
    SYNTAX      Unsigned32
    MAX-ACCESS  read-only
    STATUS      current
    DESCRIPTION "Tx connects"
    ::= { orchestratorConnectionsHistoryEntry 23 }

-- tagpath /orchestrator/connections-history/tx_registers
orchestratorConnectionsHistoryTxRegisters OBJECT-TYPE
    SYNTAX      Unsigned32
    MAX-ACCESS  read-only
    STATUS      current
    DESCRIPTION "Tx registers"
    ::= { orchestratorConnectionsHistoryEntry 24 }

-- tagpath /orchestrator/connections-history/tx_register_replies
orchestratorConnectionsHistoryTxRegisterReplies OBJECT-TYPE
    SYNTAX      Unsigned32
    MAX-ACCESS  read-only
    STATUS      current
    DESCRIPTION "Tx register replies"
    ::= { orchestratorConnectionsHistoryEntry 25 }

-- tagpath /orchestrator/connections-history/tx_challenge
orchestratorConnectionsHistoryTxChallenge OBJECT-TYPE
    SYNTAX      Unsigned32
    MAX-ACCESS  read-only
    STATUS      current
    DESCRIPTION "Tx challenge"
    ::= { orchestratorConnectionsHistoryEntry 26 }

-- tagpath /orchestrator/connections-history/tx_challenge_resp
orchestratorConnectionsHistoryTxChallengeResp OBJECT-TYPE
    SYNTAX      Unsigned32
    MAX-ACCESS  read-only
    STATUS      current
    DESCRIPTION "Tx challenge response"
    ::= { orchestratorConnectionsHistoryEntry 27 }

-- tagpath /orchestrator/connections-history/tx_challenge_ack
orchestratorConnectionsHistoryTxChallengeAck OBJECT-TYPE
    SYNTAX      Unsigned32
    MAX-ACCESS  read-only
    STATUS      current
    DESCRIPTION "Tx challenge ack"
    ::= { orchestratorConnectionsHistoryEntry 28 }

-- tagpath /orchestrator/connections-history/tx_teardown
orchestratorConnectionsHistoryTxTeardown OBJECT-TYPE
    SYNTAX      Unsigned32
    MAX-ACCESS  read-only
    STATUS      current
    DESCRIPTION "Tx teardown"
    ::= { orchestratorConnectionsHistoryEntry 29 }

-- tagpath /orchestrator/connections-history/tx_teardown_all
orchestratorConnectionsHistoryTxTeardownAll OBJECT-TYPE
    SYNTAX      Unsigned32
    MAX-ACCESS  read-only
    STATUS      current
    DESCRIPTION "Tx teardown all connections"
    ::= { orchestratorConnectionsHistoryEntry 30 }

-- tagpath /orchestrator/connections-history/tx_vm_to_peer
orchestratorConnectionsHistoryTxVmToPeer OBJECT-TYPE
    SYNTAX      Unsigned32
    MAX-ACCESS  read-only
    STATUS      current
    DESCRIPTION "Tx vManage to peer"
    ::= { orchestratorConnectionsHistoryEntry 31 }

-- tagpath /orchestrator/connections-history/tx_register_to_vm
orchestratorConnectionsHistoryTxRegisterToVm OBJECT-TYPE
    SYNTAX      Unsigned32
    MAX-ACCESS  read-only
    STATUS      current
    DESCRIPTION "Tx register to vManage"
    ::= { orchestratorConnectionsHistoryEntry 32 }

-- tagpath /orchestrator/connections-history/rx_hello
orchestratorConnectionsHistoryRxHello OBJECT-TYPE
    SYNTAX      Unsigned32
    MAX-ACCESS  read-only
    STATUS      current
    DESCRIPTION "Rx hello"
    ::= { orchestratorConnectionsHistoryEntry 33 }

-- tagpath /orchestrator/connections-history/rx_connects
orchestratorConnectionsHistoryRxConnects OBJECT-TYPE
    SYNTAX      Unsigned32
    MAX-ACCESS  read-only
    STATUS      current
    DESCRIPTION "Rx connects"
    ::= { orchestratorConnectionsHistoryEntry 34 }

-- tagpath /orchestrator/connections-history/rx_registers
orchestratorConnectionsHistoryRxRegisters OBJECT-TYPE
    SYNTAX      Unsigned32
    MAX-ACCESS  read-only
    STATUS      current
    DESCRIPTION "Rx registers"
    ::= { orchestratorConnectionsHistoryEntry 35 }

-- tagpath /orchestrator/connections-history/rx_register_replies
orchestratorConnectionsHistoryRxRegisterReplies OBJECT-TYPE
    SYNTAX      Unsigned32
    MAX-ACCESS  read-only
    STATUS      current
    DESCRIPTION "Rx register replies"
    ::= { orchestratorConnectionsHistoryEntry 36 }

-- tagpath /orchestrator/connections-history/rx_challenge
orchestratorConnectionsHistoryRxChallenge OBJECT-TYPE
    SYNTAX      Unsigned32
    MAX-ACCESS  read-only
    STATUS      current
    DESCRIPTION "Rx challenge"
    ::= { orchestratorConnectionsHistoryEntry 37 }

-- tagpath /orchestrator/connections-history/rx_challenge_resp
orchestratorConnectionsHistoryRxChallengeResp OBJECT-TYPE
    SYNTAX      Unsigned32
    MAX-ACCESS  read-only
    STATUS      current
    DESCRIPTION "Rx challenge response"
    ::= { orchestratorConnectionsHistoryEntry 38 }

-- tagpath /orchestrator/connections-history/rx_challenge_ack
orchestratorConnectionsHistoryRxChallengeAck OBJECT-TYPE
    SYNTAX      Unsigned32
    MAX-ACCESS  read-only
    STATUS      current
    DESCRIPTION "Rx challenge ack"
    ::= { orchestratorConnectionsHistoryEntry 39 }

-- tagpath /orchestrator/connections-history/rx_teardown
orchestratorConnectionsHistoryRxTeardown OBJECT-TYPE
    SYNTAX      Unsigned32
    MAX-ACCESS  read-only
    STATUS      current
    DESCRIPTION "Rx teardown"
    ::= { orchestratorConnectionsHistoryEntry 40 }

-- tagpath /orchestrator/connections-history/rx_vm_to_peer
orchestratorConnectionsHistoryRxVmToPeer OBJECT-TYPE
    SYNTAX      Unsigned32
    MAX-ACCESS  read-only
    STATUS      current
    DESCRIPTION "Rx vManage to peer"
    ::= { orchestratorConnectionsHistoryEntry 41 }

-- tagpath /orchestrator/connections-history/rx_register_to_vm
orchestratorConnectionsHistoryRxRegisterToVm OBJECT-TYPE
    SYNTAX      Unsigned32
    MAX-ACCESS  read-only
    STATUS      current
    DESCRIPTION "Rx register to vManage"
    ::= { orchestratorConnectionsHistoryEntry 42 }

-- tagpath /orchestrator/connections-history/rep-count
orchestratorConnectionsHistoryRepCount OBJECT-TYPE
    SYNTAX      Unsigned32
    MAX-ACCESS  read-only
    STATUS      current
    DESCRIPTION "Repeat count"
    ::= { orchestratorConnectionsHistoryEntry 43 }

-- tagpath /orchestrator/connections-history/prev-downtime
orchestratorConnectionsHistoryPrevDowntime OBJECT-TYPE
    SYNTAX      String
    MAX-ACCESS  read-only
    STATUS      current
    DESCRIPTION "Previous downtime"
    ::= { orchestratorConnectionsHistoryEntry 44 }

-- tagpath /orchestrator/connections-history/h-orgname
orchestratorConnectionsHistoryHOrgname OBJECT-TYPE
    SYNTAX      String (SIZE (1 .. 128))
    MAX-ACCESS  read-only
    STATUS      current
    DESCRIPTION "Organization Name"
    ::= { orchestratorConnectionsHistoryEntry 45 }

-- tagpath /orchestrator/connections-history/h-sporgname
orchestratorConnectionsHistoryHSporgname OBJECT-TYPE
    SYNTAX      String (SIZE (1 .. 128))
    MAX-ACCESS  read-only
    STATUS      current
    DESCRIPTION "SP Organization Name"
    ::= { orchestratorConnectionsHistoryEntry 46 }

-- tagpath /orchestrator/connections-history/uuid
orchestratorConnectionsHistoryUuid OBJECT-TYPE
    SYNTAX      String
    MAX-ACCESS  read-only
    STATUS      current
    DESCRIPTION "Peer's unique device identifier"
    ::= { orchestratorConnectionsHistoryEntry 47 }

-- tagpath /orchestrator/connections-history/tx_create_cert
orchestratorConnectionsHistoryTxCreateCert OBJECT-TYPE
    SYNTAX      Unsigned32
    MAX-ACCESS  read-only
    STATUS      current
    DESCRIPTION "Tx create certificate to vManage"
    ::= { orchestratorConnectionsHistoryEntry 48 }

-- tagpath /orchestrator/connections-history/rx_create_cert
orchestratorConnectionsHistoryRxCreateCert OBJECT-TYPE
    SYNTAX      Unsigned32
    MAX-ACCESS  read-only
    STATUS      current
    DESCRIPTION "Rx create certificate from vBond"
    ::= { orchestratorConnectionsHistoryEntry 49 }

-- tagpath /orchestrator/connections-history/tx_create_cert_reply
orchestratorConnectionsHistoryTxCreateCertReply OBJECT-TYPE
    SYNTAX      Unsigned32
    MAX-ACCESS  read-only
    STATUS      current
    DESCRIPTION "Tx create certificate reply to vBond"
    ::= { orchestratorConnectionsHistoryEntry 50 }

-- tagpath /orchestrator/connections-history/rx_create_cert_reply
orchestratorConnectionsHistoryRxCreateCertReply OBJECT-TYPE
    SYNTAX      Unsigned32
    MAX-ACCESS  read-only
    STATUS      current
    DESCRIPTION "Rx create certificate reply from vManage"
    ::= { orchestratorConnectionsHistoryEntry 51 }

-- tagpath /orchestrator/connections-history/protocol-version
orchestratorConnectionsHistoryProtocolVersion OBJECT-TYPE
    SYNTAX      INTEGER {unknown(0),sslv3(1),tls1(2),tls11(3),tls12(4),tls13(5),dtls1(6),dtls12(7)}
    MAX-ACCESS  read-only
    STATUS      current
    DESCRIPTION "Protocol Version"
    DEFVAL { unknown }
    ::= { orchestratorConnectionsHistoryEntry 52 }

-- tagpath /orchestrator/connections-history/cipher-name
orchestratorConnectionsHistoryCipherName OBJECT-TYPE
    SYNTAX      String
    MAX-ACCESS  read-only
    STATUS      current
    DESCRIPTION "Cipher Name"
    ::= { orchestratorConnectionsHistoryEntry 53 }

-- tagpath /orchestrator/connections-history/vd_handshake_local_bidcert_serial
orchestratorConnectionsHistoryvDaemonHSLocalBidcertSerial OBJECT-TYPE
    SYNTAX     String
    MAX-ACCESS  read-only
    STATUS      current
    DESCRIPTION "vDaemon Handshake Local Board-ID Certificate Serial"
    ::= { orchestratorConnectionsHistoryEntry 54 }

-- tagpath /orchestrator/connections-history/vd_handshake_local_bidcert_issuer
orchestratorConnectionsHistoryvDaemonHSLocalBidcertIssuer OBJECT-TYPE
    SYNTAX     String
    MAX-ACCESS  read-only
    STATUS      current
    DESCRIPTION "vDaemon Handshake Local Board-ID Certificate Issuer"
    ::= { orchestratorConnectionsHistoryEntry 55 }

-- tagpath /orchestrator/connections-history/vd_handshake_local_bidcert_subject
orchestratorConnectionsHistoryvDaemonHSLocalBidcertSubject OBJECT-TYPE
    SYNTAX     String
    MAX-ACCESS  read-only
    STATUS      current
    DESCRIPTION "vDaemon Handshake Local Board-ID Certificate Subject"
    ::= { orchestratorConnectionsHistoryEntry 56 }

-- tagpath /orchestrator/connections-history/vd_handshake_local_bidcert_key_type
orchestratorConnectionsHistoryvDaemonHSLocalBidcertKeyType OBJECT-TYPE
    SYNTAX     String
    MAX-ACCESS  read-only
    STATUS      current
    DESCRIPTION "vDaemon Handshake Local Board-ID Certificate Key Type"
    ::= { orchestratorConnectionsHistoryEntry 57 }

-- tagpath /orchestrator/connections-history/vd_handshake_local_bidcert_key_length
orchestratorConnectionsHistoryvDaemonHSLocalBidcertKeyLength OBJECT-TYPE
    SYNTAX     INTEGER
    MAX-ACCESS  read-only
    STATUS      current
    DESCRIPTION "vDaemon Handshake Local Board-ID Certificate Key Length"
    ::= { orchestratorConnectionsHistoryEntry 58 }

-- tagpath /orchestrator/connections-history/vd_handshake_local_cert_serial
orchestratorConnectionsHistoryvDaemonHSLocalCertSerial OBJECT-TYPE
    SYNTAX     String
    MAX-ACCESS  read-only
    STATUS      current
    DESCRIPTION "vDaemon Handshake Local Certificate Serial"
    ::= { orchestratorConnectionsHistoryEntry 59 }

-- tagpath /orchestrator/connections-history/vd_handshake_local_cert_issuer
orchestratorConnectionsHistoryvDaemonHSLocalCertIssuer OBJECT-TYPE
    SYNTAX     String
    MAX-ACCESS  read-only
    STATUS      current
    DESCRIPTION "vDaemon Handshake Local Certificate Issuer"
    ::= { orchestratorConnectionsHistoryEntry 60 }

-- tagpath /orchestrator/connections-history/vd_handshake_local_cert_subject
orchestratorConnectionsHistoryvDaemonHSLocalCertSubject OBJECT-TYPE
    SYNTAX     String
    MAX-ACCESS  read-only
    STATUS      current
    DESCRIPTION "vDaemon Handshake Local Certificate Subject"
    ::= { orchestratorConnectionsHistoryEntry 61 }

-- tagpath /orchestrator/connections-history/vd_handshake_local_cert_key_type
orchestratorConnectionsHistoryvDaemonHSLocalCertKeyType OBJECT-TYPE
    SYNTAX     String
    MAX-ACCESS  read-only
    STATUS      current
    DESCRIPTION "vDaemon Handshake Local Certificate Key Type"
    ::= { orchestratorConnectionsHistoryEntry 62 }

-- tagpath /orchestrator/connections-history/vd_handshake_local_cert_key_length
orchestratorConnectionsHistoryvDaemonHSLocalCertKeyLength OBJECT-TYPE
    SYNTAX     INTEGER
    MAX-ACCESS  read-only
    STATUS      current
    DESCRIPTION "vDaemon Handshake Local Certificate Key Length"
    ::= { orchestratorConnectionsHistoryEntry 63 }

-- tagpath /orchestrator/connections-history/vd_handshake_peer_bidcert_serial
orchestratorConnectionsHistoryvDaemonHSPeerBidcertSerial OBJECT-TYPE
    SYNTAX     String
    MAX-ACCESS  read-only
    STATUS      current
    DESCRIPTION "vDaemon Handshake Peer Board-ID Certificate Serial"
    ::= { orchestratorConnectionsHistoryEntry 64 }

-- tagpath /orchestrator/connections-history/vd_handshake_peer_bidcert_issuer
orchestratorConnectionsHistoryvDaemonHSPeerBidcertIssuer OBJECT-TYPE
    SYNTAX     String
    MAX-ACCESS  read-only
    STATUS      current
    DESCRIPTION "vDaemon Handshake Peer Board-ID Certificate Issuer"
    ::= { orchestratorConnectionsHistoryEntry 65 }

-- tagpath /orchestrator/connections-history/vd_handshake_peer_bidcert_subject
orchestratorConnectionsHistoryvDaemonHSPeerBidcertSubject OBJECT-TYPE
    SYNTAX     String
    MAX-ACCESS  read-only
    STATUS      current
    DESCRIPTION "vDaemon Handshake Peer Board-ID Certificate Subject"
    ::= { orchestratorConnectionsHistoryEntry 66 }

-- tagpath /orchestrator/connections-history/vd_handshake_peer_bidcert_key_type
orchestratorConnectionsHistoryvDaemonHSPeerBidcertKeyType OBJECT-TYPE
    SYNTAX     String
    MAX-ACCESS  read-only
    STATUS      current
    DESCRIPTION "vDaemon Handshake Peer Board-ID Certificate Key Type"
    ::= { orchestratorConnectionsHistoryEntry 67 }

-- tagpath /orchestrator/connections-history/vd_handshake_peer_bidcert_key_length
orchestratorConnectionsHistoryvDaemonHSPeerBidcertKeyLength OBJECT-TYPE
    SYNTAX     INTEGER
    MAX-ACCESS  read-only
    STATUS      current
    DESCRIPTION "vDaemon Handshake Peer Board-ID Certificate Key Length"
    ::= { orchestratorConnectionsHistoryEntry 68 }

-- tagpath /orchestrator/connections-history/vd_handshake_peer_cert_serial
orchestratorConnectionsHistoryvDaemonHSPeerCertSerial OBJECT-TYPE
    SYNTAX     String
    MAX-ACCESS  read-only
    STATUS      current
    DESCRIPTION "vDaemon Handshake Peer Certificate Serial"
    ::= { orchestratorConnectionsHistoryEntry 69 }

-- tagpath /orchestrator/connections-history/vd_handshake_peer_cert_issuer
orchestratorConnectionsHistoryvDaemonHSPeerCertIssuer OBJECT-TYPE
    SYNTAX     String
    MAX-ACCESS  read-only
    STATUS      current
    DESCRIPTION "vDaemon Handshake Peer Certificate Issuer"
    ::= { orchestratorConnectionsHistoryEntry 70 }

-- tagpath /orchestrator/connections-history/vd_handshake_peer_cert_subject
orchestratorConnectionsHistoryvDaemonHSPeerCertSubject OBJECT-TYPE
    SYNTAX     String
    MAX-ACCESS  read-only
    STATUS      current
    DESCRIPTION "vDaemon Handshake Peer Certificate Subject"
    ::= { orchestratorConnectionsHistoryEntry 71 }

-- tagpath /orchestrator/connections-history/vd_handshake_peer_cert_key_type
orchestratorConnectionsHistoryvDaemonHSPeerCertKeyType OBJECT-TYPE
    SYNTAX     String
    MAX-ACCESS  read-only
    STATUS      current
    DESCRIPTION "vDaemon Handshake Peer Certificate Key Type"
    ::= { orchestratorConnectionsHistoryEntry 72 }

-- tagpath /orchestrator/connections-history/vd_handshake_peer_cert_key_length
orchestratorConnectionsHistoryvDaemonHSPeerCertKeyLength OBJECT-TYPE
    SYNTAX     INTEGER
    MAX-ACCESS  read-only
    STATUS      current
    DESCRIPTION "vDaemon Handshake Peer Certificate Key Length"
    ::= { orchestratorConnectionsHistoryEntry 73 }

-- tagpath /orchestrator/connections-history/ssl_handshake_local_cert_serial
orchestratorConnectionsHistorySSLHSLocalCertSerial OBJECT-TYPE
    SYNTAX     String
    MAX-ACCESS  read-only
    STATUS      current
    DESCRIPTION "SSL Handshake Local Certificate Serial"
    ::= { orchestratorConnectionsHistoryEntry 74 }

-- tagpath /orchestrator/connections-history/ssl_handshake_local_cert_issuer
orchestratorConnectionsHistorySSLHSLocalCertIssuer OBJECT-TYPE
    SYNTAX     String
    MAX-ACCESS  read-only
    STATUS      current
    DESCRIPTION "SSL Handshake Local Certificate Issuer"
    ::= { orchestratorConnectionsHistoryEntry 75 }

-- tagpath /orchestrator/connections-history/ssl_handshake_local_cert_subject
orchestratorConnectionsHistorySSLHSLocalCertSubject OBJECT-TYPE
    SYNTAX     String
    MAX-ACCESS  read-only
    STATUS      current
    DESCRIPTION "SSL Handshake Local Certificate Subject"
    ::= { orchestratorConnectionsHistoryEntry 76 }

-- tagpath /orchestrator/connections-history/ssl_handshake_local_cert_key_type
orchestratorConnectionsHistorySSLHSLocalCertKeyType OBJECT-TYPE
    SYNTAX     String
    MAX-ACCESS  read-only
    STATUS      current
    DESCRIPTION "SSL Handshake Local Certificate Key Type"
    ::= { orchestratorConnectionsHistoryEntry 77 }

-- tagpath /orchestrator/connections-history/ssl_handshake_local_cert_key_length
orchestratorConnectionsHistorySSLHSLocalCertKeyLength OBJECT-TYPE
    SYNTAX     INTEGER
    MAX-ACCESS  read-only
    STATUS      current
    DESCRIPTION "SSL Handshake Local Certificate Key Length"
    ::= { orchestratorConnectionsHistoryEntry 78 }

-- tagpath /orchestrator/connections-history/ssl_handshake_peer_cert_serial
orchestratorConnectionsHistorySSLHSPeerCertSerial OBJECT-TYPE
    SYNTAX     String
    MAX-ACCESS  read-only
    STATUS      current
    DESCRIPTION "SSL Handshake Peer Certificate Serial"
    ::= { orchestratorConnectionsHistoryEntry 79 }

-- tagpath /orchestrator/connections-history/ssl_handshake_peer_cert_issuer
orchestratorConnectionsHistorySSLHSPeerCertIssuer OBJECT-TYPE
    SYNTAX     String
    MAX-ACCESS  read-only
    STATUS      current
    DESCRIPTION "SSL Handshake Peer Certificate Issuer"
    ::= { orchestratorConnectionsHistoryEntry 80 }

-- tagpath /orchestrator/connections-history/ssl_handshake_peer_cert_subject
orchestratorConnectionsHistorySSLHSPeerCertSubject OBJECT-TYPE
    SYNTAX     String
    MAX-ACCESS  read-only
    STATUS      current
    DESCRIPTION "SSL Handshake Peer Certificate Subject"
    ::= { orchestratorConnectionsHistoryEntry 81 }

-- tagpath /orchestrator/connections-history/ssl_handshake_peer_cert_key_type
orchestratorConnectionsHistorySSLHSPeerCertKeyType OBJECT-TYPE
    SYNTAX     String
    MAX-ACCESS  read-only
    STATUS      current
    DESCRIPTION "SSL Handshake Peer Key Type"
    ::= { orchestratorConnectionsHistoryEntry 82 }

-- tagpath /orchestrator/connections-history/ssl_handshake_peer_cert_key_length
orchestratorConnectionsHistorySSLHSPeerCertKeyLength OBJECT-TYPE
    SYNTAX     INTEGER
    MAX-ACCESS  read-only
    STATUS      current
    DESCRIPTION "SSL Handshake Peer Certificate Key Length"
    ::= { orchestratorConnectionsHistoryEntry 83 }

-- tagpath /orchestrator/connections-history/ssl_handshake_ephemeral_group
orchestratorConnectionsHistorySSLHSPeerEphemeralGroup OBJECT-TYPE  
    SYNTAX     String                                
    MAX-ACCESS  read-only                            
    STATUS      current                              
    DESCRIPTION "SSL Handshake Ephemeral Group"        
    ::= { orchestratorConnectionsHistoryEntry 84 }

-- tagpath /orchestrator/local-properties/wan-interface-list
orchestratorLocalPropertiesWanInterfaceListTable OBJECT-TYPE
    SYNTAX      SEQUENCE OF OrchestratorLocalPropertiesWanInterfaceListEntry
    MAX-ACCESS  not-accessible
    STATUS      current
    DESCRIPTION "List of WAN interfaces"
    ::= { orchestratorLocalProperties 12 }

-- tagpath /orchestrator/local-properties/wan-interface-list
orchestratorLocalPropertiesWanInterfaceListEntry OBJECT-TYPE
    SYNTAX      OrchestratorLocalPropertiesWanInterfaceListEntry
    MAX-ACCESS  not-accessible
    STATUS      current
    DESCRIPTION ""
    INDEX { orchestratorLocalPropertiesWanInterfaceListInstance, orchestratorLocalPropertiesWanInterfaceListIndex }
        ::= { orchestratorLocalPropertiesWanInterfaceListTable 1 }

OrchestratorLocalPropertiesWanInterfaceListEntry ::=
    SEQUENCE {
        orchestratorLocalPropertiesWanInterfaceListIndex Unsigned32,
        orchestratorLocalPropertiesWanInterfaceListIp InetAddressIP,
        orchestratorLocalPropertiesWanInterfaceListPort Unsigned32,
        orchestratorLocalPropertiesWanInterfaceListNumVsmarts Unsigned32,
        orchestratorLocalPropertiesWanInterfaceListNumVmanages Unsigned32,
        orchestratorLocalPropertiesWanInterfaceListAdminState StateEnum,
        orchestratorLocalPropertiesWanInterfaceListOperationState StateEnum,
        orchestratorLocalPropertiesWanInterfaceListLastConnTime String,
        orchestratorLocalPropertiesWanInterfaceListInstance Unsigned32,
        orchestratorLocalPropertiesWanInterfaceListInterfaceAdminState StateEnum,
        orchestratorLocalPropertiesWanInterfaceListInterfaceOperState StateEnum
    }

-- tagpath /orchestrator/local-properties/wan-interface-list/index
orchestratorLocalPropertiesWanInterfaceListIndex OBJECT-TYPE
    SYNTAX      Unsigned32
    MAX-ACCESS  not-accessible
    STATUS      current
    DESCRIPTION "WAN index"
    ::= { orchestratorLocalPropertiesWanInterfaceListEntry 1 }

-- tagpath /orchestrator/local-properties/wan-interface-list/ip
orchestratorLocalPropertiesWanInterfaceListIp OBJECT-TYPE
    SYNTAX      InetAddressIP
    MAX-ACCESS  read-only
    STATUS      current
    DESCRIPTION "IP address"
    ::= { orchestratorLocalPropertiesWanInterfaceListEntry 2 }

-- tagpath /orchestrator/local-properties/wan-interface-list/port
orchestratorLocalPropertiesWanInterfaceListPort OBJECT-TYPE
    SYNTAX      Unsigned32
    MAX-ACCESS  read-only
    STATUS      current
    DESCRIPTION "Port"
    ::= { orchestratorLocalPropertiesWanInterfaceListEntry 3 }

-- tagpath /orchestrator/local-properties/wan-interface-list/num-vsmarts
orchestratorLocalPropertiesWanInterfaceListNumVsmarts OBJECT-TYPE
    SYNTAX      Unsigned32
    MAX-ACCESS  read-only
    STATUS      current
    DESCRIPTION "Number of vSmarts"
    ::= { orchestratorLocalPropertiesWanInterfaceListEntry 4 }

-- tagpath /orchestrator/local-properties/wan-interface-list/num-vmanages
orchestratorLocalPropertiesWanInterfaceListNumVmanages OBJECT-TYPE
    SYNTAX      Unsigned32
    MAX-ACCESS  read-only
    STATUS      current
    DESCRIPTION "Number of vManages"
    ::= { orchestratorLocalPropertiesWanInterfaceListEntry 5 }

-- tagpath /orchestrator/local-properties/wan-interface-list/admin-state
orchestratorLocalPropertiesWanInterfaceListAdminState OBJECT-TYPE
    SYNTAX      StateEnum
    MAX-ACCESS  read-only
    STATUS      current
    DESCRIPTION "Administrative state"
    ::= { orchestratorLocalPropertiesWanInterfaceListEntry 6 }

-- tagpath /orchestrator/local-properties/wan-interface-list/operation-state
orchestratorLocalPropertiesWanInterfaceListOperationState OBJECT-TYPE
    SYNTAX      StateEnum
    MAX-ACCESS  read-only
    STATUS      current
    DESCRIPTION "Operational state"
    ::= { orchestratorLocalPropertiesWanInterfaceListEntry 7 }

-- tagpath /orchestrator/local-properties/wan-interface-list/last-conn-time
orchestratorLocalPropertiesWanInterfaceListLastConnTime OBJECT-TYPE
    SYNTAX      String
    MAX-ACCESS  read-only
    STATUS      current
    DESCRIPTION "Time since last connection"
    ::= { orchestratorLocalPropertiesWanInterfaceListEntry 8 }

-- tagpath /orchestrator/local-properties/wan-interface-list/instance
orchestratorLocalPropertiesWanInterfaceListInstance OBJECT-TYPE
    SYNTAX      Unsigned32
    MAX-ACCESS  not-accessible
    STATUS      current
    DESCRIPTION "vdaemon instance ID"
    ::= { orchestratorLocalPropertiesWanInterfaceListEntry 9 }

-- tagpath /orchestrator/local-properties/wan-interface-list/interface-admin-state
orchestratorLocalPropertiesWanInterfaceListInterfaceAdminState OBJECT-TYPE
    SYNTAX      StateEnum
    MAX-ACCESS  read-only
    STATUS      current
    DESCRIPTION "Interface administrative state"
    ::= { orchestratorLocalPropertiesWanInterfaceListEntry 10 }

-- tagpath /orchestrator/local-properties/wan-interface-list/interface-oper-state
orchestratorLocalPropertiesWanInterfaceListInterfaceOperState OBJECT-TYPE
    SYNTAX      StateEnum
    MAX-ACCESS  read-only
    STATUS      current
    DESCRIPTION "Interface operational state"
    ::= { orchestratorLocalPropertiesWanInterfaceListEntry 11 }

-- tagpath /orchestrator/valid-vsmarts
orchestratorValidVsmartsTable OBJECT-TYPE
    SYNTAX      SEQUENCE OF OrchestratorValidVsmartsEntry
    MAX-ACCESS  not-accessible
    STATUS      current
    DESCRIPTION "Display valid vSmarts"
    ::= { orchestrator 5 }

-- tagpath /orchestrator/valid-vsmarts
orchestratorValidVsmartsEntry OBJECT-TYPE
    SYNTAX      OrchestratorValidVsmartsEntry
    MAX-ACCESS  not-accessible
    STATUS      current
    DESCRIPTION ""
    INDEX { orchestratorValidVsmartsSerialNumber, orchestratorValidVsmartsOrg }
        ::= { orchestratorValidVsmartsTable 1 }

OrchestratorValidVsmartsEntry ::=
    SEQUENCE {
        orchestratorValidVsmartsSerialNumber String,
        orchestratorValidVsmartsOrg          String,
        orchestratorValidVsmartsDeviceState  INTEGER
    }

-- tagpath /orchestrator/valid-vsmarts/serial-number
orchestratorValidVsmartsSerialNumber OBJECT-TYPE
    SYNTAX      String (SIZE (1 .. 40))
    MAX-ACCESS  read-only
    STATUS      current
    DESCRIPTION "Serial number of the device"
    ::= { orchestratorValidVsmartsEntry 1 }

-- tagpath /orchestrator/valid-vsmarts/org
orchestratorValidVsmartsOrg OBJECT-TYPE
    SYNTAX      String (SIZE (1 .. 128))
    MAX-ACCESS  read-only
    STATUS      current
    DESCRIPTION "Organization that the controller belongs to"
    ::= { orchestratorValidVsmartsEntry 2 }

-- tagpath /orchestrator/valid-vsmarts/device-state
orchestratorValidVsmartsDeviceState OBJECT-TYPE
    SYNTAX      INTEGER {invalid(0),valid(1),config-init(2)}
    MAX-ACCESS  read-only
    STATUS      current
    DESCRIPTION "The state that the controller currently has"
    ::= { orchestratorValidVsmartsEntry 3 }

-- tagpath /orchestrator/valid-vedges
orchestratorValidVedgesTable OBJECT-TYPE
    SYNTAX      SEQUENCE OF OrchestratorValidVedgesEntry
    MAX-ACCESS  not-accessible
    STATUS      current
    DESCRIPTION "Display valid vedges"
    ::= { orchestrator 6 }

-- tagpath /orchestrator/valid-vedges
orchestratorValidVedgesEntry OBJECT-TYPE
    SYNTAX      OrchestratorValidVedgesEntry
    MAX-ACCESS  not-accessible
    STATUS      current
    DESCRIPTION ""
    INDEX { IMPLIED orchestratorValidVedgesChassisNumber }
        ::= { orchestratorValidVedgesTable 1 }

OrchestratorValidVedgesEntry ::=
    SEQUENCE {
        orchestratorValidVedgesChassisNumber String,
        orchestratorValidVedgesSerialNumber String,
        orchestratorValidVedgesValidity INTEGER,
        orchestratorValidVedgesOrg String,
        orchestratorValidVedgesInstalledSerialNumber String,
        orchestratorValidVedgesSubjectSerialNumber String
    }

-- tagpath /orchestrator/valid-vedges/chassis-number
orchestratorValidVedgesChassisNumber OBJECT-TYPE
    SYNTAX      String (SIZE (1 .. 40))
    MAX-ACCESS  not-accessible
    STATUS      current
    DESCRIPTION "Chassis number of the device"
    ::= { orchestratorValidVedgesEntry 1 }

-- tagpath /orchestrator/valid-vedges/serial-number
orchestratorValidVedgesSerialNumber OBJECT-TYPE
    SYNTAX      String (SIZE (1 .. 40))
    MAX-ACCESS  read-only
    STATUS      current
    DESCRIPTION "Serial number of the device"
    ::= { orchestratorValidVedgesEntry 2 }

-- tagpath /orchestrator/valid-vedges/validity
orchestratorValidVedgesValidity OBJECT-TYPE
    SYNTAX      INTEGER {valid(1),invalid(2),staging(3)}
    MAX-ACCESS  read-only
    STATUS      current
    DESCRIPTION "Device valid or staging"
    ::= { orchestratorValidVedgesEntry 3 }

-- tagpath /orchestrator/valid-vedges/org
orchestratorValidVedgesOrg OBJECT-TYPE
    SYNTAX      String (SIZE (1 .. 128))
    MAX-ACCESS  read-only
    STATUS      current
    DESCRIPTION "Organization the vedge belongs to"
    ::= { orchestratorValidVedgesEntry 4 }

-- tagpath /orchestrator/valid-vedges/installed-serial-number
orchestratorValidVedgesInstalledSerialNumber OBJECT-TYPE
    SYNTAX      String (SIZE (1 .. 40))
    MAX-ACCESS  read-only
    STATUS      current
    DESCRIPTION "Installed Serial number of the device"
    ::= { orchestratorValidVedgesEntry 5 }

-- tagpath /orchestrator/valid-vedges/subject-serial-number
orchestratorValidVedgesSubjectSerialNumber OBJECT-TYPE
    SYNTAX      String (SIZE (1 .. 12))
    MAX-ACCESS  read-only
    STATUS      current
    DESCRIPTION "Subject Serial number of the device"
    ::= { orchestratorValidVedgesEntry 6 }

-- tagpath /orchestrator/summary
orchestratorSummaryTable OBJECT-TYPE
    SYNTAX      SEQUENCE OF OrchestratorSummaryEntry
    MAX-ACCESS  not-accessible
    STATUS      current
    DESCRIPTION "Display orchestrator summary"
    ::= { orchestrator 7 }

-- tagpath /orchestrator/summary
orchestratorSummaryEntry OBJECT-TYPE
    SYNTAX      OrchestratorSummaryEntry
    MAX-ACCESS  not-accessible
    STATUS      current
    DESCRIPTION ""
    INDEX { orchestratorSummaryInstance }
        ::= { orchestratorSummaryTable 1 }

OrchestratorSummaryEntry ::=
    SEQUENCE {
        orchestratorSummaryInstance Unsigned32,
        orchestratorSummaryVmanageCounts UnsignedShort,
        orchestratorSummaryVsmartCounts UnsignedShort,
        orchestratorSummaryVedgeCounts UnsignedShort,
        orchestratorSummaryProtocol INTEGER,
        orchestratorSummaryListeningIp InetAddressIP,
        orchestratorSummaryListeningPort Unsigned32,
        orchestratorSummaryListeningIpv6 InetAddressIP,
        orchestratorSummaryValidControllerCounts UnsignedShort
    }

-- tagpath /orchestrator/summary/instance
orchestratorSummaryInstance OBJECT-TYPE
    SYNTAX      Unsigned32
    MAX-ACCESS  not-accessible
    STATUS      current
    DESCRIPTION "vdaemon instance id"
    ::= { orchestratorSummaryEntry 1 }

-- tagpath /orchestrator/summary/vmanage_counts
orchestratorSummaryVmanageCounts OBJECT-TYPE
    SYNTAX      UnsignedShort
    MAX-ACCESS  read-only
    STATUS      current
    DESCRIPTION ""
    ::= { orchestratorSummaryEntry 2 }

-- tagpath /orchestrator/summary/vsmart_counts
orchestratorSummaryVsmartCounts OBJECT-TYPE
    SYNTAX      UnsignedShort
    MAX-ACCESS  read-only
    STATUS      current
    DESCRIPTION ""
    ::= { orchestratorSummaryEntry 3 }

-- tagpath /orchestrator/summary/vedge_counts
orchestratorSummaryVedgeCounts OBJECT-TYPE
    SYNTAX      UnsignedShort
    MAX-ACCESS  read-only
    STATUS      current
    DESCRIPTION ""
    ::= { orchestratorSummaryEntry 4 }

-- tagpath /control/summary/protocol
orchestratorSummaryProtocol OBJECT-TYPE
    SYNTAX      INTEGER {dtls(0),tls(1),tls-psk(2)}
    MAX-ACCESS  read-only
    STATUS      current
    DESCRIPTION "Protocol"
    ::= { orchestratorSummaryEntry 5 }

-- tagpath /orchestrator/summary/listening_ip
orchestratorSummaryListeningIp OBJECT-TYPE
    SYNTAX      InetAddressIP
    MAX-ACCESS  not-accessible
    STATUS      current
    DESCRIPTION "Listening IP address"
    ::= { orchestratorSummaryEntry 6 }

-- tagpath /orchestrator/summary/listening_port
orchestratorSummaryListeningPort OBJECT-TYPE
    SYNTAX      Unsigned32
    MAX-ACCESS  not-accessible
    STATUS      current
    DESCRIPTION "Listening port number"
    ::= { orchestratorSummaryEntry 7 }

-- tagpath /orchestrator/summary/listening_ipv6
orchestratorSummaryListeningIpv6 OBJECT-TYPE
    SYNTAX      InetAddressIP
    MAX-ACCESS  not-accessible
    STATUS      current
    DESCRIPTION "Listening IPv6 address"
    ::= { orchestratorSummaryEntry 8 }

-- tagpath /orchestrator/summary/valid_controller_counts
orchestratorSummaryValidControllerCounts OBJECT-TYPE
    SYNTAX      UnsignedShort
    MAX-ACCESS  read-only
    STATUS      current
    DESCRIPTION "Valid Controller Counts"
    ::= { orchestratorSummaryEntry 9 }

-- tagpath /orchestrator/valid-vmanage-id
orchestratorValidVmanageIdTable OBJECT-TYPE
    SYNTAX      SEQUENCE OF OrchestratorValidVmanageIdEntry
    MAX-ACCESS  not-accessible
    STATUS      current
    DESCRIPTION "Display valid vManage CA id"
    ::= { orchestrator 8 }

-- tagpath /orchestrator/valid-vmanage-id
orchestratorValidVmanageIdEntry OBJECT-TYPE
    SYNTAX      OrchestratorValidVmanageIdEntry
    MAX-ACCESS  not-accessible
    STATUS      current
    DESCRIPTION ""
    INDEX { IMPLIED orchestratorValidVManageIdChassisNumbers }
        ::= { orchestratorValidVmanageIdTable 1 }

OrchestratorValidVmanageIdEntry ::=
    SEQUENCE {
        orchestratorValidVManageIdChassisNumbers String
    }

-- tagpath /orchestrator/valid-vmanage-id/chassis-number
orchestratorValidVManageIdChassisNumbers OBJECT-TYPE
    SYNTAX      String (SIZE (1 .. 40))
    MAX-ACCESS  read-only
    STATUS      current
    DESCRIPTION "Chassis number of the device"
    ::= { orchestratorValidVmanageIdEntry 1 }

-- tagpath /orchestrator/reverse-proxy-mapping
orchestratorReverseProxyMappingTable OBJECT-TYPE
    SYNTAX      SEQUENCE OF OrchestratorReverseProxyMapping
    MAX-ACCESS  not-accessible
    STATUS      current
    DESCRIPTION "Display configured reverse proxy mappings"
    ::= { orchestrator 9 }

-- tagpath /orchestrator/reverse-proxy-mapping
orchestratorReverseProxyMapping OBJECT-TYPE
    SYNTAX     OrchestratorReverseProxyMapping 
    MAX-ACCESS  not-accessible
    STATUS      current
    DESCRIPTION ""
    INDEX { orchestratorReverseProxyMappingUuid, 
            orchestratorReverseProxyMappingPrivateIp, orchestratorReverseProxyMappingPrivatePort }
    ::= { orchestratorReverseProxyMappingTable 1 }

OrchestratorReverseProxyMapping ::=
    SEQUENCE {
        orchestratorReverseProxyMappingUuid String,
        orchestratorReverseProxyMappingPrivateIp InetAddressIP,
        orchestratorReverseProxyMappingPrivatePort UnsignedShort,
        orchestratorReverseProxyMappingProxyIp InetAddressIP,
        orchestratorReverseProxyMappingProxyPort UnsignedShort 
    }

-- tagpath /orchestrator/reverse-proxy-mapping/uuid
orchestratorReverseProxyMappingUuid OBJECT-TYPE
    SYNTAX     String 
    MAX-ACCESS  read-only
    STATUS      current
    DESCRIPTION "UUID of vSmart or vManage"
    ::= { orchestratorReverseProxyMapping 1 }

-- tagpath /orchestrator/reverse-proxy-mapping/private-ip
orchestratorReverseProxyMappingPrivateIp OBJECT-TYPE
    SYNTAX     InetAddressIP
    MAX-ACCESS  read-only
    STATUS      current
    DESCRIPTION "Private IP address of vSmart or vManage"
    ::= { orchestratorReverseProxyMapping 2 }

-- tagpath /orchestrator/reverse-proxy-mapping/private-port
orchestratorReverseProxyMappingPrivatePort OBJECT-TYPE
    SYNTAX     UnsignedShort
    MAX-ACCESS  read-only
    STATUS      current
    DESCRIPTION "Private port of vSmart or vManage"
    ::= { orchestratorReverseProxyMapping 3 }

-- tagpath /orchestrator/reverse-proxy-mapping/proxy-ip
orchestratorReverseProxyMappingProxyIp OBJECT-TYPE
    SYNTAX     InetAddressIP 
    MAX-ACCESS  read-only
    STATUS      current
    DESCRIPTION "Proxy IP address mapping this vSmart or vManage"
    ::= { orchestratorReverseProxyMapping 4 }

-- tagpath /orchestrator/reverse-proxy-mapping/proxy-port
orchestratorReverseProxyMappingProxyPort OBJECT-TYPE
    SYNTAX      UnsignedShort
    MAX-ACCESS  read-only
    STATUS      current
    DESCRIPTION "Proxy port mapping this vSmart or vManage"
    ::= { orchestratorReverseProxyMapping 5 }

-- tagpath /orchestrator/unclaimed-vedges
orchestratorUnclaimedVedgesTable OBJECT-TYPE
    SYNTAX      SEQUENCE OF OrchestratorUnclaimedVedgesEntry
    MAX-ACCESS  not-accessible
    STATUS      current
    DESCRIPTION "Display unclaimed vedges"
    ::= { orchestrator 10 }

-- tagpath /orchestrator/unclaimed-vedges
orchestratorUnclaimedVedgesEntry OBJECT-TYPE
    SYNTAX      OrchestratorUnclaimedVedgesEntry
    MAX-ACCESS  not-accessible
    STATUS      current
    DESCRIPTION ""
    INDEX { IMPLIED orchestratorUnclaimedVedgesChassisNumber }
        ::= { orchestratorUnclaimedVedgesTable 1 }

OrchestratorUnclaimedVedgesEntry ::=
    SEQUENCE {
        orchestratorUnclaimedVedgesChassisNumber String,
        orchestratorUnclaimedVedgesSerialNumber String,
        orchestratorUnclaimedVedgesSubjectSerialNumber String,
        orchestratorUnclaimedVedgesOrg String
    }

-- tagpath /orchestrator/unclaimed-vedges/chassis-number
orchestratorUnclaimedVedgesChassisNumber OBJECT-TYPE
    SYNTAX      String (SIZE (1 .. 40))
    MAX-ACCESS  not-accessible
    STATUS      current
    DESCRIPTION "Chassis number of the device"
    ::= { orchestratorUnclaimedVedgesEntry 1 }

-- tagpath /orchestrator/unclaimed-vedges/serial-number
orchestratorUnclaimedVedgesSerialNumber OBJECT-TYPE
    SYNTAX      String (SIZE (1 .. 40))
    MAX-ACCESS  read-only
    STATUS      current
    DESCRIPTION "Serial number of the device"
    ::= { orchestratorUnclaimedVedgesEntry 2 }

-- tagpath /orchestrator/unclaimed-vedges/subject-serial-number
orchestratorUnclaimedVedgesSubjectSerialNumber OBJECT-TYPE
    SYNTAX      String (SIZE (1 .. 12))
    MAX-ACCESS  read-only
    STATUS      current
    DESCRIPTION "Subject Serial number of the device"
    ::= { orchestratorUnclaimedVedgesEntry 3 }

-- tagpath /orchestrator/unclaimed-vedges/org
orchestratorUnclaimedVedgesOrg OBJECT-TYPE
    SYNTAX      String (SIZE (1 .. 128))
    MAX-ACCESS  read-only
    STATUS      current
    DESCRIPTION "Organization name"
    ::= { orchestratorUnclaimedVedgesEntry 4 }

-- tagpath /ztp/entries
ztpEntriesTable OBJECT-TYPE
    SYNTAX      SEQUENCE OF ZtpEntriesEntry
    MAX-ACCESS  not-accessible
    STATUS      current
    DESCRIPTION "Display vEdges in the ZTP database"
    ::= { ztp 1 }

-- tagpath /ztp/entries
ztpEntriesEntry OBJECT-TYPE
    SYNTAX      ZtpEntriesEntry
    MAX-ACCESS  not-accessible
    STATUS      current
    DESCRIPTION ""
    INDEX { ztpEntriesIndex }
        ::= { ztpEntriesTable 1 }

ZtpEntriesEntry ::=
    SEQUENCE {
        ztpEntriesIndex Unsigned32,
        ztpEntriesChassisNumber String,
        ztpEntriesSerialNumber String,
        ztpEntriesValidity String,
        ztpEntriesVbondIp String,
        ztpEntriesVbondPort UnsignedShort,
        ztpEntriesOrganizationName String,
        ztpEntriesRootCertPath String
    }

-- tagpath /ztp/entries/index
ztpEntriesIndex OBJECT-TYPE
    SYNTAX      Unsigned32
    MAX-ACCESS  read-only
    STATUS      current
    DESCRIPTION "Row index"
    ::= { ztpEntriesEntry 1 }

-- tagpath /ztp/entries/chassis-number
ztpEntriesChassisNumber OBJECT-TYPE
    SYNTAX      String (SIZE (1 .. 40))
    MAX-ACCESS  read-only
    STATUS      current
    DESCRIPTION "Chassis number of the device"
    ::= { ztpEntriesEntry 2 }

-- tagpath /ztp/entries/serial-number
ztpEntriesSerialNumber OBJECT-TYPE
    SYNTAX      String (SIZE (1 .. 40))
    MAX-ACCESS  read-only
    STATUS      current
    DESCRIPTION "Serial number of the device"
    ::= { ztpEntriesEntry 3 }

-- tagpath /ztp/entries/validity
ztpEntriesValidity OBJECT-TYPE
    SYNTAX      String (SIZE (1 .. 8))
    MAX-ACCESS  read-only
    STATUS      current
    DESCRIPTION "Device chassis number validity status"
    ::= { ztpEntriesEntry 4 }

-- tagpath /ztp/entries/vbond-ip
ztpEntriesVbondIp OBJECT-TYPE
    SYNTAX      String (SIZE (1 .. 128))
    MAX-ACCESS  read-only
    STATUS      current
    DESCRIPTION "Enterprise vBond public IP address"
    ::= { ztpEntriesEntry 5 }

-- tagpath /ztp/entries/vbond-port
ztpEntriesVbondPort OBJECT-TYPE
    SYNTAX      UnsignedShort
    MAX-ACCESS  read-only
    STATUS      current
    DESCRIPTION "Enterprise vBond public port number"
    ::= { ztpEntriesEntry 6 }

-- tagpath /ztp/entries/organization-name
ztpEntriesOrganizationName OBJECT-TYPE
    SYNTAX      String (SIZE (1 .. 128))
    MAX-ACCESS  read-only
    STATUS      current
    DESCRIPTION "Enterprise organization name"
    ::= { ztpEntriesEntry 7 }

-- tagpath /ztp/entries/root-cert-path
ztpEntriesRootCertPath OBJECT-TYPE
    SYNTAX      String (SIZE (1 .. 128))
    MAX-ACCESS  read-only
    STATUS      current
    DESCRIPTION "Enterprise root certificate path"
    ::= { ztpEntriesEntry 8 }

END
