--
 -- AUTOGENERATED   AUTOGENERATED  AUTOGENERATED
 -- AUTOGENERATED   AUTOGENERATED  AUTOGENERATED
 --
VIPTELA-MODELS DEFINITIONS ::= BEGIN
IMPORTS
    MODULE-IDENTITY, enterprises
        FROM SNMPv2-SMI
    TEXTUAL-CONVENTION
        FROM SNMPv2-TC
    viptela
        FROM VIPTELA-GLOBAL
;

viptela-models MODULE-IDENTITY
    LAST-UPDATED "202103020000Z"
    ORGANIZATION "Viptela, Inc."
    CONTACT-INFO "Viptela, Inc.  Email:support@viptela.com"
    DESCRIPTION  "Viptela Device types (PIDs)"
    ::= { viptela 8 }

DeviceModelType ::= TEXTUAL-CONVENTION
    DISPLAY-HINT "d"
    STATUS       current
    DESCRIPTION "Viptela Model types/pids"
    SYNTAX       INTEGER {
        vsmart(1),
        vmanage(2),
        vbond-software(3),
        vedge-cloud(12),
        vedge-nfvis-ENCS5100(101),
        vedge-nfvis-ENCS5400(102),
        vedge-nfvis-UCSC-M5(103),
        vedge-nfvis-UCSC-E(104),
        vedge-nfvis-CSP2100(105),
        vedge-nfvis-CSP2100-X1(106),
        vedge-nfvis-CSP2100-X2(107),
        vedge-nfvis-CSP-5444(108),
        vedge-nfvis-CSP-5456(109),
        vedge-nfvis-C8200-UCPE(110),
        vedge-nfvis-C8200-UCPEVM(111),
        vedge-nfvis-CSP-5400(112),
        vedge-nfvis-CSP-5216(113),
        vedge-nfvis-CSP-5228(114),
        vedge-nfvis-CSP-5436(115),
        vedge-nfvis-UCSC-C240-M6SN(116),
        vedge-nfvis-UCSC-C240-M6N(117),
        vedge-nfvis-UCSC-C240-M6SX(118),
        vedge-nfvis-UCSC-C240-M6S(119),
        vedge-nfvis-UCSC-C220-M6S(120),
        vedge-nfvis-UCSC-C220-M6N(121),
        vedge-nfvis-C8300-UCPE-1N20(122)
    }

END
