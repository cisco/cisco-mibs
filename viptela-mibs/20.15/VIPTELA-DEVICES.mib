--
 -- AUTOGENERATED   AUTOGENERATED  AUTOGENERATED
 -- AUTOGENERATED   AUTOGENERATED  AUTOGENERATED
 --
VIPTELA-DEVICES DEFINITIONS ::= BEGIN
IMPORTS
    MODULE-IDENTITY, enterprises
        FROM SNMPv2-SMI
    TEXTUAL-CONVENTION
        FROM SNMPv2-TC
    viptela
        FROM VIPTELA-GLOBAL
    viptelaDevices
        FROM VIPTELA-HARDWARE
;

viptela-devices MODULE-IDENTITY
    LAST-UPDATED "202103020000Z"
    ORGANIZATION "Viptela, Inc."
    CONTACT-INFO "Viptela, Inc.  Email:support@viptela.com"
    DESCRIPTION  "Viptela Devices"
    ::= { viptela 9 }


--tagpath /viptela-devices/vsmart
vsmart OBJECT IDENTIFIER ::= { viptelaDevices 1 }

--tagpath /viptela-devices/vmanage
vmanage OBJECT IDENTIFIER ::= { viptelaDevices 2 }

--tagpath /viptela-devices/vbond-software
vbondSoftware OBJECT IDENTIFIER ::= { viptelaDevices 3 }

--tagpath /viptela-devices/vedge-cloud
vedgeCloud OBJECT IDENTIFIER ::= { viptelaDevices 12 }

--tagpath /viptela-devices/vedge-nfvis-ENCS5100
nfvis-ENCS5100 OBJECT IDENTIFIER ::= { viptelaDevices 101 }

--tagpath /viptela-devices/vedge-nfvis-ENCS5400
nfvis-ENCS5400 OBJECT IDENTIFIER ::= { viptelaDevices 102 }

--tagpath /viptela-devices/vedge-nfvis-UCSC-M5
nfvis-UCSC-M5 OBJECT IDENTIFIER ::= { viptelaDevices 103 }

--tagpath /viptela-devices/vedge-nfvis-UCSC-E
nfvis-UCSC-E OBJECT IDENTIFIER ::= { viptelaDevices 104 }

--tagpath /viptela-devices/vedge-nfvis-CSP2100
nfvis-CSP2100 OBJECT IDENTIFIER ::= { viptelaDevices 105 }

--tagpath /viptela-devices/vedge-nfvis-CSP2100-X1
nfvis-CSP2100-X1 OBJECT IDENTIFIER ::= { viptelaDevices 106 }

--tagpath /viptela-devices/vedge-nfvis-CSP2100-X2
nfvis-CSP2100-X2 OBJECT IDENTIFIER ::= { viptelaDevices 107 }

--tagpath /viptela-devices/vedge-nfvis-CSP-5444
nfvis-CSP-5444 OBJECT IDENTIFIER ::= { viptelaDevices 108 }

--tagpath /viptela-devices/vedge-nfvis-CSP-5456
nfvis-CSP-5456 OBJECT IDENTIFIER ::= { viptelaDevices 109 }

--tagpath /viptela-devices/vedge-nfvis-C8200-UCPE
nfvis-C8200-UCPE OBJECT IDENTIFIER ::= { viptelaDevices 110 }

--tagpath /viptela-devices/vedge-nfvis-C8200-UCPEVM
nfvis-C8200-UCPEVM OBJECT IDENTIFIER ::= { viptelaDevices 111 }

--tagpath /viptela-devices/vedge-nfvis-CSP-5400
nfvis-CSP-5400 OBJECT IDENTIFIER ::= { viptelaDevices 112 }

--tagpath /viptela-devices/vedge-nfvis-CSP-5216
nfvis-CSP-5216 OBJECT IDENTIFIER ::= { viptelaDevices 113 }

--tagpath /viptela-devices/vedge-nfvis-CSP-5228
nfvis-CSP-5228 OBJECT IDENTIFIER ::= { viptelaDevices 114 }

--tagpath /viptela-devices/vedge-nfvis-CSP-5436
nfvis-CSP-5436 OBJECT IDENTIFIER ::= { viptelaDevices 115 }

--tagpath /viptela-devices/vedge-nfvis-UCSC-C240-M6SN
nfvis-UCSC-C240-M6SN OBJECT IDENTIFIER ::= { viptelaDevices 116 }

--tagpath /viptela-devices/vedge-nfvis-UCSC-C240-M6N
nfvis-UCSC-C240-M6N OBJECT IDENTIFIER ::= { viptelaDevices 117 }

--tagpath /viptela-devices/vedge-nfvis-UCSC-C240-M6SX
nfvis-UCSC-C240-M6SX OBJECT IDENTIFIER ::= { viptelaDevices 118 }

--tagpath /viptela-devices/vedge-nfvis-UCSC-C240-M6S
nfvis-UCSC-C240-M6S OBJECT IDENTIFIER ::= { viptelaDevices 119 }

--tagpath /viptela-devices/vedge-nfvis-UCSC-C220-M6S
nfvis-UCSC-C220-M6S OBJECT IDENTIFIER ::= { viptelaDevices 120 }

--tagpath /viptela-devices/vedge-nfvis-UCSC-C220-M6N
nfvis-UCSC-C220-M6N OBJECT IDENTIFIER ::= { viptelaDevices 121 }

--tagpath /viptela-devices/vedge-nfvis-C8300-UCPE-1N20
nfvis-C8300-UCPE-1N20 OBJECT IDENTIFIER ::= { viptelaDevices 122 }


END
