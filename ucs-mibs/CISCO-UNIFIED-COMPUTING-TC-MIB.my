-- *********************************************************************
-- CISCO-UNIFIED-COMPUTING-TC-MIB.my
-- 
-- MIB representation of the Cisco Unified Computing System
-- TEXTUALCONVENTIONS management information model package
-- 
-- Created January 2026 by Charles Bullis
-- 
-- Copyright (c) 2005-2026 Cisco Systems, Inc. All rights reserved.
-- 
-- *********************************************************************

CISCO-UNIFIED-COMPUTING-TC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIB,
    CucsManagedObjectId,
    CucsManagedObjectDn
        FROM CISCO-UNIFIED-COMPUTING-MIB;

cucsTextualConventionsObjects MODULE-IDENTITY
    LAST-UPDATED    "202601150000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        TEXTUALCONVENTIONS management information model package"
    ::= { ciscoUnifiedComputingMIB 4 }

CucsAaaAccess ::= TEXTUAL-CONVENTION
    STATUS        current
    DESCRIPTION
        ""
    SYNTAX        BITS
    {
        readOnly(0),
        admin(1),
        operations(2),
        fault(3),
        aaa(4),
        podConfig(5),
        podPolicy(6),
        podSecurity(7),
        podQos(8),
        extLanConfig(9),
        extLanPolicy(10),
        extLanSecurity(11),
        extLanQos(12),
        extSanConfig(13),
        extSanPolicy(14),
        extSanSecurity(15),
        extSanQos(16),
        pnEquipment(17),
        pnPolicy(18),
        pnSecurity(19),
        pnMaintenance(20),
        lsConfig(21),
        lsStorage(22),
        lsNetwork(23),
        lsSecurity(24),
        lsServer(25),
        lsQos(26),
        lsConfigPolicy(27),
        lsStoragePolicy(28),
        lsNetworkPolicy(29),
        lsSecurityPolicy(30),
        lsServerPolicy(31),
        lsQosPolicy(32),
        lsExtAccess(33),
        powerMgmt(34),
        lsServerOper(36),
        lsCompute(37),
        orgManagement(38),
        domainGroupManagement(39),
        statsManagement(40),
        kvm(41),
        tag(42)
    }

CucsAaaAccountStatus ::= TEXTUAL-CONVENTION
    STATUS        current
    DESCRIPTION
        ""
    SYNTAX        INTEGER
    {
        active(0),
        inactive(1)
    }

CucsAaaAdminState ::= TEXTUAL-CONVENTION
    STATUS        current
    DESCRIPTION
        ""
    SYNTAX        INTEGER
    {
        enable(0),
        disable(1)
    }

CucsAaaAuthRealmFsmCurrentFsm ::= TEXTUAL-CONVENTION
    STATUS        current
    DESCRIPTION
        ""
    SYNTAX        INTEGER
    {
        nop(0),
        updateRealm(200)
    }

CucsAaaAuthRealmFsmStageName ::= TEXTUAL-CONVENTION
    STATUS        current
    DESCRIPTION
        ""
    SYNTAX        INTEGER
    {
        nop(0),
        updateRealmBegin(200),
        updateRealmSetRealmLocal(201),
        updateRealmSetRealmPeer(202),
        updateRealmFail(324),
        updateRealmSuccess(325),
        updateRealmSetRealm(385)
    }

CucsAaaCimcSessionType ::= TEXTUAL-CONVENTION
    STATUS        current
    DESCRIPTION
        ""
    SYNTAX        INTEGER
    {
        all(0),
        kvm(1),
        vmedia(2),
        sol(3)
    }

CucsAaaClear ::= TEXTUAL-CONVENTION
    STATUS        current
    DESCRIPTION
        ""
    SYNTAX        INTEGER
    {
        no(0),
        yes(1)
    }

CucsAaaConfigState ::= TEXTUAL-CONVENTION
    STATUS        current
    DESCRIPTION
        ""
    SYNTAX        INTEGER
    {
        ok(0),
        notApplied(1)
    }

CucsAaaDomainAuthRealm ::= TEXTUAL-CONVENTION
    STATUS        current
    DESCRIPTION
        ""
    SYNTAX        INTEGER
    {
        local(0),
        radius(1),
        tacacs(2),
        ldap(3),
        none(4)
    }

CucsAaaEpAccess ::= TEXTUAL-CONVENTION
    STATUS        current
    DESCRIPTION
        ""
    SYNTAX        INTEGER
    {
        readonly(1),
        admin(2)
    }

CucsAaaEpFsmCurrentFsm ::= TEXTUAL-CONVENTION
    STATUS        current
    DESCRIPTION
        ""
    SYNTAX        INTEGER
    {
        nop(0),
        updateEp(197)
    }

CucsAaaEpFsmStageName ::= TEXTUAL-CONVENTION
    STATUS        current
    DESCRIPTION
        ""
    SYNTAX        INTEGER
    {
        nop(0),
        updateEpBegin(197),
        updateEpSetEpLocal(198),
        updateEpSetEpPeer(199),
        updateEpFail(322),
        updateEpSuccess(323)
    }

CucsAaaEpFsmTaskItem ::= TEXTUAL-CONVENTION
    STATUS        current
    DESCRIPTION
        ""
    SYNTAX        INTEGER
    {
        nop(0),
        updateEp(197)
    }

CucsAaaExtMgmtAccess ::= TEXTUAL-CONVENTION
    STATUS        current
    DESCRIPTION
        ""
    SYNTAX        INTEGER
    {
        kvm(1)
    }

CucsAaaIpmiOverLan ::= TEXTUAL-CONVENTION
    STATUS        current
    DESCRIPTION
        ""
    SYNTAX        INTEGER
    {
        disable(0),
        enable(1)
    }

CucsAaaLdapEpFsmCurrentFsm ::= TEXTUAL-CONVENTION
    STATUS        current
    DESCRIPTION
        ""
    SYNTAX        INTEGER
    {
        nop(0),
        updateEp(197)
    }

CucsAaaLdapEpFsmStageName ::= TEXTUAL-CONVENTION
    STATUS        current
    DESCRIPTION
        ""
    SYNTAX        INTEGER
    {
        nop(0),
        updateEpBegin(197),
        updateEpSetEpLocal(198),
        updateEpSetEpPeer(199),
        updateEpFail(322),
        updateEpSuccess(323)
    }

CucsAaaLdapGroupRuleAuthorization ::= TEXTUAL-CONVENTION
    STATUS        current
    DESCRIPTION
        ""
    SYNTAX        INTEGER
    {
        disable(0),
        enable(1)
    }

CucsAaaLdapGroupRuleTraversal ::= TEXTUAL-CONVENTION
    STATUS        current
    DESCRIPTION
        ""
    SYNTAX        INTEGER
    {
        nonRecursive(0),
        recursive(1)
    }

CucsAaaLdapVendor ::= TEXTUAL-CONVENTION
    STATUS        current
    DESCRIPTION
        ""
    SYNTAX        INTEGER
    {
        openLdap(0),
        msAd(1)
    }

CucsAaaNoRolePolicy ::= TEXTUAL-CONVENTION
    STATUS        current
    DESCRIPTION
        ""
    SYNTAX        INTEGER
    {
        noLogin(0),
        assignDefaultRole(1)
    }

CucsAaaPwdHashAlgo ::= TEXTUAL-CONVENTION
    STATUS        current
    DESCRIPTION
        ""
    SYNTAX        INTEGER
    {
        unknown(0),
        md5(1),
        blowfish(3),
        sha256(5),
        sha512(6),
        yescrypt(7)
    }

CucsAaaPwdPolicy ::= TEXTUAL-CONVENTION
    STATUS        current
    DESCRIPTION
        ""
    SYNTAX        INTEGER
    {
        enable(0),
        disable(1)
    }

CucsAaaRadiusEpFsmCurrentFsm ::= TEXTUAL-CONVENTION
    STATUS        current
    DESCRIPTION
        ""
    SYNTAX        INTEGER
    {
        nop(0),
        updateEp(197)
    }

CucsAaaRadiusEpFsmStageName ::= TEXTUAL-CONVENTION
    STATUS        current
    DESCRIPTION
        ""
    SYNTAX        INTEGER
    {
        nop(0),
        updateEpBegin(197),
        updateEpSetEpLocal(198),
        updateEpSetEpPeer(199),
        updateEpFail(322),
        updateEpSuccess(323)
    }

CucsAaaRadiusService ::= TEXTUAL-CONVENTION
    STATUS        current
    DESCRIPTION
        ""
    SYNTAX        INTEGER
    {
        all(0),
        defaultValue(1),
        accounting(2)
    }

CucsAaaRealm ::= TEXTUAL-CONVENTION
    STATUS        current
    DESCRIPTION
        ""
    SYNTAX        INTEGER
    {
        local(0),
        radius(1),
        tacacs(2),
        ldap(3),
        none(4)
    }

CucsAaaRealmFsmCurrentFsm ::= TEXTUAL-CONVENTION
    STATUS        current
    DESCRIPTION
        ""
    SYNTAX        INTEGER
    {
        nop(0),
        updateRealm(200)
    }

CucsAaaRealmFsmStageName ::= TEXTUAL-CONVENTION
    STATUS        current
    DESCRIPTION
        ""
    SYNTAX        INTEGER
    {
        nop(0),
        updateRealmBegin(200),
        updateRealmSetRealmLocal(201),
        updateRealmSetRealmPeer(202),
        updateRealmFail(324),
        updateRealmSuccess(325),
        updateRealmSetRealm(385)
    }

CucsAaaRealmFsmTaskItem ::= TEXTUAL-CONVENTION
    STATUS        current
    DESCRIPTION
        ""
    SYNTAX        INTEGER
    {
        nop(0),
        updateRealm(200)
    }

CucsAaaSession ::= TEXTUAL-CONVENTION
    STATUS        current
    DESCRIPTION
        ""
    SYNTAX        INTEGER
    {
        local(0),
        remote(1),
        ipmi(2)
    }

CucsAaaSessionState ::= TEXTUAL-CONVENTION
    STATUS        current
    DESCRIPTION
        ""
    SYNTAX        INTEGER
    {
        active(0),
        inactive(1)
    }

CucsAaaSessionTimeout ::= TEXTUAL-CONVENTION
    STATUS        current
    DESCRIPTION
        ""
    SYNTAX        Gauge32 (5..120)

CucsAaaSshStr ::= TEXTUAL-CONVENTION
    STATUS        current
    DESCRIPTION
        ""
    SYNTAX        INTEGER
    {
        none(0),
        key(1)
    }

CucsAaaTabRestoreMode ::= TEXTUAL-CONVENTION
    STATUS        current
    DESCRIPTION
        ""
    SYNTAX        INTEGER
    {
        autoRestore(0),
        promptUser(1),
        doNotRestore(2)
    }

CucsAaaTacacsPlusEpFsmCurrentFsm ::= TEXTUAL-CONVENTION
    STATUS        current
    DESCRIPTION
        ""
    SYNTAX        INTEGER
    {
        nop(0),
        updateEp(197)
    }

CucsAaaTacacsPlusEpFsmStageName ::= TEXTUAL-CONVENTION
    STATUS        current
    DESCRIPTION
        ""
    SYNTAX        INTEGER
    {
        nop(0),
        updateEpBegin(197),
        updateEpSetEpLocal(198),
        updateEpSetEpPeer(199),
        updateEpFail(322),
        updateEpSuccess(323)
    }

CucsAaaUserPasswdexpirystatus ::= TEXTUAL-CONVENTION
    STATUS        current
    DESCRIPTION
        ""
    SYNTAX        INTEGER
    {
        no(0),
        warning(1),
        expired(2)
    }

CucsAaaUserBlockingLevel ::= TEXTUAL-CONVENTION
    STATUS        current
    DESCRIPTION
        ""
    SYNTAX        INTEGER
    {
        allUsers(0),
        perUser(1)
    }

CucsAaaUserEpFsmCurrentFsm ::= TEXTUAL-CONVENTION
    STATUS        current
    DESCRIPTION
        ""
    SYNTAX        INTEGER
    {
        nop(0),
        updateUserEp(203)
    }

CucsAaaUserEpFsmStageName ::= TEXTUAL-CONVENTION
    STATUS        current
    DESCRIPTION
        ""
    SYNTAX        INTEGER
    {
        nop(0),
        updateUserEpBegin(203),
        updateUserEpSetUserLocal(204),
        updateUserEpSetUserPeer(205),
        updateUserEpFail(326),
        updateUserEpSuccess(327)
    }

CucsAaaUserEpFsmTaskItem ::= TEXTUAL-CONVENTION
    STATUS        current
    DESCRIPTION
        ""
    SYNTAX        INTEGER
    {
        nop(0),
        updateUserEp(203)
    }

CucsAaaUserInterface ::= TEXTUAL-CONVENTION
    STATUS        current
    DESCRIPTION
        ""
    SYNTAX        INTEGER
    {
        none(0),
        shell(1),
        web(2),
        ep(3),
        kvm(4),
        vmedia(5),
        sol(6)
    }

CucsAdaptorAdapterStatsTrafficDir ::= TEXTUAL-CONVENTION
    STATUS        current
    DESCRIPTION
        ""
    SYNTAX        INTEGER
    {
        unknown(0),
        tx(1),
        rx(2)
    }

CucsAdaptorAdminPowerState ::= TEXTUAL-CONVENTION
    STATUS        current
    DESCRIPTION
        ""
    SYNTAX        INTEGER
    {
        none(0),
        resetPower(1)
    }

CucsAdaptorAdminState ::= TEXTUAL-CONVENTION
    STATUS        current
    DESCRIPTION
        ""
    SYNTAX        INTEGER
    {
        enabled(0),
        resetConnectivityActive(44),
        resetConnectivityPassive(45),
        resetConnectivity(46),
        disabled(47),
        disabledPassive(48),
        disabledActive(49),
        enabledPassive(50),
        enabledActive(51)
    }

CucsAdaptorAzureQosProfileAdpAzureQos ::= TEXTUAL-CONVENTION
    STATUS        current
    DESCRIPTION
        ""
    SYNTAX        INTEGER
    {
        disabled(0),
        enabled(1)
    }

CucsAdaptorCIoEpIfType ::= TEXTUAL-CONVENTION
    STATUS        current
    DESCRIPTION
        ""
    SYNTAX        INTEGER
    {
        unknown(0),
        physical(1),
        aggregation(2),
        virtual(3)
    }

CucsAdaptorCapDefFwVersionOpr ::= TEXTUAL-CONVENTION
    STATUS        current
    DESCRIPTION
        ""
    SYNTAX        INTEGER
    {
        none(0),
        gt(1),
        lt(2),
        range(3)
    }

CucsAdaptorCapDefType ::= TEXTUAL-CONVENTION
    STATUS        current
    DESCRIPTION
        ""
    SYNTAX        INTEGER
    {
        virtualizedEthIf(1),
        virtualizedFcIf(2),
        virtualizedScsiIf(3),
        nonVirtualizedEthIf(4),
        nonVirtualizedFcIf(5),
        fcoe(6),
        protectedEthIf(7),
        protectedFcIf(8),
        protectedFcoe(9),
        pathEncapVirtual(10),
        pathEncapConsolidated(11),
        uplinkAggregation(12),
        virtualizedEthSriov(13),
        virtualizedFcSriov(14),
        virtualizedEthSriovUsnic(15),
        virtualizedEthVmq(16),
        ethFlowMonitoringNetflow(17),
        ethRoce(18),
        ethVxlan(19),
        ethNvgre(20),
        virtualizedCeEthIf(21),
        pathEncapVirtualCe(22),
        pxebootConfigSupport(23),
        oracleRacSupport(25),
        virtualizedEthVmmq(27),
        ethVxlanVmq(28),
        ethRoceV2(29),
        ethVxlanRocev2(30),
        ethNvgreRocev2(31),
        ethPtp(32)
    }

CucsAdaptorCapSpecRetimerSupport ::= TEXTUAL-CONVENTION
    STATUS        current
    DESCRIPTION
        ""
    SYNTAX        INTEGER
    {
        no(0),
        yes(1)
    }

CucsAdaptorCapSpecType ::= TEXTUAL-CONVENTION
    STATUS        current
    DESCRIPTION
        ""
    SYNTAX        INTEGER
    {
        virtualizedEthIf(1),
        virtualizedFcIf(2),
        virtualizedScsiIf(3),
        nonVirtualizedEthIf(4),
        nonVirtualizedFcIf(5),
        fcoe(6),
        protectedEthIf(7),
        protectedFcIf(8),
        protectedFcoe(9),
        pathEncapVirtual(10),
        pathEncapConsolidated(11),
        uplinkAggregation(12),
        virtualizedEthSriov(13),
        virtualizedFcSriov(14),
        virtualizedEthSriovUsnic(15),
        virtualizedEthVmq(16),
        ethFlowMonitoringNetflow(17),
        ethRoce(18),
        ethVxlan(19),
        ethNvgre(20),
        virtualizedCeEthIf(21),
        pathEncapVirtualCe(22),
        pxebootConfigSupport(23),
        oracleRacSupport(25),
        virtualizedEthVmmq(27),
        ethVxlanVmq(28),
        ethRoceV2(29),
        ethVxlanRocev2(30),
        ethNvgreRocev2(31),
        ethPtp(32)
    }

CucsAdaptorDefaultAction ::= TEXTUAL-CONVENTION
    STATUS        current
    DESCRIPTION
        ""
    SYNTAX        INTEGER
    {
        no(0),
        yes(1)
    }

CucsAdaptorDynamicConfigParams ::= TEXTUAL-CONVENTION
    STATUS        current
    DESCRIPTION
        ""
    SYNTAX        BITS
    {
        unknown(0),
        vlan(1)
    }

CucsAdaptorEthAdvFilterProfileAdminState ::= TEXTUAL-CONVENTION
    STATUS        current
    DESCRIPTION
        ""
    SYNTAX        INTEGER
    {
        disabled(0),
        enabled(1)
    }

CucsAdaptorEthArfsProfileAccelaratedRFS ::= TEXTUAL-CONVENTION
    STATUS        current
    DESCRIPTION
        ""
    SYNTAX        INTEGER
    {
        disabled(0),
        enabled(1)
    }

CucsAdaptorEthGENEVEProfileOffload ::= TEXTUAL-CONVENTION
    STATUS        current
    DESCRIPTION
        ""
    SYNTAX        INTEGER
    {
        disabled(0),
        enabled(1)
    }

CucsAdaptorEthInterruptProfileCoalescingType ::= TEXTUAL-CONVENTION
    STATUS        current
    DESCRIPTION
        ""
    SYNTAX        INTEGER
    {
        min(0),
        idle(1)
    }

CucsAdaptorEthInterruptScalingProfileAdminState ::= TEXTUAL-CONVENTION
    STATUS        current
    DESCRIPTION
        ""
    SYNTAX        INTEGER
    {
        disabled(0),
        enabled(1)
    }

CucsAdaptorEthNVGREProfileAdminState ::= TEXTUAL-CONVENTION
    STATUS        current
    DESCRIPTION
        ""
    SYNTAX        INTEGER
    {
        disabled(0),
        enabled(1)
    }

CucsAdaptorEthOffloadProfileLargeReceive ::= TEXTUAL-CONVENTION
    STATUS        current
    DESCRIPTION
        ""
    SYNTAX        INTEGER
    {
        disabled(0),
        enabled(1)
    }

CucsAdaptorEthOffloadProfileTcpRxChecksum ::= TEXTUAL-CONVENTION
    STATUS        current
    DESCRIPTION
        ""
    SYNTAX        INTEGER
    {
        disabled(0),
        enabled(1)
    }

CucsAdaptorEthOffloadProfileTcpSegment ::= TEXTUAL-CONVENTION
    STATUS        current
    DESCRIPTION
        ""
    SYNTAX        INTEGER
    {
        disabled(0),
        enabled(1)
    }

CucsAdaptorEthOffloadProfileTcpTxChecksum ::= TEXTUAL-CONVENTION
    STATUS        current
    DESCRIPTION
        ""
    SYNTAX        INTEGER
    {
        disabled(0),
        enabled(1)
    }

CucsAdaptorEthPortBySizeLargeStatsThresholded ::= TEXTUAL-CONVENTION
    STATUS        current
    DESCRIPTION
        ""
    SYNTAX        BITS
    {
        greaterThanOrEqualTo9216Delta(0),
        greaterThanOrEqualTo9216DeltaAvg(1),
        greaterThanOrEqualTo9216DeltaMax(2),
        greaterThanOrEqualTo9216DeltaMin(3),
        lessThan2048Delta(4),
        lessThan2048DeltaAvg(5),
        lessThan2048DeltaMax(6),
        lessThan2048DeltaMin(7),
        lessThan4096Delta(8),
        lessThan4096DeltaAvg(9),
        lessThan4096DeltaMax(10),
        lessThan4096DeltaMin(11),
        lessThan8192Delta(12),
        lessThan8192DeltaAvg(13),
        lessThan8192DeltaMax(14),
        lessThan8192DeltaMin(15),
        lessThan9216Delta(16),
        lessThan9216DeltaAvg(17),
        lessThan9216DeltaMax(18),
        lessThan9216DeltaMin(19),
        lessThanOrEqualTo1518Delta(20),
        lessThanOrEqualTo1518DeltaAvg(21),
        lessThanOrEqualTo1518DeltaMax(22),
        lessThanOrEqualTo1518DeltaMin(23),
        noBreakdownGreaterThan1518Delta(24),
        noBreakdownGreaterThan1518DeltaAvg(25),
        noBreakdownGreaterThan1518DeltaMax(26),
        noBreakdownGreaterThan1518DeltaMin(27)
    }

CucsAdaptorEthPortBySizeLargeStatsHistThresholded ::= TEXTUAL-CONVENTION
    STATUS        current
    DESCRIPTION
        ""
    SYNTAX        BITS
    {
        greaterThanOrEqualTo9216Delta(0),
        greaterThanOrEqualTo9216DeltaAvg(1),
        greaterThanOrEqualTo9216DeltaMax(2),
        greaterThanOrEqualTo9216DeltaMin(3),
        lessThan2048Delta(4),
        lessThan2048DeltaAvg(5),
        lessThan2048DeltaMax(6),
        lessThan2048DeltaMin(7),
        lessThan4096Delta(8),
        lessThan4096DeltaAvg(9),
        lessThan4096DeltaMax(10),
        lessThan4096DeltaMin(11),
        lessThan8192Delta(12),
        lessThan8192DeltaAvg(13),
        lessThan8192DeltaMax(14),
        lessThan8192DeltaMin(15),
        lessThan9216Delta(16),
        lessThan9216DeltaAvg(17),
        lessThan9216DeltaMax(18),
        lessThan9216DeltaMin(19),
        lessThanOrEqualTo1518Delta(20),
        lessThanOrEqualTo1518DeltaAvg(21),
        lessThanOrEqualTo1518DeltaMax(22),
        lessThanOrEqualTo1518DeltaMin(23),
        noBreakdownGreaterThan1518Delta(24),
        noBreakdownGreaterThan1518DeltaAvg(25),
        noBreakdownGreaterThan1518DeltaMax(26),
        noBreakdownGreaterThan1518DeltaMin(27)
    }

CucsAdaptorEthPortBySizeSmallStatsThresholded ::= TEXTUAL-CONVENTION
    STATUS        current
    DESCRIPTION
        ""
    SYNTAX        BITS
    {
        equals64Delta(0),
        equals64DeltaAvg(1),
        equals64DeltaMax(2),
        equals64DeltaMin(3),
        lessThan1024Delta(4),
        lessThan1024DeltaAvg(5),
        lessThan1024DeltaMax(6),
        lessThan1024DeltaMin(7),
        lessThan128Delta(8),
        lessThan128DeltaAvg(9),
        lessThan128DeltaMax(10),
        lessThan128DeltaMin(11),
        lessThan256Delta(12),
        lessThan256DeltaAvg(13),
        lessThan256DeltaMax(14),
        lessThan256DeltaMin(15),
        lessThan512Delta(16),
        lessThan512DeltaAvg(17),
        lessThan512DeltaMax(18),
        lessThan512DeltaMin(19),
        lessThan64Delta(20),
        lessThan64DeltaAvg(21),
        lessThan64DeltaMax(22),
        lessThan64DeltaMin(23)
    }

CucsAdaptorEthPortBySizeSmallStatsHistThresholded ::= TEXTUAL-CONVENTION
    STATUS        current
    DESCRIPTION
        ""
    SYNTAX        BITS
    {
        equals64Delta(0),
        equals64DeltaAvg(1),
        equals64DeltaMax(2),
        equals64DeltaMin(3),
        lessThan1024Delta(4),
        lessThan1024DeltaAvg(5),
        lessThan1024DeltaMax(6),
        lessThan1024DeltaMin(7),
        lessThan128Delta(8),
        lessThan128DeltaAvg(9),
        lessThan128DeltaMax(10),
        lessThan128DeltaMin(11),
        lessThan256Delta(12),
        lessThan256DeltaAvg(13),
        lessThan256DeltaMax(14),
        lessThan256DeltaMin(15),
        lessThan512Delta(16),
        lessThan512DeltaAvg(17),
        lessThan512DeltaMax(18),
        lessThan512DeltaMin(19),
        lessThan64Delta(20),
        lessThan64DeltaAvg(21),
        lessThan64DeltaMax(22),
        lessThan64DeltaMin(23)
    }

CucsAdaptorEthPortErrStatsThresholded ::= TEXTUAL-CONVENTION
    STATUS        current
    DESCRIPTION
        ""
    SYNTAX        BITS
    {
        badCrcPacketsDelta(0),
        badCrcPacketsDeltaAvg(1),
        badCrcPacketsDeltaMax(2),
        badCrcPacketsDeltaMin(3),
        badLengthPacketsDelta(4),
        badLengthPacketsDeltaAvg(5),
        badLengthPacketsDeltaMax(6),
        badLengthPacketsDeltaMin(7),
        macDiscardedPacketsDelta(8),
        macDiscardedPacketsDeltaAvg(9),
        macDiscardedPacketsDeltaMax(10),
        macDiscardedPacketsDeltaMin(11),
        noBufferDropPacketsDelta(12),
        noBufferDropPacketsDeltaAvg(13),
        noBufferDropPacketsDeltaMax(14),
        noBufferDropPacketsDeltaMin(15)
    }

CucsAdaptorEthPortErrStatsHistThresholded ::= TEXTUAL-CONVENTION
    STATUS        current
    DESCRIPTION
        ""
    SYNTAX        BITS
    {
        badCrcPacketsDelta(0),
        badCrcPacketsDeltaAvg(1),
        badCrcPacketsDeltaMax(2),
        badCrcPacketsDeltaMin(3),
        badLengthPacketsDelta(4),
        badLengthPacketsDeltaAvg(5),
        badLengthPacketsDeltaMax(6),
        badLengthPacketsDeltaMin(7),
        macDiscardedPacketsDelta(8),
        macDiscardedPacketsDeltaAvg(9),
        macDiscardedPacketsDeltaMax(10),
        macDiscardedPacketsDeltaMin(11),
        noBufferDropPacketsDelta(12),
        noBufferDropPacketsDeltaAvg(13),
        noBufferDropPacketsDeltaMax(14),
        noBufferDropPacketsDeltaMin(15)
    }

CucsAdaptorEthPortMcastStatsThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        multicastPacketsDelta(4),
        multicastPacketsDeltaAvg(5),
        multicastPacketsDeltaMax(6),
        multicastPacketsDeltaMin(7),
        unicastPacketsDelta(8),
        unicastPacketsDeltaAvg(9),
        unicastPacketsDeltaMax(10),
        unicastPacketsDeltaMin(11)
    }

CucsAdaptorEthPortMcastStatsHistThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        multicastPacketsDelta(4),
        multicastPacketsDeltaAvg(5),
        multicastPacketsDeltaMax(6),
        multicastPacketsDeltaMin(7),
        unicastPacketsDelta(8),
        unicastPacketsDeltaAvg(9),
        unicastPacketsDeltaMax(10),
        unicastPacketsDeltaMin(11)
    }

CucsAdaptorEthPortOutsizedStatsThresholded ::= TEXTUAL-CONVENTION
    STATUS        current
    DESCRIPTION
        ""
    SYNTAX        BITS
    {
        oversizedBadCrcPacketsDelta(0),
        oversizedBadCrcPacketsDeltaAvg(1),
        oversizedBadCrcPacketsDeltaMax(2),
        oversizedBadCrcPacketsDeltaMin(3),
        oversizedGoodCrcPacketsDelta(4),
        oversizedGoodCrcPacketsDeltaAvg(5),
        oversizedGoodCrcPacketsDeltaMax(6),
        oversizedGoodCrcPacketsDeltaMin(7),
        oversizedPacketsDelta(8),
        oversizedPacketsDeltaAvg(9),
        oversizedPacketsDeltaMax(10),
        oversizedPacketsDeltaMin(11),
        undersizedBadCrcPacketsDelta(12),
        undersizedBadCrcPacketsDeltaAvg(13),
        undersizedBadCrcPacketsDeltaMax(14),
        undersizedBadCrcPacketsDeltaMin(15),
        undersizedGoodCrcPacketsDelta(16),
        undersizedGoodCrcPacketsDeltaAvg(17),
        undersizedGoodCrcPacketsDeltaMax(18),
        undersizedGoodCrcPacketsDeltaMin(19)
    }

CucsAdaptorEthPortOutsizedStatsHistThresholded ::= TEXTUAL-CONVENTION
    STATUS        current
    DESCRIPTION
        ""
    SYNTAX        BITS
    {
        oversizedBadCrcPacketsDelta(0),
        oversizedBadCrcPacketsDeltaAvg(1),
        oversizedBadCrcPacketsDeltaMax(2),
        oversizedBadCrcPacketsDeltaMin(3),
        oversizedGoodCrcPacketsDelta(4),
        oversizedGoodCrcPacketsDeltaAvg(5),
        oversizedGoodCrcPacketsDeltaMax(6),
        oversizedGoodCrcPacketsDeltaMin(7),
        oversizedPacketsDelta(8),
        oversizedPacketsDeltaAvg(9),
        oversizedPacketsDeltaMax(10),
        oversizedPacketsDeltaMin(11),
        undersizedBadCrcPacketsDelta(12),
        undersizedBadCrcPacketsDeltaAvg(13),
        undersizedBadCrcPacketsDeltaMax(14),
        undersizedBadCrcPacketsDeltaMin(15),
        undersizedGoodCrcPacketsDelta(16),
        undersizedGoodCrcPacketsDeltaAvg(17),
        undersizedGoodCrcPacketsDeltaMax(18),
        undersizedGoodCrcPacketsDeltaMin(19)
    }

CucsAdaptorEthPortPfcStatsThresholded ::= TEXTUAL-CONVENTION
    STATUS        current
    DESCRIPTION
        ""
    SYNTAX        BITS
    {
        priority0QueueWaitTime(0),
        priority0QueueWaitTimeAvg(1),
        priority0QueueWaitTimeMax(2),
        priority0QueueWaitTimeMin(3),
        priority1QueueWaitTime(4),
        priority1QueueWaitTimeAvg(5),
        priority1QueueWaitTimeMax(6),
        priority1QueueWaitTimeMin(7),
        priority2QueueWaitTime(8),
        priority2QueueWaitTimeAvg(9),
        priority2QueueWaitTimeMax(10),
        priority2QueueWaitTimeMin(11),
        priority3QueueWaitTime(12),
        priority3QueueWaitTimeAvg(13),
        priority3QueueWaitTimeMax(14),
        priority3QueueWaitTimeMin(15),
        priority4QueueWaitTime(16),
        priority4QueueWaitTimeAvg(17),
        priority4QueueWaitTimeMax(18),
        priority4QueueWaitTimeMin(19),
        priority5QueueWaitTime(20),
        priority5QueueWaitTimeAvg(21),
        priority5QueueWaitTimeMax(22),
        priority5QueueWaitTimeMin(23),
        priority6QueueWaitTime(24),
        priority6QueueWaitTimeAvg(25),
        priority6QueueWaitTimeMax(26),
        priority6QueueWaitTimeMin(27),
        priority7QueueWaitTime(28),
        priority7QueueWaitTimeAvg(29),
        priority7QueueWaitTimeMax(30),
        priority7QueueWaitTimeMin(31)
    }

CucsAdaptorEthPortPfcStatsHistThresholded ::= TEXTUAL-CONVENTION
    STATUS        current
    DESCRIPTION
        ""
    SYNTAX        BITS
    {
        priority0QueueWaitTime(0),
        priority0QueueWaitTimeAvg(1),
        priority0QueueWaitTimeMax(2),
        priority0QueueWaitTimeMin(3),
        priority1QueueWaitTime(4),
        priority1QueueWaitTimeAvg(5),
        priority1QueueWaitTimeMax(6),
        priority1QueueWaitTimeMin(7),
        priority2QueueWaitTime(8),
        priority2QueueWaitTimeAvg(9),
        priority2QueueWaitTimeMax(10),
        priority2QueueWaitTimeMin(11),
        priority3QueueWaitTime(12),
        priority3QueueWaitTimeAvg(13),
        priority3QueueWaitTimeMax(14),
        priority3QueueWaitTimeMin(15),
        priority4QueueWaitTime(16),
        priority4QueueWaitTimeAvg(17),
        priority4QueueWaitTimeMax(18),
        priority4QueueWaitTimeMin(19),
        priority5QueueWaitTime(20),
        priority5QueueWaitTimeAvg(21),
        priority5QueueWaitTimeMax(22),
        priority5QueueWaitTimeMin(23),
        priority6QueueWaitTime(24),
        priority6QueueWaitTimeAvg(25),
        priority6QueueWaitTimeMax(26),
        priority6QueueWaitTimeMin(27),
        priority7QueueWaitTime(28),
        priority7QueueWaitTimeAvg(29),
        priority7QueueWaitTimeMax(30),
        priority7QueueWaitTimeMin(31)
    }

CucsAdaptorEthPortStatsThresholded ::= TEXTUAL-CONVENTION
    STATUS        current
    DESCRIPTION
        ""
    SYNTAX        BITS
    {
        goodPacketsDelta(0),
        goodPacketsDeltaAvg(1),
        goodPacketsDeltaMax(2),
        goodPacketsDeltaMin(3),
        pausePacketsDelta(4),
        pausePacketsDeltaAvg(5),
        pausePacketsDeltaMax(6),
        pausePacketsDeltaMin(7),
        perPriorityPausePacketsDelta(8),
        perPriorityPausePacketsDeltaAvg(9),
        perPriorityPausePacketsDeltaMax(10),
        perPriorityPausePacketsDeltaMin(11),
        pppPacketsDelta(12),
        pppPacketsDeltaAvg(13),
        pppPacketsDeltaMax(14),
        pppPacketsDeltaMin(15),
        totalPacketsDelta(16),
        totalPacketsDeltaAvg(17),
        totalPacketsDeltaMax(18),
        totalPacketsDeltaMin(19),
        vlanPacketsDelta(20),
        vlanPacketsDeltaAvg(21),
        vlanPacketsDeltaMax(22),
        vlanPacketsDeltaMin(23)
    }

CucsAdaptorEthPortStatsHistThresholded ::= TEXTUAL-CONVENTION
    STATUS        current
    DESCRIPTION
        ""
    SYNTAX        BITS
    {
        goodPacketsDelta(0),
        goodPacketsDeltaAvg(1),
        goodPacketsDeltaMax(2),
        goodPacketsDeltaMin(3),
        pausePacketsDelta(4),
        pausePacketsDeltaAvg(5),
        pausePacketsDeltaMax(6),
        pausePacketsDeltaMin(7),
        perPriorityPausePacketsDelta(8),
        perPriorityPausePacketsDeltaAvg(9),
        perPriorityPausePacketsDeltaMax(10),
        perPriorityPausePacketsDeltaMin(11),
        pppPacketsDelta(12),
        pppPacketsDeltaAvg(13),
        pppPacketsDeltaMax(14),
        pppPacketsDeltaMin(15),
        totalPacketsDelta(16),
        totalPacketsDeltaAvg(17),
        totalPacketsDeltaMax(18),
        totalPacketsDeltaMin(19),
        vlanPacketsDelta(20),
        vlanPacketsDeltaAvg(21),
        vlanPacketsDeltaMax(22),
        vlanPacketsDeltaMin(23)
    }

CucsAdaptorEthRoCEProfileAdminState ::= TEXTUAL-CONVENTION
    STATUS        current
    DESCRIPTION
        ""
    SYNTAX        INTEGER
    {
        disabled(0),
        enabled(1)
    }

CucsAdaptorEthRoCEProfileV1 ::= TEXTUAL-CONVENTION
    STATUS        current
    DESCRIPTION
        ""
    SYNTAX        INTEGER
    {
        disabled(0),
        enabled(1)
    }

CucsAdaptorEthRoCEProfileV2 ::= TEXTUAL-CONVENTION
    STATUS        current
    DESCRIPTION
        ""
    SYNTAX        INTEGER
    {
        disabled(0),
        enabled(1)
    }

CucsAdaptorEthVxLANProfileAdminState ::= TEXTUAL-CONVENTION
    STATUS        current
    DESCRIPTION
        ""
    SYNTAX        INTEGER
    {
        disabled(0),
        enabled(1)
    }

CucsAdaptorEtherIfStatsThresholded ::= TEXTUAL-CONVENTION
    STATUS        current
    DESCRIPTION
        ""
    SYNTAX        BITS
    {
        rxBytesDelta(0),
        rxBytesDeltaAvg(1),
        rxBytesDeltaMax(2),
        rxBytesDeltaMin(3),
        rxDroppedDelta(4),
        rxDroppedDeltaAvg(5),
        rxDroppedDeltaMax(6),
        rxDroppedDeltaMin(7),
        rxErrorsDelta(8),
        rxErrorsDeltaAvg(9),
        rxErrorsDeltaMax(10),
        rxErrorsDeltaMin(11),
        rxPacketsDelta(12),
        rxPacketsDeltaAvg(13),
        rxPacketsDeltaMax(14),
        rxPacketsDeltaMin(15),
        txBytesDelta(16),
        txBytesDeltaAvg(17),
        txBytesDeltaMax(18),
        txBytesDeltaMin(19),
        txDroppedDelta(20),
        txDroppedDeltaAvg(21),
        txDroppedDeltaMax(22),
        txDroppedDeltaMin(23),
        txErrorsDelta(24),
        txErrorsDeltaAvg(25),
        txErrorsDeltaMax(26),
        txErrorsDeltaMin(27),
        txPacketsDelta(28),
        txPacketsDeltaAvg(29),
        txPacketsDeltaMax(30),
        txPacketsDeltaMin(31)
    }

CucsAdaptorEtherIfStatsHistThresholded ::= TEXTUAL-CONVENTION
    STATUS        current
    DESCRIPTION
        ""
    SYNTAX        BITS
    {
        rxBytesDelta(0),
        rxBytesDeltaAvg(1),
        rxBytesDeltaMax(2),
        rxBytesDeltaMin(3),
        rxDroppedDelta(4),
        rxDroppedDeltaAvg(5),
        rxDroppedDeltaMax(6),
        rxDroppedDeltaMin(7),
        rxErrorsDelta(8),
        rxErrorsDeltaAvg(9),
        rxErrorsDeltaMax(10),
        rxErrorsDeltaMin(11),
        rxPacketsDelta(12),
        rxPacketsDeltaAvg(13),
        rxPacketsDeltaMax(14),
        rxPacketsDeltaMin(15),
        txBytesDelta(16),
        txBytesDeltaAvg(17),
        txBytesDeltaMax(18),
        txBytesDeltaMin(19),
        txDroppedDelta(20),
        txDroppedDeltaAvg(21),
        txDroppedDeltaMax(22),
        txDroppedDeltaMin(23),
        txErrorsDelta(24),
        txErrorsDeltaAvg(25),
        txErrorsDeltaMax(26),
        txErrorsDeltaMin(27),
        txPacketsDelta(28),
        txPacketsDeltaAvg(29),
        txPacketsDeltaMax(30),
        txPacketsDeltaMin(31)
    }

CucsAdaptorExtEthIfFsmCurrentFsm ::= TEXTUAL-CONVENTION
    STATUS        current
    DESCRIPTION
        ""
    SYNTAX        INTEGER
    {
        nop(0),
        pathReset(499)
    }

CucsAdaptorExtEthIfFsmStageName ::= TEXTUAL-CONVENTION
    STATUS        current
    DESCRIPTION
        ""
    SYNTAX        INTEGER
    {
        nop(0),
        pathResetBegin(499),
        pathResetDisable(500),
        pathResetEnable(501),
        pathResetFail(502),
        pathResetSuccess(503)
    }

CucsAdaptorExtEthIfFsmTaskItem ::= TEXTUAL-CONVENTION
    STATUS        current
    DESCRIPTION
        ""
    SYNTAX        INTEGER
    {
        nop(0),
        pathReset(499)
    }

CucsAdaptorExtEthIfPcPortId ::= TEXTUAL-CONVENTION
    STATUS        current
    DESCRIPTION
        ""
    SYNTAX        Gauge32 (1024..4096)

CucsAdaptorExtEthIfPcTransport ::= TEXTUAL-CONVENTION
    STATUS        current
    DESCRIPTION
        ""
    SYNTAX        BITS
    {
        ether(0),
        dce(1),
        fc(2)
    }

CucsAdaptorExtEthIfPcEpPortId ::= TEXTUAL-CONVENTION
    STATUS        current
    DESCRIPTION
        ""
    SYNTAX        Gauge32 (1..8)

CucsAdaptorExtEthIfPcEpSlotId ::= TEXTUAL-CONVENTION
    STATUS        current
    DESCRIPTION
        ""
    SYNTAX        Gauge32 (1..8)

CucsAdaptorExtIfAdminState ::= TEXTUAL-CONVENTION
    STATUS        current
    DESCRIPTION
        ""
    SYNTAX        INTEGER
    {
        enabled(0),
        resetConnectivity(44)
    }

CucsAdaptorExtIfEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsAdaptorExtIfEpType ::= TEXTUAL-CONVENTION
    STATUS        current
    DESCRIPTION
        ""
    SYNTAX        BITS
    {
        lan(0),
        san(1),
        ipc(2)
    }

CucsAdaptorExtIfPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsAdaptorExtIfPcType ::= TEXTUAL-CONVENTION
    STATUS        current
    DESCRIPTION
        ""
    SYNTAX        BITS
    {
        lan(0),
        san(1),
        ipc(2)
    }

CucsAdaptorExtIfRemoteAdminState ::= TEXTUAL-CONVENTION
    STATUS        current
    DESCRIPTION
        ""
    SYNTAX        INTEGER
    {
        enabled(0),
        remoteTrigger(1),
        resetConnectivity(44)
    }

CucsAdaptorExtIpV6RssHashProfileIpHash ::= TEXTUAL-CONVENTION
    STATUS        current
    DESCRIPTION
        ""
    SYNTAX        INTEGER
    {
        disabled(0),
        enabled(1)
    }

CucsAdaptorExtIpV6RssHashProfileTcpHash ::= TEXTUAL-CONVENTION
    STATUS        current
    DESCRIPTION
        ""
    SYNTAX        INTEGER
    {
        disabled(0),
        enabled(1)
    }

CucsAdaptorExternalEpLocale ::= TEXTUAL-CONVENTION
    STATUS        current
    DESCRIPTION
        ""
    SYNTAX        BITS
    {
        server(0),
        chassis(1),
        internal(2),
        external(3)
    }

CucsAdaptorExternalPcLocale ::= TEXTUAL-CONVENTION
    STATUS        current
    DESCRIPTION
        ""
    SYNTAX        BITS
    {
        server(0),
        chassis(1),
        internal(2),
        external(3)
    }

CucsAdaptorFamilyTypeDefBootMode ::= TEXTUAL-CONVENTION
    STATUS        current
    DESCRIPTION
        ""
    SYNTAX        INTEGER
    {
        unsecure(0),
        secure(1)
    }

CucsAdaptorFamilyTypeDefCpldSupport ::= TEXTUAL-CONVENTION
    STATUS        current
    DESCRIPTION
        ""
    SYNTAX        INTEGER
    {
        no(0),
        yes(1)
    }

CucsAdaptorFamilyTypeDefPcieNodeSupport ::= TEXTUAL-CONVENTION
    STATUS        current
    DESCRIPTION
        ""
    SYNTAX        INTEGER
    {
        no(0),
        yes(1)
    }

CucsAdaptorFamilyTypeDefUbmSupport ::= TEXTUAL-CONVENTION
    STATUS        current
    DESCRIPTION
        ""
    SYNTAX        INTEGER
    {
        no(0),
        yes(1)
    }

CucsAdaptorFcErrorRecoveryProfileFcpErrorRecovery ::= TEXTUAL-CONVENTION
    STATUS        current
    DESCRIPTION
        ""
    SYNTAX        INTEGER
    {
        disabled(0),
        enabled(1)
    }

CucsAdaptorFcIfEventStatsThresholded ::= TEXTUAL-CONVENTION
    STATUS        current
    DESCRIPTION
        ""
    SYNTAX        BITS
    {
        invalidCRCCountDelta(0),
        invalidCRCCountDeltaAvg(1),
        invalidCRCCountDeltaMax(2),
        invalidCRCCountDeltaMin(3),
        linkFailureCountDelta(4),
        linkFailureCountDeltaAvg(5),
        linkFailureCountDeltaMax(6),
        linkFailureCountDeltaMin(7),
        lipCountDelta(8),
        lipCountDeltaAvg(9),
        lipCountDeltaMax(10),
        lipCountDeltaMin(11),
        lossOfSignalCountDelta(12),
        lossOfSignalCountDeltaAvg(13),
        lossOfSignalCountDeltaMax(14),
        lossOfSignalCountDeltaMin(15),
        lossOfSyncCountDelta(16),
        lossOfSyncCountDeltaAvg(17),
        lossOfSyncCountDeltaMax(18),
        lossOfSyncCountDeltaMin(19),
        nOSCountDelta(20),
        nOSCountDeltaAvg(21),
        nOSCountDeltaMax(22),
        nOSCountDeltaMin(23),
        secondsSinceLastResetDelta(24),
        secondsSinceLastResetDeltaAvg(25),
        secondsSinceLastResetDeltaMax(26),
        secondsSinceLastResetDeltaMin(27),
        seqProtocolErrCountDelta(28),
        seqProtocolErrCountDeltaAvg(29),
        seqProtocolErrCountDeltaMax(30),
        seqProtocolErrCountDeltaMin(31)
    }

CucsAdaptorFcIfEventStatsHistThresholded ::= TEXTUAL-CONVENTION
    STATUS        current
    DESCRIPTION
        ""
    SYNTAX        BITS
    {
        invalidCRCCountDelta(0),
        invalidCRCCountDeltaAvg(1),
        invalidCRCCountDeltaMax(2),
        invalidCRCCountDeltaMin(3),
        linkFailureCountDelta(4),
        linkFailureCountDeltaAvg(5),
        linkFailureCountDeltaMax(6),
        linkFailureCountDeltaMin(7),
        lipCountDelta(8),
        lipCountDeltaAvg(9),
        lipCountDeltaMax(10),
        lipCountDeltaMin(11),
        lossOfSignalCountDelta(12),
        lossOfSignalCountDeltaAvg(13),
        lossOfSignalCountDeltaMax(14),
        lossOfSignalCountDeltaMin(15),
        lossOfSyncCountDelta(16),
        lossOfSyncCountDeltaAvg(17),
        lossOfSyncCountDeltaMax(18),
        lossOfSyncCountDeltaMin(19),
        nOSCountDelta(20),
        nOSCountDeltaAvg(21),
        nOSCountDeltaMax(22),
        nOSCountDeltaMin(23),
        secondsSinceLastResetDelta(24),
        secondsSinceLastResetDeltaAvg(25),
        secondsSinceLastResetDeltaMax(26),
        secondsSinceLastResetDeltaMin(27),
        seqProtocolErrCountDelta(28),
        seqProtocolErrCountDeltaAvg(29),
        seqProtocolErrCountDeltaMax(30),
        seqProtocolErrCountDeltaMin(31)
    }

CucsAdaptorFcIfFC4StatsThresholded ::= TEXTUAL-CONVENTION
    STATUS        current
    DESCRIPTION
        ""
    SYNTAX        BITS
    {
        controlRequestsDelta(0),
        controlRequestsDeltaAvg(1),
        controlRequestsDeltaMax(2),
        controlRequestsDeltaMin(3),
        inputMegabytesDelta(4),
        inputMegabytesDeltaAvg(5),
        inputMegabytesDeltaMax(6),
        inputMegabytesDeltaMin(7),
        inputRequestsDelta(8),
        inputRequestsDeltaAvg(9),
        inputRequestsDeltaMax(10),
        inputRequestsDeltaMin(11),
        outputMegabytesDelta(12),
        outputMegabytesDeltaAvg(13),
        outputMegabytesDeltaMax(14),
        outputMegabytesDeltaMin(15),
        outputRequestsDelta(16),
        outputRequestsDeltaAvg(17),
        outputRequestsDeltaMax(18),
        outputRequestsDeltaMin(19)
    }

CucsAdaptorFcIfFC4StatsHistThresholded ::= TEXTUAL-CONVENTION
    STATUS        current
    DESCRIPTION
        ""
    SYNTAX        BITS
    {
        controlRequestsDelta(0),
        controlRequestsDeltaAvg(1),
        controlRequestsDeltaMax(2),
        controlRequestsDeltaMin(3),
        inputMegabytesDelta(4),
        inputMegabytesDeltaAvg(5),
        inputMegabytesDeltaMax(6),
        inputMegabytesDeltaMin(7),
        inputRequestsDelta(8),
        inputRequestsDeltaAvg(9),
        inputRequestsDeltaMax(10),
        inputRequestsDeltaMin(11),
        outputMegabytesDelta(12),
        outputMegabytesDeltaAvg(13),
        outputMegabytesDeltaMax(14),
        outputMegabytesDeltaMin(15),
        outputRequestsDelta(16),
        outputRequestsDeltaAvg(17),
        outputRequestsDeltaMax(18),
        outputRequestsDeltaMin(19)
    }

CucsAdaptorFcIfFrameStatsThresholded ::= TEXTUAL-CONVENTION
    STATUS        current
    DESCRIPTION
        ""
    SYNTAX        BITS
    {
        dumpedFramesDelta(0),
        dumpedFramesDeltaAvg(1),
        dumpedFramesDeltaMax(2),
        dumpedFramesDeltaMin(3),
        errorFramesDelta(4),
        errorFramesDeltaAvg(5),
        errorFramesDeltaMax(6),
        errorFramesDeltaMin(7),
        rxFramesDelta(8),
        rxFramesDeltaAvg(9),
        rxFramesDeltaMax(10),
        rxFramesDeltaMin(11),
        txFramesDelta(12),
        txFramesDeltaAvg(13),
        txFramesDeltaMax(14),
        txFramesDeltaMin(15)
    }

CucsAdaptorFcIfFrameStatsHistThresholded ::= TEXTUAL-CONVENTION
    STATUS        current
    DESCRIPTION
        ""
    SYNTAX        BITS
    {
        dumpedFramesDelta(0),
        dumpedFramesDeltaAvg(1),
        dumpedFramesDeltaMax(2),
        dumpedFramesDeltaMin(3),
        errorFramesDelta(4),
        errorFramesDeltaAvg(5),
        errorFramesDeltaMax(6),
        errorFramesDeltaMin(7),
        rxFramesDelta(8),
        rxFramesDeltaAvg(9),
        rxFramesDeltaMax(10),
        rxFramesDeltaMin(11),
        txFramesDelta(12),
        txFramesDeltaAvg(13),
        txFramesDeltaMax(14),
        txFramesDeltaMin(15)
    }

CucsAdaptorFcPortStatsThresholded ::= TEXTUAL-CONVENTION
    STATUS        current
    DESCRIPTION
        ""
    SYNTAX        BITS
    {
        rxBadFramesDelta(0),
        rxBadFramesDeltaAvg(1),
        rxBadFramesDeltaMax(2),
        rxBadFramesDeltaMin(3),
        rxFramesDelta(4),
        rxFramesDeltaAvg(5),
        rxFramesDeltaMax(6),
        rxFramesDeltaMin(7),
        txBadFramesDelta(8),
        txBadFramesDeltaAvg(9),
        txBadFramesDeltaMax(10),
        txBadFramesDeltaMin(11),
        txFramesDelta(12),
        txFramesDeltaAvg(13),
        txFramesDeltaMax(14),
        txFramesDeltaMin(15)
    }

CucsAdaptorFcPortStatsHistThresholded ::= TEXTUAL-CONVENTION
    STATUS        current
    DESCRIPTION
        ""
    SYNTAX        BITS
    {
        rxBadFramesDelta(0),
        rxBadFramesDeltaAvg(1),
        rxBadFramesDeltaMax(2),
        rxBadFramesDeltaMin(3),
        rxFramesDelta(4),
        rxFramesDeltaAvg(5),
        rxFramesDeltaMax(6),
        rxFramesDeltaMin(7),
        txBadFramesDelta(8),
        txBadFramesDeltaAvg(9),
        txBadFramesDeltaMax(10),
        txBadFramesDeltaMin(11),
        txFramesDelta(12),
        txFramesDeltaAvg(13),
        txFramesDeltaMax(14),
        txFramesDeltaMin(15)
    }

CucsAdaptorHBAVnicStatsThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CucsAdaptorHBAVnicStatsHistThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CucsAdaptorHostEthIfHostPort ::= TEXTUAL-CONVENTION
    STATUS        current
    DESCRIPTION
        ""
    SYNTAX        INTEGER
    {
        any(0),
        n1(1),
        n2(2),
        none(10)
    }

CucsAdaptorHostEthIfTransport ::= TEXTUAL-CONVENTION
    STATUS        current
    DESCRIPTION
        ""
    SYNTAX        BITS
    {
        ether(0),
        dce(1),
        fc(2)
    }

CucsAdaptorHostEthIfFsmCurrentFsm ::= TEXTUAL-CONVENTION
    STATUS        current
    DESCRIPTION
        ""
    SYNTAX        INTEGER
    {
        nop(0),
        circuitReset(505)
    }

CucsAdaptorHostEthIfFsmStageName ::= TEXTUAL-CONVENTION
    STATUS        current
    DESCRIPTION
        ""
    SYNTAX        INTEGER
    {
        nop(0),
        circuitResetBegin(505),
        circuitResetDisableA(506),
        circuitResetEnableA(507),
        circuitResetDisableB(508),
        circuitResetEnableB(509),
        circuitResetFail(515),
        circuitResetSuccess(516)
    }

CucsAdaptorHostEthIfFsmTaskItem ::= TEXTUAL-CONVENTION
    STATUS        current
    DESCRIPTION
        ""
    SYNTAX        INTEGER
    {
        nop(0),
        circuitReset(505)
    }

CucsAdaptorHostEthIfProfilePooledResources ::= TEXTUAL-CONVENTION
    STATUS        current
    DESCRIPTION
        ""
    SYNTAX        INTEGER
    {
        disabled(0),
        enabled(1)
    }

CucsAdaptorHostFcIfAdminState ::= TEXTUAL-CONVENTION
    STATUS        current
    DESCRIPTION
        ""
    SYNTAX        INTEGER
    {
        enabled(0),
        resetConnectivityActive(44),
        resetConnectivityPassive(45),
        resetConnectivity(46),
        disabled(47),
        disabledPassive(48),
        disabledActive(49),
        enabledPassive(50),
        enabledActive(51)
    }

CucsAdaptorHostFcIfHostPort ::= TEXTUAL-CONVENTION
    STATUS        current
    DESCRIPTION
        ""
    SYNTAX        INTEGER
    {
        any(0),
        n1(1),
        n2(2),
        none(10)
    }

CucsAdaptorHostFcIfPersBind ::= TEXTUAL-CONVENTION
    STATUS        current
    DESCRIPTION
        ""
    SYNTAX        INTEGER
    {
        disabled(0),
        enabled(4)
    }

CucsAdaptorHostFcIfTransport ::= TEXTUAL-CONVENTION
    STATUS        current
    DESCRIPTION
        ""
    SYNTAX        BITS
    {
        ether(0),
        dce(1),
        fc(2)
    }

CucsAdaptorHostFcIfFsmCurrentFsm ::= TEXTUAL-CONVENTION
    STATUS        current
    DESCRIPTION
        ""
    SYNTAX        INTEGER
    {
        nop(0),
        resetFcPersBinding(142),
        circuitReset(510)
    }

CucsAdaptorHostFcIfFsmStageName ::= TEXTUAL-CONVENTION
    STATUS        current
    DESCRIPTION
        ""
    SYNTAX        INTEGER
    {
        nop(0),
        resetFcPersBindingBegin(142),
        resetFcPersBindingFail(328),
        resetFcPersBindingSuccess(329),
        circuitResetBegin(510),
        circuitResetDisableA(511),
        circuitResetEnableA(512),
        circuitResetDisableB(513),
        circuitResetEnableB(514),
        circuitResetFail(517),
        circuitResetSuccess(518),
        resetFcPersBindingExecuteLocal(813),
        resetFcPersBindingExecutePeer(814)
    }

CucsAdaptorHostFcIfFsmTaskItem ::= TEXTUAL-CONVENTION
    STATUS        current
    DESCRIPTION
        ""
    SYNTAX        INTEGER
    {
        nop(0),
        resetFcPersBinding(142),
        circuitReset(510)
    }

CucsAdaptorHostFcIfRemoteAdminState ::= TEXTUAL-CONVENTION
    STATUS        current
    DESCRIPTION
        ""
    SYNTAX        INTEGER
    {
        enabled(0),
        remoteTrigger(1),
        resetConnectivityActive(44),
        resetConnectivityPassive(45),
        resetConnectivity(46),
        disabled(47),
        disabledPassive(48),
        disabledActive(49),
        enabledPassive(50),
        enabledActive(51)
    }

CucsAdaptorHostIfAdminState ::= TEXTUAL-CONVENTION
    STATUS        current
    DESCRIPTION
        ""
    SYNTAX        INTEGER
    {
        enabled(0),
        resetConnectivityActive(44),
        resetConnectivityPassive(45),
        resetConnectivity(46),
        disabled(47),
        disabledPassive(48),
        disabledActive(49),
        enabledPassive(50),
        enabledActive(51)
    }

CucsAdaptorHostIfBootDev ::= TEXTUAL-CONVENTION
    STATUS        current
    DESCRIPTION
        ""
    SYNTAX        INTEGER
    {
        disabled(0),
        enabled(1)
    }

CucsAdaptorHostIfRemoteAdminState ::= TEXTUAL-CONVENTION
    STATUS        current
    DESCRIPTION
        ""
    SYNTAX        INTEGER
    {
        enabled(0),
        remoteTrigger(1),
        resetConnectivityActive(44),
        resetConnectivityPassive(45),
        resetConnectivity(46),
        disabled(47),
        disabledPassive(48),
        disabledActive(49),
        enabledPassive(50),
        enabledActive(51)
    }

CucsAdaptorHostMgmtCapPreboot ::= TEXTUAL-CONVENTION
    STATUS        current
    DESCRIPTION
        ""
    SYNTAX        INTEGER
    {
        none(0),
        pnuOS(1),
        efi(2)
    }

CucsAdaptorHostMgmtCapPresence ::= TEXTUAL-CONVENTION
    STATUS        current
    DESCRIPTION
        ""
    SYNTAX        INTEGER
    {
        unspecified(0),
        host(1),
        cimc(2)
    }

CucsAdaptorHostPortId ::= TEXTUAL-CONVENTION
    STATUS        current
    DESCRIPTION
        ""
    SYNTAX        Gauge32 (1..5000)

CucsAdaptorHostServiceEthIfIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsAdaptorHostVisibility ::= TEXTUAL-CONVENTION
    STATUS        current
    DESCRIPTION
        ""
    SYNTAX        INTEGER
    {
        no(0),
        yes(1),
        osDependent(2)
    }

CucsAdaptorIScsiCapBootOrderType ::= TEXTUAL-CONVENTION
    STATUS        current
    DESCRIPTION
        ""
    SYNTAX        INTEGER
    {
        systemBootOrder(0),
        fddOrder(1),
        hddOrder(2),
        cdOrder(3),
        networkDeviceOrder(6),
        internalEfiShell(16),
        unknownDeviceOrder(99),
        localStorageAnyDeviceOrder(100),
        sanDeviceOrder(101),
        sanAnyDeviceOrder(102),
        internalUsbDeviceOrder(103),
        externalUsbDeviceOrder(104),
        sdcardDeviceOrder(105),
        lanAnyDeviceOrder(106),
        uefiTargetDeviceOrder(107),
        iscsiDeviceOrder(108),
        iscsiAnyDeviceOrder(109),
        cimcVmediaCddDeviceOrder(110),
        cimcVmediaHddDeviceOrder(111),
        cimcVmediaFddDeviceOrder(112),
        kvmVmediaCddDeviceOrder(113),
        kvmVmediaHddDeviceOrder(114),
        kvmVmediaFddDeviceOrder(115),
        uefiShellDeviceOrder(116),
        nvmeDeviceOrder(117),
        nvmeDiskSsdDeviceOrder(118),
        nvmePciSsdDeviceOrder(119),
        bevOrder(128)
    }

CucsAdaptorInterruptMode ::= TEXTUAL-CONVENTION
    STATUS        current
    DESCRIPTION
        ""
    SYNTAX        INTEGER
    {
        msiX(1),
        msi(2),
        intx(3)
    }

CucsAdaptorIpV4RssHashProfileIpHash ::= TEXTUAL-CONVENTION
    STATUS        current
    DESCRIPTION
        ""
    SYNTAX        INTEGER
    {
        disabled(0),
        enabled(1)
    }

CucsAdaptorIpV4RssHashProfileTcpHash ::= TEXTUAL-CONVENTION
    STATUS        current
    DESCRIPTION
        ""
    SYNTAX        INTEGER
    {
        disabled(0),
        enabled(1)
    }

CucsAdaptorIpV6RssHashProfileIpHash ::= TEXTUAL-CONVENTION
    STATUS        current
    DESCRIPTION
        ""
    SYNTAX        INTEGER
    {
        disabled(0),
        enabled(1)
    }

CucsAdaptorIpV6RssHashProfileTcpHash ::= TEXTUAL-CONVENTION
    STATUS        current
    DESCRIPTION
        ""
    SYNTAX        INTEGER
    {
        disabled(0),
        enabled(1)
    }

CucsAdaptorIscsiProtConnectionTimeOut ::= TEXTUAL-CONVENTION
    STATUS        current
    DESCRIPTION
        ""
    SYNTAX        Gauge32 (0..255)

CucsAdaptorIscsiProtDhcpTimeOut ::= TEXTUAL-CONVENTION
    STATUS        current
    DESCRIPTION
        ""
    SYNTAX        Gauge32 (60..300)

CucsAdaptorIscsiProtLunBusyRetryCount ::= TEXTUAL-CONVENTION
    STATUS        current
    DESCRIPTION
        ""
    SYNTAX        Gauge32 (0..60)

CucsAdaptorLanCapDefaultVlan ::= TEXTUAL-CONVENTION
    STATUS        current
    DESCRIPTION
        ""
    SYNTAX        INTEGER
    {
        nativeVlan(1),
        defaultVlan(2)
    }

CucsAdaptorLinkState ::= TEXTUAL-CONVENTION
    STATUS        current
    DESCRIPTION
        ""
    SYNTAX        INTEGER
    {
        unknown(0),
        adminDown(1),
        down(2),
        error(3),
        up(4),
        unallocated(5),
        unavailable(6),
        offline(7)
    }

CucsAdaptorLldpCapSupport ::= TEXTUAL-CONVENTION
    STATUS        current
    DESCRIPTION
        ""
    SYNTAX        INTEGER
    {
        none(1),
        full(2)
    }

CucsAdaptorMenloBaseErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        uncorrectableErrorsDelta(4),
        uncorrectableErrorsDeltaAvg(5),
        uncorrectableErrorsDeltaMax(6),
        uncorrectableErrorsDeltaMin(7)
    }

CucsAdaptorMenloBaseErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        uncorrectableErrorsDelta(4),
        uncorrectableErrorsDeltaAvg(5),
        uncorrectableErrorsDeltaMax(6),
        uncorrectableErrorsDeltaMin(7)
    }

CucsAdaptorMenloDcePortStatsThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CucsAdaptorMenloDcePortStatsHistThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CucsAdaptorMenloEthErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        dropAclDelta(4),
        dropAclDeltaAvg(5),
        dropAclDeltaMax(6),
        dropAclDeltaMin(7),
        popErrorsDelta(8),
        popErrorsDeltaAvg(9),
        popErrorsDeltaMax(10),
        popErrorsDeltaMin(11),
        pushErrorsDelta(12),
        pushErrorsDeltaAvg(13),
        pushErrorsDeltaMax(14),
        pushErrorsDeltaMin(15),
        uncorrectableErrorsDelta(16),
        uncorrectableErrorsDeltaAvg(17),
        uncorrectableErrorsDeltaMax(18),
        uncorrectableErrorsDeltaMin(19)
    }

CucsAdaptorMenloEthErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        dropAclDelta(4),
        dropAclDeltaAvg(5),
        dropAclDeltaMax(6),
        dropAclDeltaMin(7),
        popErrorsDelta(8),
        popErrorsDeltaAvg(9),
        popErrorsDeltaMax(10),
        popErrorsDeltaMin(11),
        pushErrorsDelta(12),
        pushErrorsDeltaAvg(13),
        pushErrorsDeltaMax(14),
        pushErrorsDeltaMin(15),
        uncorrectableErrorsDelta(16),
        uncorrectableErrorsDeltaAvg(17),
        uncorrectableErrorsDeltaMax(18),
        uncorrectableErrorsDeltaMin(19)
    }

CucsAdaptorMenloEthStatsThresholded ::= TEXTUAL-CONVENTION
    STATUS        current
    DESCRIPTION
        ""
    SYNTAX        BITS
    {
        dropOverrunDelta(0),
        dropOverrunDeltaAvg(1),
        dropOverrunDeltaMax(2),
        dropOverrunDeltaMin(3),
        dropRuntDelta(4),
        dropRuntDeltaAvg(5),
        dropRuntDeltaMax(6),
        dropRuntDeltaMin(7),
        truncateOverrunDelta(8),
        truncateOverrunDeltaAvg(9),
        truncateOverrunDeltaMax(10),
        truncateOverrunDeltaMin(11)
    }

CucsAdaptorMenloEthStatsHistThresholded ::= TEXTUAL-CONVENTION
    STATUS        current
    DESCRIPTION
        ""
    SYNTAX        BITS
    {
        dropOverrunDelta(0),
        dropOverrunDeltaAvg(1),
        dropOverrunDeltaMax(2),
        dropOverrunDeltaMin(3),
        dropRuntDelta(4),
        dropRuntDeltaAvg(5),
        dropRuntDeltaMax(6),
        dropRuntDeltaMin(7),
        truncateOverrunDelta(8),
        truncateOverrunDeltaAvg(9),
        truncateOverrunDeltaMax(10),
        truncateOverrunDeltaMin(11)
    }

CucsAdaptorMenloFcErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloFcErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloFcStatsThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CucsAdaptorMenloFcStatsHistThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CucsAdaptorMenloHostPortStatsThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CucsAdaptorMenloHostPortStatsHistThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CucsAdaptorMenloMcpuErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloMcpuErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloMcpuStatsThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CucsAdaptorMenloMcpuStatsHistThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CucsAdaptorMenloNetEgStatsThresholded ::= TEXTUAL-CONVENTION
    STATUS        current
    DESCRIPTION
        ""
    SYNTAX        BITS
    {
        dropCmdDelta(0),
        dropCmdDeltaAvg(1),
        dropCmdDeltaMax(2),
        dropCmdDeltaMin(3),
        dropLifCfgInvalidDelta(4),
        dropLifCfgInvalidDeltaAvg(5),
        dropLifCfgInvalidDeltaMax(6),
        dropLifCfgInvalidDeltaMin(7),
        dropLifMapNoHitDelta(8),
        dropLifMapNoHitDeltaAvg(9),
        dropLifMapNoHitDeltaMax(10),
        dropLifMapNoHitDeltaMin(11),
        dropSrcBindDelta(12),
        dropSrcBindDeltaAvg(13),
        dropSrcBindDeltaMax(14),
        dropSrcBindDeltaMin(15),
        learnReqDropDelta(16),
        learnReqDropDeltaAvg(17),
        learnReqDropDeltaMax(18),
        learnReqDropDeltaMin(19)
    }

CucsAdaptorMenloNetEgStatsHistThresholded ::= TEXTUAL-CONVENTION
    STATUS        current
    DESCRIPTION
        ""
    SYNTAX        BITS
    {
        dropCmdDelta(0),
        dropCmdDeltaAvg(1),
        dropCmdDeltaMax(2),
        dropCmdDeltaMin(3),
        dropLifCfgInvalidDelta(4),
        dropLifCfgInvalidDeltaAvg(5),
        dropLifCfgInvalidDeltaMax(6),
        dropLifCfgInvalidDeltaMin(7),
        dropLifMapNoHitDelta(8),
        dropLifMapNoHitDeltaAvg(9),
        dropLifMapNoHitDeltaMax(10),
        dropLifMapNoHitDeltaMin(11),
        dropSrcBindDelta(12),
        dropSrcBindDeltaAvg(13),
        dropSrcBindDeltaMax(14),
        dropSrcBindDeltaMin(15),
        learnReqDropDelta(16),
        learnReqDropDeltaAvg(17),
        learnReqDropDeltaMax(18),
        learnReqDropDeltaMin(19)
    }

CucsAdaptorMenloNetInStatsThresholded ::= TEXTUAL-CONVENTION
    STATUS        current
    DESCRIPTION
        ""
    SYNTAX        BITS
    {
        dropFcLifInvalidDelta(0),
        dropFcLifInvalidDeltaAvg(1),
        dropFcLifInvalidDeltaMax(2),
        dropFcLifInvalidDeltaMin(3),
        dropFcMulticastDelta(4),
        dropFcMulticastDeltaAvg(5),
        dropFcMulticastDeltaMax(6),
        dropFcMulticastDeltaMin(7),
        dropNullPifDelta(8),
        dropNullPifDeltaAvg(9),
        dropNullPifDeltaMax(10),
        dropNullPifDeltaMin(11),
        fwdLookupNoHitDelta(12),
        fwdLookupNoHitDeltaAvg(13),
        fwdLookupNoHitDeltaMax(14),
        fwdLookupNoHitDeltaMin(15)
    }

CucsAdaptorMenloNetInStatsHistThresholded ::= TEXTUAL-CONVENTION
    STATUS        current
    DESCRIPTION
        ""
    SYNTAX        BITS
    {
        dropFcLifInvalidDelta(0),
        dropFcLifInvalidDeltaAvg(1),
        dropFcLifInvalidDeltaMax(2),
        dropFcLifInvalidDeltaMin(3),
        dropFcMulticastDelta(4),
        dropFcMulticastDeltaAvg(5),
        dropFcMulticastDeltaMax(6),
        dropFcMulticastDeltaMin(7),
        dropNullPifDelta(8),
        dropNullPifDeltaAvg(9),
        dropNullPifDeltaMax(10),
        dropNullPifDeltaMin(11),
        fwdLookupNoHitDelta(12),
        fwdLookupNoHitDeltaAvg(13),
        fwdLookupNoHitDeltaMax(14),
        fwdLookupNoHitDeltaMin(15)
    }

CucsAdaptorMenloQErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloQErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloQStatsThresholded ::= TEXTUAL-CONVENTION
    STATUS        current
    DESCRIPTION
        ""
    SYNTAX        BITS
    {
        dropOverrunN0Delta(0),
        dropOverrunN0DeltaAvg(1),
        dropOverrunN0DeltaMax(2),
        dropOverrunN0DeltaMin(3),
        dropOverrunN1Delta(4),
        dropOverrunN1DeltaAvg(5),
        dropOverrunN1DeltaMax(6),
        dropOverrunN1DeltaMin(7),
        truncateOverrunN0Delta(8),
        truncateOverrunN0DeltaAvg(9),
        truncateOverrunN0DeltaMax(10),
        truncateOverrunN0DeltaMin(11),
        truncateOverrunN1Delta(12),
        truncateOverrunN1DeltaAvg(13),
        truncateOverrunN1DeltaMax(14),
        truncateOverrunN1DeltaMin(15)
    }

CucsAdaptorMenloQStatsHistThresholded ::= TEXTUAL-CONVENTION
    STATUS        current
    DESCRIPTION
        ""
    SYNTAX        BITS
    {
        dropOverrunN0Delta(0),
        dropOverrunN0DeltaAvg(1),
        dropOverrunN0DeltaMax(2),
        dropOverrunN0DeltaMin(3),
        dropOverrunN1Delta(4),
        dropOverrunN1DeltaAvg(5),
        dropOverrunN1DeltaMax(6),
        dropOverrunN1DeltaMin(7),
        truncateOverrunN0Delta(8),
        truncateOverrunN0DeltaAvg(9),
        truncateOverrunN0DeltaMax(10),
        truncateOverrunN0DeltaMin(11),
        truncateOverrunN1Delta(12),
        truncateOverrunN1DeltaAvg(13),
        truncateOverrunN1DeltaMax(14),
        truncateOverrunN1DeltaMin(15)
    }

CucsAdaptorMenloQueueStatsComponent ::= TEXTUAL-CONVENTION
    STATUS        current
    DESCRIPTION
        ""
    SYNTAX        INTEGER
    {
        unknown(0),
        cpu(1),
        eth(2),
        fc(3),
        n(4)
    }

CucsAdaptorMenloStatsIndex ::= TEXTUAL-CONVENTION
    STATUS        current
    DESCRIPTION
        ""
    SYNTAX        INTEGER
    {
        unknown(0),
        n0(1),
        n1(2),
        n0A(3),
        n0B(4),
        n1A(5),
        n1B(6)
    }

CucsAdaptorMgmtCapMode ::= TEXTUAL-CONVENTION
    STATUS        current
    DESCRIPTION
        ""
    SYNTAX        INTEGER
    {
        full(1),
        partial(2)
    }

CucsAdaptorMgmtCapOperPowerRequirement ::= TEXTUAL-CONVENTION
    STATUS        current
    DESCRIPTION
        ""
    SYNTAX        INTEGER
    {
        none(0),
        standby(1),
        full(2)
    }

CucsAdaptorMgmtCapRebootActionOnDestructive ::= TEXTUAL-CONVENTION
    STATUS        current
    DESCRIPTION
        ""
    SYNTAX        INTEGER
    {
        none(0),
        host(1),
        adaptor(2)
    }

CucsAdaptorNICVnicStatsThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CucsAdaptorNICVnicStatsHistThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CucsAdaptorNwMgmtCapApi ::= TEXTUAL-CONVENTION
    STATUS        current
    DESCRIPTION
        ""
    SYNTAX        INTEGER
    {
        none(0),
        menlo(1),
        palo(2)
    }

CucsAdaptorNwMgmtCapMgmtTransport ::= TEXTUAL-CONVENTION
    STATUS        current
    DESCRIPTION
        ""
    SYNTAX        INTEGER
    {
        l2(0),
        l3(1)
    }

CucsAdaptorOffloadMethod ::= TEXTUAL-CONVENTION
    STATUS        current
    DESCRIPTION
        ""
    SYNTAX        INTEGER
    {
        virtual(0),
        physical(1),
        none(2)
    }

CucsAdaptorPIoEpIfType ::= TEXTUAL-CONVENTION
    STATUS        current
    DESCRIPTION
        ""
    SYNTAX        INTEGER
    {
        unknown(0),
        physical(1),
        aggregation(2),
        virtual(3)
    }

CucsAdaptorPTPAdminState ::= TEXTUAL-CONVENTION
    STATUS        current
    DESCRIPTION
        ""
    SYNTAX        INTEGER
    {
        disabled(0),
        enabled(1)
    }

CucsAdaptorProtocolProfileConnectionTimeOut ::= TEXTUAL-CONVENTION
    STATUS        current
    DESCRIPTION
        ""
    SYNTAX        Gauge32 (0..255)

CucsAdaptorProtocolProfileLunBusyRetryCount ::= TEXTUAL-CONVENTION
    STATUS        current
    DESCRIPTION
        ""
    SYNTAX        Gauge32 (0..60)

CucsAdaptorPurpose ::= TEXTUAL-CONVENTION
    STATUS        current
    DESCRIPTION
        ""
    SYNTAX        INTEGER
    {
        unused(0),
        general(1),
        management(2),
        utility(3),
        crosslink(4),
        overlay(5)
    }

CucsAdaptorReachability ::= TEXTUAL-CONVENTION
    STATUS        current
    DESCRIPTION
        ""
    SYNTAX        BITS
    {
        a(0),
        b(1),
        unmanaged(7)
    }

CucsAdaptorRnicCapSpecType ::= TEXTUAL-CONVENTION
    STATUS        current
    DESCRIPTION
        ""
    SYNTAX        INTEGER
    {
        virtualizedEthIf(1),
        virtualizedFcIf(2),
        virtualizedScsiIf(3),
        nonVirtualizedEthIf(4),
        nonVirtualizedFcIf(5),
        fcoe(6),
        protectedEthIf(7),
        protectedFcIf(8),
        protectedFcoe(9),
        pathEncapVirtual(10),
        pathEncapConsolidated(11),
        uplinkAggregation(12),
        virtualizedEthSriov(13),
        virtualizedFcSriov(14),
        virtualizedEthSriovUsnic(15),
        virtualizedEthVmq(16),
        ethFlowMonitoringNetflow(17),
        ethRoce(18),
        ethVxlan(19),
        ethNvgre(20),
        cdnSupport(21),
        ethNvgreVmq(22),
        virtualizedCeEthIf(23),
        pathEncapVirtualCe(24),
        oracleRacSupport(25),
        virtualizedEthVmmq(27),
        ethVxlanVmq(28),
        ethRoceV2(29),
        ethVxlanRocev2(30),
        ethNvgreRocev2(31),
        ethPtp(32)
    }

CucsAdaptorRssProfileReceiveSideScaling ::= TEXTUAL-CONVENTION
    STATUS        current
    DESCRIPTION
        ""
    SYNTAX        INTEGER
    {
        disabled(0),
        enabled(1)
    }

CucsAdaptorSanCapHostNvram ::= TEXTUAL-CONVENTION
    STATUS        current
    DESCRIPTION
        ""
    SYNTAX        INTEGER
    {
        none(1),
        full(2)
    }

CucsAdaptorSwAutoNegType ::= TEXTUAL-CONVENTION
    STATUS        current
    DESCRIPTION
        ""
    SYNTAX        INTEGER
    {
        on(0),
        off(1),
        n25g(2)
    }

CucsAdaptorUnitErrorCode ::= TEXTUAL-CONVENTION
    STATUS        current
    DESCRIPTION
        ""
    SYNTAX        INTEGER
    {
        noError(0),
        pcieUnstableLink(1),
        asicFatalError(2),
        fcpuError(3),
        lowMemory(4)
    }

CucsAdaptorUnitFaultValue ::= TEXTUAL-CONVENTION
    STATUS        current
    DESCRIPTION
        ""
    SYNTAX        BITS
    {
        communicationErrors(0),
        counterfeit(1),
        secureBootFail(2),
        backupImage(3),
        fwValidationFailed(4),
        altImage(5),
        diagImage(6),
        notRelKeySigned(7),
        upgradableCountLow(8),
        upgradableCountZero(9)
    }

CucsAdaptorUnitId ::= TEXTUAL-CONVENTION
    STATUS        current
    DESCRIPTION
        ""
    SYNTAX        Gauge32 (1..8)

CucsAdaptorUnitVisibility ::= TEXTUAL-CONVENTION
    STATUS        current
    DESCRIPTION
        ""
    SYNTAX        INTEGER
    {
        visible(0),
        notVisible(1)
    }

CucsAdaptorUnitExtnId ::= TEXTUAL-CONVENTION
    STATUS        current
    DESCRIPTION
        ""
    SYNTAX        Gauge32 (1..5000)

CucsAdaptorVhbaType ::= TEXTUAL-CONVENTION
    STATUS        current
    DESCRIPTION
        ""
    SYNTAX        INTEGER
    {
        fcInitiator(1),
        fcTarget(2),
        fcNvmeInitiator(3),
        fcNvmeTarget(4)
    }

CucsAdaptorVnicStatsThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CucsAdaptorVnicStatsHistThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CucsAdaptorComparisonOper ::= TEXTUAL-CONVENTION
    STATUS        current
    DESCRIPTION
        ""
    SYNTAX        INTEGER
    {
        none(0),
        gt(1),
        lt(2),
        range(3)
    }

CucsAddressMACMask ::= TEXTUAL-CONVENTION
    STATUS        current
    DESCRIPTION
        ""
    SYNTAX        Counter64

CucsAddressType ::= TEXTUAL-CONVENTION
    STATUS        current
    DESCRIPTION
        ""
    SYNTAX        INTEGER
    {
        unknown(0),
        operational(1),
        floating(2)
    }

CucsAddressUIDSuffxMask ::= TEXTUAL-CONVENTION
    STATUS        current
    DESCRIPTION
        ""
    SYNTAX        Counter64

CucsAddressWWNMask ::= TEXTUAL-CONVENTION
    STATUS        current
    DESCRIPTION
        ""
    SYNTAX        Counter64

CucsBiosBootDevErrorCode ::= TEXTUAL-CONVENTION
    STATUS        current
    DESCRIPTION
        ""
    SYNTAX        INTEGER
    {
        success(0),
        failure(1)
    }

CucsBiosBootDevGrpType ::= TEXTUAL-CONVENTION
    STATUS        current
    DESCRIPTION
        ""
    SYNTAX        INTEGER
    {
        systemBootOrder(0),
        fddOrder(1),
        hddOrder(2),
        cdOrder(3),
        networkDeviceOrder(6),
        internalEfiShell(16),
        unknownDeviceOrder(99),
        localStorageAnyDeviceOrder(100),
        sanDeviceOrder(101),
        sanAnyDeviceOrder(102),
        internalUsbDeviceOrder(103),
        externalUsbDeviceOrder(104),
        sdcardDeviceOrder(105),
        lanAnyDeviceOrder(106),
        uefiTargetDeviceOrder(107),
        iscsiDeviceOrder(108),
        iscsiAnyDeviceOrder(109),
        cimcVmediaCddDeviceOrder(110),
        cimcVmediaHddDeviceOrder(111),
        cimcVmediaFddDeviceOrder(112),
        kvmVmediaCddDeviceOrder(113),
        kvmVmediaHddDeviceOrder(114),
        kvmVmediaFddDeviceOrder(115),
        uefiShellDeviceOrder(116),
        nvmeDeviceOrder(117),
        nvmeDiskSsdDeviceOrder(118),
        nvmePciSsdDeviceOrder(119),
        bevOrder(128)
    }

CucsBiosBootDevOrder ::= TEXTUAL-CONVENTION
    STATUS        current
    DESCRIPTION
        ""
    SYNTAX        INTEGER
    {
        n1(1),
        n2(2),
        n3(3),
        n4(4),
        n5(5),
        n6(6),
        n7(7)
    }

CucsBiosDefaultAction ::= TEXTUAL-CONVENTION
    STATUS        current
    DESCRIPTION
        ""
    SYNTAX        INTEGER
    {
        no(0),
        yes(1)
    }

CucsBiosSupportedAction ::= TEXTUAL-CONVENTION
    STATUS        current
    DESCRIPTION
        ""
    SYNTAX        INTEGER
    {
        no(0),
        yes(1)
    }

CucsBiosVfACPI10SupportVpACPI10Support ::= TEXTUAL-CONVENTION
    STATUS        current
    DESCRIPTION
        ""
    SYNTAX        INTEGER
    {
        platformRecommended(0),
        disabled(122),
        enabled(123),
        platformDefault(-2)
    }

CucsBiosVfASPMSupportVpASPMSupport ::= TEXTUAL-CONVENTION
    STATUS        current
    DESCRIPTION
        ""
    SYNTAX        INTEGER
    {
        platformRecommended(0),
        disabled(508),
        auto(509),
        forcel0(510)
    }

CucsBiosVfAllUSBDevicesVpAllUSBDevices ::= TEXTUAL-CONVENTION
    STATUS        current
    DESCRIPTION
        ""
    SYNTAX        INTEGER
    {
        platformRecommended(0),
        disabled(389),
        enabled(390)
    }

CucsBiosVfAltitudeVpAltitude ::= TEXTUAL-CONVENTION
    STATUS        current
    DESCRIPTION
        ""
    SYNTAX        INTEGER
    {
        platformRecommended(0),
        auto(482),
        n300M(483),
        n900M(484),
        n1500M(485),
        n3000M(486)
    }

CucsBiosVfAssertNMIOnPERRVpAssertNMIOnPERR ::= TEXTUAL-CONVENTION
    STATUS        current
    DESCRIPTION
        ""
    SYNTAX        INTEGER
    {
        platformRecommended(0),
        disabled(68),
        enabled(69),
        platformDefault(-2)
    }

CucsBiosVfAssertNMIOnSERRVpAssertNMIOnSERR ::= TEXTUAL-CONVENTION
    STATUS        current
    DESCRIPTION
        ""
    SYNTAX        INTEGER
    {
        platformRecommended(0),
        disabled(66),
        enabled(67),
        platformDefault(-2)
    }

CucsBiosVfBMEDMAMitigationVpBMEDMAMitigation ::= TEXTUAL-CONVENTION
    STATUS        current
    DESCRIPTION
        ""
    SYNTAX        INTEGER
    {
        platformRecommended(0),
        disabled(610),
        enabled(611)
    }

CucsBiosVfBootOptionRetryVpBootOptionRetry ::= TEXTUAL-CONVENTION
    STATUS        current
    DESCRIPTION
        ""
    SYNTAX        INTEGER
    {
        platformRecommended(0),
        disabled(96),
        enabled(97),
        platformDefault(-2)
    }

CucsBiosVfCPUHardwarePowerManagementVpCPUHardwarePowerManagement ::= TEXTUAL-CONVENTION
    STATUS        current
    DESCRIPTION
        ""
    SYNTAX        INTEGER
    {
        platformRecommended(0),
        disabled(409),
        hwpmNativeMode(410),
        hwpmOobMode(411)
    }

CucsBiosVfCPUPerformanceVpCPUPerformance ::= TEXTUAL-CONVENTION
    STATUS        current
    DESCRIPTION
        ""
    SYNTAX        INTEGER
    {
        platformRecommended(0),
        enterprise(175),
        highThroughput(176),
        hpc(177),
        custom(490),
        platformDefault(-2)
    }

CucsBiosVfCPUPowerManagementVpCPUPowerManagement ::= TEXTUAL-CONVENTION
    STATUS        current
    DESCRIPTION
        ""
    SYNTAX        INTEGER
    {
        platformRecommended(0),
        performance(414),
        disabled(491),
        energyEfficient(492),
        custom(493)
    }

CucsBiosVfConsistentDeviceNameControlVpCDNControl ::= TEXTUAL-CONVENTION
    STATUS        current
    DESCRIPTION
        ""
    SYNTAX        INTEGER
    {
        platformRecommended(0),
        disabled(530),
        enabled(531)
    }

CucsBiosVfConsoleRedirectionVpBaudRate ::= TEXTUAL-CONVENTION
    STATUS        current
    DESCRIPTION
        ""
    SYNTAX        INTEGER
    {
        platformRecommended(0),
        n9600(131),
        n19200(132),
        n38400(133),
        n57600(134),
        n115200(135),
        platformDefault(-2)
    }

CucsBiosVfConsoleRedirectionVpConsoleRedirection ::= TEXTUAL-CONVENTION
    STATUS        current
    DESCRIPTION
        ""
    SYNTAX        INTEGER
    {
        platformRecommended(0),
        disabled(77),
        serialPortA(78),
        serialPortB(130),
        enabled(260),
        com0(261),
        com1(560),
        platformDefault(-2)
    }

CucsBiosVfConsoleRedirectionVpFlowControl ::= TEXTUAL-CONVENTION
    STATUS        current
    DESCRIPTION
        ""
    SYNTAX        INTEGER
    {
        platformRecommended(0),
        none(79),
        rtsCts(80),
        platformDefault(-2)
    }

CucsBiosVfConsoleRedirectionVpLegacyOSRedirection ::= TEXTUAL-CONVENTION
    STATUS        current
    DESCRIPTION
        ""
    SYNTAX        INTEGER
    {
        platformRecommended(0),
        disabled(90),
        enabled(91),
        n80x24(500),
        n80x25(501),
        platformDefault(-2)
    }

CucsBiosVfConsoleRedirectionVpPuttyKeyPad ::= TEXTUAL-CONVENTION
    STATUS        current
    DESCRIPTION
        ""
    SYNTAX        INTEGER
    {
        platformRecommended(0),
        vt100(311),
        linux(312),
        xtermr6(313),
        sco(314),
        escn(315),
        vt400(316)
    }

CucsBiosVfConsoleRedirectionVpTerminalType ::= TEXTUAL-CONVENTION
    STATUS        current
    DESCRIPTION
        ""
    SYNTAX        INTEGER
    {
        platformRecommended(0),
        pcAnsi(86),
        vt100(87),
        vt100Plus(88),
        vtUtf8(89),
        platformDefault(-2)
    }

CucsBiosVfCoreMultiProcessingVpCoreMultiProcessing ::= TEXTUAL-CONVENTION
    STATUS        current
    DESCRIPTION
        ""
    SYNTAX        INTEGER
    {
        platformRecommended(0),
        all(170),
        n1(178),
        n2(179),
        n3(180),
        n4(181),
        n5(182),
        n6(183),
        n7(184),
        n8(185),
        n9(190),
        n10(191),
        n11(274),
        n12(275),
        n13(294),
        n14(295),
        n15(296),
        n16(440),
        n17(441),
        n18(442),
        n19(551),
        n20(552),
        n21(553),
        n22(554),
        n23(557),
        n24(558),
        platformDefault(-2)
    }

CucsBiosVfDDR3VoltageSelectionVpDDR3VoltageSelection ::= TEXTUAL-CONVENTION
    STATUS        current
    DESCRIPTION
        ""
    SYNTAX        INTEGER
    {
        platformRecommended(0),
        ddr31500mv(511),
        ddr31350mv(512)
    }

CucsBiosVfDRAMClockThrottlingVpDRAMClockThrottling ::= TEXTUAL-CONVENTION
    STATUS        current
    DESCRIPTION
        ""
    SYNTAX        INTEGER
    {
        platformRecommended(0),
        auto(435),
        balanced(436),
        performance(437),
        energyEfficient(438)
    }

CucsBiosVfDirectCacheAccessVpDirectCacheAccess ::= TEXTUAL-CONVENTION
    STATUS        current
    DESCRIPTION
        ""
    SYNTAX        INTEGER
    {
        platformRecommended(0),
        disabled(28),
        enabled(29),
        auto(559),
        platformDefault(-2)
    }

CucsBiosVfDramRefreshRateVpDramRefreshRate ::= TEXTUAL-CONVENTION
    STATUS        current
    DESCRIPTION
        ""
    SYNTAX        INTEGER
    {
        platformRecommended(0),
        n1x(262),
        n2x(263),
        n3x(264),
        n4x(265),
        auto(270)
    }

CucsBiosVfEnergyPerformanceTuningVpPwrPerfTuning ::= TEXTUAL-CONVENTION
    STATUS        current
    DESCRIPTION
        ""
    SYNTAX        INTEGER
    {
        platformRecommended(0),
        os(568),
        bios(569)
    }

CucsBiosVfEnhancedIntelSpeedStepTechVpEnhancedIntelSpeedStepTech ::= TEXTUAL-CONVENTION
    STATUS        current
    DESCRIPTION
        ""
    SYNTAX        INTEGER
    {
        platformRecommended(0),
        disabled(3),
        enabled(4),
        platformDefault(-2)
    }

CucsBiosVfEnhancedPowerCappingSupportVpEnhancedPowerCapping ::= TEXTUAL-CONVENTION
    STATUS        current
    DESCRIPTION
        ""
    SYNTAX        INTEGER
    {
        platformRecommended(0),
        disabled(495),
        enabled(496)
    }

CucsBiosVfExecuteDisableBitVpExecuteDisableBit ::= TEXTUAL-CONVENTION
    STATUS        current
    DESCRIPTION
        ""
    SYNTAX        INTEGER
    {
        platformRecommended(0),
        disabled(10),
        enabled(11),
        platformDefault(-2)
    }

CucsBiosVfFRB2TimerVpFRB2Timer ::= TEXTUAL-CONVENTION
    STATUS        current
    DESCRIPTION
        ""
    SYNTAX        INTEGER
    {
        platformRecommended(0),
        disabled(420),
        enabled(421)
    }

CucsBiosVfFrequencyFloorOverrideVpFrequencyFloorOverride ::= TEXTUAL-CONVENTION
    STATUS        current
    DESCRIPTION
        ""
    SYNTAX        INTEGER
    {
        platformRecommended(0),
        disabled(430),
        enabled(431)
    }

CucsBiosVfFrontPanelLockoutVpFrontPanelLockout ::= TEXTUAL-CONVENTION
    STATUS        current
    DESCRIPTION
        ""
    SYNTAX        INTEGER
    {
        platformRecommended(0),
        disabled(60),
        enabled(61),
        platformDefault(-2)
    }

CucsBiosVfIOEMezz1OptionROMVpIOEMezz1OptionROM ::= TEXTUAL-CONVENTION
    STATUS        current
    DESCRIPTION
        ""
    SYNTAX        INTEGER
    {
        platformRecommended(0),
        disabled(588),
        enabled(589),
        uefiOnly(590),
        legacyOnly(591)
    }

CucsBiosVfIOENVMe1OptionROMVpIOENVMe1OptionROM ::= TEXTUAL-CONVENTION
    STATUS        current
    DESCRIPTION
        ""
    SYNTAX        INTEGER
    {
        platformRecommended(0),
        disabled(596),
        enabled(597),
        uefiOnly(598),
        legacyOnly(599)
    }

CucsBiosVfIOENVMe2OptionROMVpIOENVMe2OptionROM ::= TEXTUAL-CONVENTION
    STATUS        current
    DESCRIPTION
        ""
    SYNTAX        INTEGER
    {
        platformRecommended(0),
        disabled(600),
        enabled(601),
        uefiOnly(602),
        legacyOnly(603)
    }

CucsBiosVfIOESlot1OptionROMVpIOESlot1OptionROM ::= TEXTUAL-CONVENTION
    STATUS        current
    DESCRIPTION
        ""
    SYNTAX        INTEGER
    {
        platformRecommended(0),
        disabled(584),
        enabled(585),
        uefiOnly(586),
        legacyOnly(587)
    }

CucsBiosVfIOESlot2OptionROMVpIOESlot2OptionROM ::= TEXTUAL-CONVENTION
    STATUS        current
    DESCRIPTION
        ""
    SYNTAX        INTEGER
    {
        platformRecommended(0),
        disabled(592),
        enabled(593),
        uefiOnly(594),
        legacyOnly(595)
    }

CucsBiosVfIntegratedGraphicsVpIntegratedGraphics ::= TEXTUAL-CONVENTION
    STATUS        current
    DESCRIPTION
        ""
    SYNTAX        INTEGER
    {
        platformRecommended(0),
        disabled(399),
        enabled(400)
    }

CucsBiosVfIntegratedGraphicsApertureSizeVpIntgtGraphApertureSize ::= TEXTUAL-CONVENTION
    STATUS        current
    DESCRIPTION
        ""
    SYNTAX        INTEGER
    {
        platformRecommended(0),
        n128mb(401),
        n256mb(402),
        n512mb(403),
        n1024mb(404),
        n2048mb(405),
        n4096mb(406)
    }

CucsBiosVfIntelEntrySASRAIDModuleVpSASRAID ::= TEXTUAL-CONVENTION
    STATUS        current
    DESCRIPTION
        ""
    SYNTAX        INTEGER
    {
        platformRecommended(0),
        disabled(154),
        enabled(155),
        platformDefault(-2)
    }

CucsBiosVfIntelEntrySASRAIDModuleVpSASRAIDModule ::= TEXTUAL-CONVENTION
    STATUS        current
    DESCRIPTION
        ""
    SYNTAX        INTEGER
    {
        platformRecommended(0),
        itIrRaid(156),
        intelEsrtii(157),
        platformDefault(-2)
    }

CucsBiosVfIntelHyperThreadingTechVpIntelHyperThreadingTech ::= TEXTUAL-CONVENTION
    STATUS        current
    DESCRIPTION
        ""
    SYNTAX        INTEGER
    {
        platformRecommended(0),
        disabled(5),
        enabled(6),
        platformDefault(-2)
    }

CucsBiosVfIntelTrustedExecutionTechnologyVpIntelTstdExecTechSup ::= TEXTUAL-CONVENTION
    STATUS        current
    DESCRIPTION
        ""
    SYNTAX        INTEGER
    {
        platformRecommended(0),
        disabled(515),
        enabled(516)
    }

CucsBiosVfIntelTurboBoostTechVpIntelTurboBoostTech ::= TEXTUAL-CONVENTION
    STATUS        current
    DESCRIPTION
        ""
    SYNTAX        INTEGER
    {
        platformRecommended(0),
        disabled(1),
        enabled(2),
        platformDefault(-2)
    }

CucsBiosVfIntelVTForDirectedIOVpIntelVTDATSSupport ::= TEXTUAL-CONVENTION
    STATUS        current
    DESCRIPTION
        ""
    SYNTAX        INTEGER
    {
        platformRecommended(0),
        disabled(20),
        enabled(21),
        platformDefault(-2)
    }

CucsBiosVfIntelVTForDirectedIOVpIntelVTDCoherencySupport ::= TEXTUAL-CONVENTION
    STATUS        current
    DESCRIPTION
        ""
    SYNTAX        INTEGER
    {
        platformRecommended(0),
        disabled(18),
        enabled(19),
        platformDefault(-2)
    }

CucsBiosVfIntelVTForDirectedIOVpIntelVTDInterruptRemapping ::= TEXTUAL-CONVENTION
    STATUS        current
    DESCRIPTION
        ""
    SYNTAX        INTEGER
    {
        platformRecommended(0),
        disabled(16),
        enabled(17),
        platformDefault(-2)
    }

CucsBiosVfIntelVTForDirectedIOVpIntelVTDPassThroughDMASupport ::= TEXTUAL-CONVENTION
    STATUS        current
    DESCRIPTION
        ""
    SYNTAX        INTEGER
    {
        platformRecommended(0),
        disabled(22),
        enabled(23),
        platformDefault(-2)
    }

CucsBiosVfIntelVTForDirectedIOVpIntelVTForDirectedIO ::= TEXTUAL-CONVENTION
    STATUS        current
    DESCRIPTION
        ""
    SYNTAX        INTEGER
    {
        platformRecommended(0),
        disabled(14),
        enabled(15),
        platformDefault(-2)
    }

CucsBiosVpIntelVirtualizationTechnology ::= TEXTUAL-CONVENTION
    STATUS        current
    DESCRIPTION
        ""
    SYNTAX        INTEGER
    {
        platformRecommended(0),
        disabled(12),
        enabled(13),
        platformDefault(-2)
    }

CucsBiosVfInterleaveConfigurationVpChannelInterleaving ::= TEXTUAL-CONVENTION
    STATUS        current
    DESCRIPTION
        ""
    SYNTAX        INTEGER
    {
        platformRecommended(0),
        auto(301),
        n1Way(302),
        n2Way(303),
        n3Way(304),
        n4Way(305)
    }

CucsBiosVfInterleaveConfigurationVpMemoryInterleaving ::= TEXTUAL-CONVENTION
    STATUS        current
    DESCRIPTION
        ""
    SYNTAX        INTEGER
    {
        platformRecommended(0),
        numa1WayNodeInterleave(297),
        n2WayNodeInterleave(298),
        n4WayNodeInterleave(299),
        n8WayInterleavingInterSocket(300)
    }

CucsBiosVfInterleaveConfigurationVpRankInterleaving ::= TEXTUAL-CONVENTION
    STATUS        current
    DESCRIPTION
        ""
    SYNTAX        INTEGER
    {
        platformRecommended(0),
        auto(306),
        n1Way(307),
        n2Way(308),
        n4Way(309),
        n8Way(310)
    }

CucsBiosVfLOMPortsConfigurationVpAllOnboardLOMPorts ::= TEXTUAL-CONVENTION
    STATUS        current
    DESCRIPTION
        ""
    SYNTAX        INTEGER
    {
        platformRecommended(0),
        disabled(371),
        enabled(372)
    }

CucsBiosVfLOMPortsConfigurationVpLOMPort0OptionROM ::= TEXTUAL-CONVENTION
    STATUS        current
    DESCRIPTION
        ""
    SYNTAX        INTEGER
    {
        platformRecommended(0),
        disabled(373),
        enabled(374),
        uefiOnly(375),
        legacyOnly(376)
    }

CucsBiosVfLOMPortsConfigurationVpLOMPort1OptionROM ::= TEXTUAL-CONVENTION
    STATUS        current
    DESCRIPTION
        ""
    SYNTAX        INTEGER
    {
        platformRecommended(0),
        disabled(377),
        enabled(378),
        uefiOnly(379),
        legacyOnly(380)
    }

CucsBiosVfLOMPortsConfigurationVpLOMPort2OptionROM ::= TEXTUAL-CONVENTION
    STATUS        current
    DESCRIPTION
        ""
    SYNTAX        INTEGER
    {
        platformRecommended(0),
        disabled(381),
        enabled(382),
        uefiOnly(383),
        legacyOnly(384)
    }

CucsBiosVfLOMPortsConfigurationVpLOMPort3OptionROM ::= TEXTUAL-CONVENTION
    STATUS        current
    DESCRIPTION
        ""
    SYNTAX        INTEGER
    {
        platformRecommended(0),
        disabled(385),
        enabled(386),
        uefiOnly(387),
        legacyOnly(388)
    }

CucsBiosVfLocalX2ApicVpLocalX2Apic ::= TEXTUAL-CONVENTION
    STATUS        current
    DESCRIPTION
        ""
    SYNTAX        INTEGER
    {
        platformRecommended(0),
        xapic(271),
        x2apic(272),
        auto(273)
    }

CucsBiosVfLvDIMMSupportVpLvDDRMode ::= TEXTUAL-CONVENTION
    STATUS        current
    DESCRIPTION
        ""
    SYNTAX        INTEGER
    {
        platformRecommended(0),
        powerSavingMode(138),
        performanceMode(139),
        auto(443),
        platformDefault(-2)
    }

CucsBiosVfMaxVariableMTRRSettingVpProcessorMtrr ::= TEXTUAL-CONVENTION
    STATUS        current
    DESCRIPTION
        ""
    SYNTAX        INTEGER
    {
        platformRecommended(0),
        autoMax(192),
        n8(193),
        platformDefault(-2)
    }

CucsBiosVfMaximumMemoryBelow4GBVpMaximumMemoryBelow4GB ::= TEXTUAL-CONVENTION
    STATUS        current
    DESCRIPTION
        ""
    SYNTAX        INTEGER
    {
        platformRecommended(0),
        disabled(54),
        enabled(55),
        platformDefault(-2)
    }

CucsBiosVfMemoryMappedIOAbove4GBVpMemoryMappedIOAbove4GB ::= TEXTUAL-CONVENTION
    STATUS        current
    DESCRIPTION
        ""
    SYNTAX        INTEGER
    {
        platformRecommended(0),
        disabled(56),
        enabled(57),
        platformDefault(-2)
    }

CucsBiosVfMirroringModeVpMirroringMode ::= TEXTUAL-CONVENTION
    STATUS        current
    DESCRIPTION
        ""
    SYNTAX        INTEGER
    {
        platformRecommended(0),
        interSocket(142),
        intraSocket(143),
        platformDefault(-2)
    }

CucsBiosVfNUMAOptimizedVpNUMAOptimized ::= TEXTUAL-CONVENTION
    STATUS        current
    DESCRIPTION
        ""
    SYNTAX        INTEGER
    {
        platformRecommended(0),
        disabled(32),
        enabled(33),
        platformDefault(-2)
    }

CucsBiosVfOSBootWatchdogTimerVpOSBootWatchdogTimer ::= TEXTUAL-CONVENTION
    STATUS        current
    DESCRIPTION
        ""
    SYNTAX        INTEGER
    {
        platformRecommended(0),
        disabled(114),
        enabled(115),
        platformDefault(-2)
    }

CucsBiosVfOSBootWatchdogTimerPolicyVpOSBootWatchdogTimerPolicy ::= TEXTUAL-CONVENTION
    STATUS        current
    DESCRIPTION
        ""
    SYNTAX        INTEGER
    {
        platformRecommended(0),
        powerOff(116),
        reset(162),
        platformDefault(-2)
    }

CucsBiosVfOSBootWatchdogTimerTimeOutVpOSBootWatchdogTimerPolicy ::= TEXTUAL-CONVENTION
    STATUS        current
    DESCRIPTION
        ""
    SYNTAX        INTEGER
    {
        platformRecommended(0),
        n5Minutes(171),
        n10Minutes(172),
        n15Minutes(173),
        n20Minutes(174),
        platformDefault(-2)
    }

CucsBiosVfOSBootWatchdogTimerTimeoutVpOSBootWatchdogTimerTimeout ::= TEXTUAL-CONVENTION
    STATUS        current
    DESCRIPTION
        ""
    SYNTAX        INTEGER
    {
        platformRecommended(0),
        n5Minutes(254),
        n10Minutes(255),
        n15Minutes(256),
        n20Minutes(257),
        platformDefault(-2)
    }

CucsBiosVfOnboardGraphicsVpOnboardGraphics ::= TEXTUAL-CONVENTION
    STATUS        current
    DESCRIPTION
        ""
    SYNTAX        INTEGER
    {
        platformRecommended(0),
        disabled(407),
        enabled(408)
    }

CucsBiosVfOnboardSATAControllerVpOnboardSATAController ::= TEXTUAL-CONVENTION
    STATUS        current
    DESCRIPTION
        ""
    SYNTAX        INTEGER
    {
        platformRecommended(0),
        disabled(38),
        enabled(39),
        platformDefault(-2)
    }

CucsBiosVfOnboardSATAControllerVpSATAMode ::= TEXTUAL-CONVENTION
    STATUS        current
    DESCRIPTION
        ""
    SYNTAX        INTEGER
    {
        platformRecommended(0),
        enhanced(40),
        compatibility(41),
        ahci(42),
        swRaid(186),
        platformDefault(-2)
    }

CucsBiosVfOnboardStorageVpOnboardSCUStorageSupport ::= TEXTUAL-CONVENTION
    STATUS        current
    DESCRIPTION
        ""
    SYNTAX        INTEGER
    {
        platformRecommended(0),
        disabled(252),
        enabled(253),
        platformDefault(-2)
    }

CucsBiosVfOptionROMEnableVpState ::= TEXTUAL-CONVENTION
    STATUS        current
    DESCRIPTION
        ""
    SYNTAX        INTEGER
    {
        platformRecommended(0),
        disabled(208),
        enabled(209),
        uefiOnly(443),
        legacyOnly(444),
        platformDefault(-2)
    }

CucsBiosVfOptionROMLoadVpLoad ::= TEXTUAL-CONVENTION
    STATUS        current
    DESCRIPTION
        ""
    SYNTAX        INTEGER
    {
        platformRecommended(0),
        enable(163),
        disable(164),
        enabled(187),
        disabled(188),
        platformDefault(-2)
    }

CucsBiosVfOutOfBandManagementVpComSpcrEnable ::= TEXTUAL-CONVENTION
    STATUS        current
    DESCRIPTION
        ""
    SYNTAX        INTEGER
    {
        platformRecommended(0),
        disabled(564),
        enabled(565)
    }

CucsBiosVfPCHSATAModeVpPCHSATAMode ::= TEXTUAL-CONVENTION
    STATUS        current
    DESCRIPTION
        ""
    SYNTAX        INTEGER
    {
        platformRecommended(0),
        ahci(497),
        disabled(498),
        lsiSwRaid(499)
    }

CucsBiosVfPCHSATAModeVpSATAMode ::= TEXTUAL-CONVENTION
    STATUS        current
    DESCRIPTION
        ""
    SYNTAX        INTEGER
    {
        platformRecommended(0),
        ahci(532),
        disabled(533),
        lsiSwRaid(534)
    }

CucsBiosVfPCILOMPortsConfigurationVpPCIe10GLOM2Link ::= TEXTUAL-CONVENTION
    STATUS        current
    DESCRIPTION
        ""
    SYNTAX        INTEGER
    {
        platformRecommended(0),
        enabled(528),
        disabled(529)
    }

CucsBiosVfPCIROMCLPVpPCIROMCLP ::= TEXTUAL-CONVENTION
    STATUS        current
    DESCRIPTION
        ""
    SYNTAX        INTEGER
    {
        platformRecommended(0),
        disabled(570),
        enabled(571)
    }

CucsBiosVfPCISlotLinkSpeedVpPCIeSlot10LinkSpeed ::= TEXTUAL-CONVENTION
    STATUS        current
    DESCRIPTION
        ""
    SYNTAX        INTEGER
    {
        platformRecommended(0),
        gen1(366),
        gen2(367),
        gen3(368),
        auto(369),
        disabled(370)
    }

CucsBiosVfPCISlotLinkSpeedVpPCIeSlot1LinkSpeed ::= TEXTUAL-CONVENTION
    STATUS        current
    DESCRIPTION
        ""
    SYNTAX        INTEGER
    {
        platformRecommended(0),
        gen1(321),
        gen2(322),
        gen3(323),
        auto(324),
        disabled(325)
    }

CucsBiosVfPCISlotLinkSpeedVpPCIeSlot2LinkSpeed ::= TEXTUAL-CONVENTION
    STATUS        current
    DESCRIPTION
        ""
    SYNTAX        INTEGER
    {
        platformRecommended(0),
        gen1(326),
        gen2(327),
        gen3(328),
        auto(329),
        disabled(330)
    }

CucsBiosVfPCISlotLinkSpeedVpPCIeSlot3LinkSpeed ::= TEXTUAL-CONVENTION
    STATUS        current
    DESCRIPTION
        ""
    SYNTAX        INTEGER
    {
        platformRecommended(0),
        gen1(331),
        gen2(332),
        gen3(333),
        auto(334),
        disabled(335)
    }

CucsBiosVfPCISlotLinkSpeedVpPCIeSlot4LinkSpeed ::= TEXTUAL-CONVENTION
    STATUS        current
    DESCRIPTION
        ""
    SYNTAX        INTEGER
    {
        platformRecommended(0),
        gen1(336),
        gen2(337),
        gen3(338),
        auto(339),
        disabled(340)
    }

CucsBiosVfPCISlotLinkSpeedVpPCIeSlot5LinkSpeed ::= TEXTUAL-CONVENTION
    STATUS        current
    DESCRIPTION
        ""
    SYNTAX        INTEGER
    {
        platformRecommended(0),
        gen1(341),
        gen2(342),
        gen3(343),
        auto(344),
        disabled(345)
    }

CucsBiosVfPCISlotLinkSpeedVpPCIeSlot6LinkSpeed ::= TEXTUAL-CONVENTION
    STATUS        current
    DESCRIPTION
        ""
    SYNTAX        INTEGER
    {
        platformRecommended(0),
        gen1(346),
        gen2(347),
        gen3(348),
        auto(349),
        disabled(350)
    }

CucsBiosVfPCISlotLinkSpeedVpPCIeSlot7LinkSpeed ::= TEXTUAL-CONVENTION
    STATUS        current
    DESCRIPTION
        ""
    SYNTAX        INTEGER
    {
        platformRecommended(0),
        gen1(351),
        gen2(352),
        gen3(353),
        auto(354),
        disabled(355)
    }

CucsBiosVfPCISlotLinkSpeedVpPCIeSlot8LinkSpeed ::= TEXTUAL-CONVENTION
    STATUS        current
    DESCRIPTION
        ""
    SYNTAX        INTEGER
    {
        platformRecommended(0),
        gen1(356),
        gen2(357),
        gen3(358),
        auto(359),
        disabled(360)
    }

CucsBiosVfPCISlotLinkSpeedVpPCIeSlot9LinkSpeed ::= TEXTUAL-CONVENTION
    STATUS        current
    DESCRIPTION
        ""
    SYNTAX        INTEGER
    {
        platformRecommended(0),
        gen1(361),
        gen2(362),
        gen3(363),
        auto(364),
        disabled(365)
    }

CucsBiosVfPCISlotOptionROMEnableVpPCIeSlotHBAOptionROM ::= TEXTUAL-CONVENTION
    STATUS        current
    DESCRIPTION
        ""
    SYNTAX        INTEGER
    {
        platformRecommended(0),
        disabled(463),
        enabled(464),
        uefiOnly(465),
        legacyOnly(466)
    }

CucsBiosVfPCISlotOptionROMEnableVpPCIeSlotMLOMOptionROM ::= TEXTUAL-CONVENTION
    STATUS        current
    DESCRIPTION
        ""
    SYNTAX        INTEGER
    {
        platformRecommended(0),
        disabled(459),
        enabled(460),
        uefiOnly(461),
        legacyOnly(462)
    }

CucsBiosVfPCISlotOptionROMEnableVpPCIeSlotN1OptionROM ::= TEXTUAL-CONVENTION
    STATUS        current
    DESCRIPTION
        ""
    SYNTAX        INTEGER
    {
        platformRecommended(0),
        disabled(467),
        enabled(468),
        uefiOnly(469),
        legacyOnly(470)
    }

CucsBiosVfPCISlotOptionROMEnableVpPCIeSlotN2OptionROM ::= TEXTUAL-CONVENTION
    STATUS        current
    DESCRIPTION
        ""
    SYNTAX        INTEGER
    {
        platformRecommended(0),
        disabled(471),
        enabled(472),
        uefiOnly(473),
        legacyOnly(474)
    }

CucsBiosVfPCISlotOptionROMEnableVpPCIeSlotSASOptionROM ::= TEXTUAL-CONVENTION
    STATUS        current
    DESCRIPTION
        ""
    SYNTAX        INTEGER
    {
        platformRecommended(0),
        disabled(317),
        enabled(318),
        uefiOnly(319),
        legacyOnly(320)
    }

CucsBiosVfPCISlotOptionROMEnableVpSlot10State ::= TEXTUAL-CONVENTION
    STATUS        current
    DESCRIPTION
        ""
    SYNTAX        INTEGER
    {
        platformRecommended(0),
        disabled(290),
        enabled(291),
        uefiOnly(292),
        legacyOnly(293)
    }

CucsBiosVfPCISlotOptionROMEnableVpSlot1State ::= TEXTUAL-CONVENTION
    STATUS        current
    DESCRIPTION
        ""
    SYNTAX        INTEGER
    {
        platformRecommended(0),
        disabled(210),
        enabled(211),
        uefiOnly(445),
        legacyOnly(446),
        platformDefault(-2)
    }

CucsBiosVfPCISlotOptionROMEnableVpSlot2State ::= TEXTUAL-CONVENTION
    STATUS        current
    DESCRIPTION
        ""
    SYNTAX        INTEGER
    {
        platformRecommended(0),
        disabled(212),
        enabled(213),
        uefiOnly(447),
        legacyOnly(448),
        platformDefault(-2)
    }

CucsBiosVfPCISlotOptionROMEnableVpSlot3State ::= TEXTUAL-CONVENTION
    STATUS        current
    DESCRIPTION
        ""
    SYNTAX        INTEGER
    {
        platformRecommended(0),
        disabled(214),
        enabled(215),
        uefiOnly(449),
        legacyOnly(450),
        platformDefault(-2)
    }

CucsBiosVfPCISlotOptionROMEnableVpSlot4State ::= TEXTUAL-CONVENTION
    STATUS        current
    DESCRIPTION
        ""
    SYNTAX        INTEGER
    {
        platformRecommended(0),
        disabled(216),
        enabled(217),
        uefiOnly(451),
        legacyOnly(452),
        platformDefault(-2)
    }

CucsBiosVfPCISlotOptionROMEnableVpSlot5State ::= TEXTUAL-CONVENTION
    STATUS        current
    DESCRIPTION
        ""
    SYNTAX        INTEGER
    {
        platformRecommended(0),
        disabled(218),
        enabled(219),
        uefiOnly(453),
        legacyOnly(454),
        platformDefault(-2)
    }

CucsBiosVfPCISlotOptionROMEnableVpSlot6State ::= TEXTUAL-CONVENTION
    STATUS        current
    DESCRIPTION
        ""
    SYNTAX        INTEGER
    {
        platformRecommended(0),
        disabled(266),
        enabled(267),
        uefiOnly(455),
        legacyOnly(456)
    }

CucsBiosVfPCISlotOptionROMEnableVpSlot7State ::= TEXTUAL-CONVENTION
    STATUS        current
    DESCRIPTION
        ""
    SYNTAX        INTEGER
    {
        platformRecommended(0),
        disabled(268),
        enabled(269),
        uefiOnly(457),
        legacyOnly(458)
    }

CucsBiosVfPCISlotOptionROMEnableVpSlot8State ::= TEXTUAL-CONVENTION
    STATUS        current
    DESCRIPTION
        ""
    SYNTAX        INTEGER
    {
        platformRecommended(0),
        disabled(282),
        enabled(283),
        uefiOnly(284),
        legacyOnly(285)
    }

CucsBiosVfPCISlotOptionROMEnableVpSlot9State ::= TEXTUAL-CONVENTION
    STATUS        current
    DESCRIPTION
        ""
    SYNTAX        INTEGER
    {
        platformRecommended(0),
        disabled(286),
        enabled(287),
        uefiOnly(288),
        legacyOnly(289)
    }

CucsBiosVfPCISlotOptionROMEnableVpSlotMezzState ::= TEXTUAL-CONVENTION
    STATUS        current
    DESCRIPTION
        ""
    SYNTAX        INTEGER
    {
        platformRecommended(0),
        disabled(220),
        enabled(221),
        uefiOnly(412),
        legacyOnly(413),
        platformDefault(-2)
    }

CucsBiosVfPOSTErrorPauseVpPOSTErrorPause ::= TEXTUAL-CONVENTION
    STATUS        current
    DESCRIPTION
        ""
    SYNTAX        INTEGER
    {
        platformRecommended(0),
        disabled(102),
        enabled(103),
        platformDefault(-2)
    }

CucsBiosVfPSTATECoordinationVpPSTATECoordination ::= TEXTUAL-CONVENTION
    STATUS        current
    DESCRIPTION
        ""
    SYNTAX        INTEGER
    {
        platformRecommended(0),
        hwAll(432),
        swAll(433),
        swAny(434)
    }

CucsBiosVfPackageCStateLimitVpPackageCStateLimit ::= TEXTUAL-CONVENTION
    STATUS        current
    DESCRIPTION
        ""
    SYNTAX        INTEGER
    {
        platformRecommended(0),
        noLimit(222),
        c0(223),
        c1(224),
        c3(225),
        c6(226),
        c2(504),
        c7(505),
        c7s(506),
        auto(507),
        platformDefault(-2)
    }

CucsBiosVfPanicAndHighWatermarkVpPanicAndHighWatermark ::= TEXTUAL-CONVENTION
    STATUS        current
    DESCRIPTION
        ""
    SYNTAX        INTEGER
    {
        platformRecommended(0),
        low(612),
        high(613)
    }

CucsBiosVfPreBootDMAProtectionVpPreBootDMAProtection ::= TEXTUAL-CONVENTION
    STATUS        current
    DESCRIPTION
        ""
    SYNTAX        INTEGER
    {
        platformRecommended(0),
        disabled(614),
        enabled(615)
    }

CucsBiosVfProcessorC1EVpProcessorC1E ::= TEXTUAL-CONVENTION
    STATUS        current
    DESCRIPTION
        ""
    SYNTAX        INTEGER
    {
        platformRecommended(0),
        disabled(202),
        enabled(203),
        platformDefault(-2)
    }

CucsBiosVfProcessorC3ReportVpProcessorC3Report ::= TEXTUAL-CONVENTION
    STATUS        current
    DESCRIPTION
        ""
    SYNTAX        INTEGER
    {
        platformRecommended(0),
        disabled(108),
        enabled(109),
        acpiC2(136),
        acpiC3(137),
        platformDefault(-2)
    }

CucsBiosVfProcessorC6ReportVpProcessorC6Report ::= TEXTUAL-CONVENTION
    STATUS        current
    DESCRIPTION
        ""
    SYNTAX        INTEGER
    {
        platformRecommended(0),
        disabled(110),
        enabled(111),
        platformDefault(-2)
    }

CucsBiosVfProcessorC7ReportVpProcessorC7Report ::= TEXTUAL-CONVENTION
    STATUS        current
    DESCRIPTION
        ""
    SYNTAX        INTEGER
    {
        platformRecommended(0),
        disabled(206),
        enabled(207),
        c7(502),
        c7s(503),
        platformDefault(-2)
    }

CucsBiosVfProcessorCMCIVpProcessorCMCI ::= TEXTUAL-CONVENTION
    STATUS        current
    DESCRIPTION
        ""
    SYNTAX        INTEGER
    {
        platformRecommended(0),
        enabled(555),
        disabled(556)
    }

CucsBiosVfProcessorCStateVpProcessorCState ::= TEXTUAL-CONVENTION
    STATUS        current
    DESCRIPTION
        ""
    SYNTAX        INTEGER
    {
        platformRecommended(0),
        disabled(200),
        enabled(201),
        platformDefault(-2)
    }

CucsBiosVfProcessorEnergyConfigurationVpEnergyPerformance ::= TEXTUAL-CONVENTION
    STATUS        current
    DESCRIPTION
        ""
    SYNTAX        INTEGER
    {
        platformRecommended(0),
        performance(426),
        balancedPerformance(427),
        balancedEnergy(428),
        energyEfficient(429)
    }

CucsBiosVfProcessorEnergyConfigurationVpPowerTechnology ::= TEXTUAL-CONVENTION
    STATUS        current
    DESCRIPTION
        ""
    SYNTAX        INTEGER
    {
        platformRecommended(0),
        disabled(422),
        energyEfficient(423),
        performance(424),
        custom(425)
    }

CucsBiosVfProcessorPrefetchConfigVpAdjacentCacheLinePrefetcher ::= TEXTUAL-CONVENTION
    STATUS        current
    DESCRIPTION
        ""
    SYNTAX        INTEGER
    {
        platformRecommended(0),
        disabled(407),
        enabled(408)
    }

CucsBiosVfProcessorPrefetchConfigVpDCUIPPrefetcher ::= TEXTUAL-CONVENTION
    STATUS        current
    DESCRIPTION
        ""
    SYNTAX        INTEGER
    {
        platformRecommended(0),
        disabled(411),
        enabled(412)
    }

CucsBiosVfProcessorPrefetchConfigVpDCUStreamerPrefetch ::= TEXTUAL-CONVENTION
    STATUS        current
    DESCRIPTION
        ""
    SYNTAX        INTEGER
    {
        platformRecommended(0),
        disabled(409),
        enabled(410)
    }

CucsBiosVfProcessorPrefetchConfigVpHardwarePrefetcher ::= TEXTUAL-CONVENTION
    STATUS        current
    DESCRIPTION
        ""
    SYNTAX        INTEGER
    {
        platformRecommended(0),
        disabled(405),
        enabled(406)
    }

CucsBiosVfQPILinkFrequencySelectVpQPILinkFrequencySelect ::= TEXTUAL-CONVENTION
    STATUS        current
    DESCRIPTION
        ""
    SYNTAX        INTEGER
    {
        platformRecommended(0),
        n6400(436),
        n7200(437),
        n8000(438),
        n64(439),
        n72(440),
        n80(441),
        auto(442),
        n9600(494)
    }

CucsBiosVfQPISnoopModeVpQPISnoopMode ::= TEXTUAL-CONVENTION
    STATUS        current
    DESCRIPTION
        ""
    SYNTAX        INTEGER
    {
        platformRecommended(0),
        homeSnoop(487),
        clusterOnDie(488),
        earlySnoop(489),
        auto(548),
        homeDirectorySnoop(549),
        homeDirectorySnoopWithOsb(550)
    }

CucsBiosVfQuietBootVpQuietBoot ::= TEXTUAL-CONVENTION
    STATUS        current
    DESCRIPTION
        ""
    SYNTAX        INTEGER
    {
        platformRecommended(0),
        disabled(100),
        enabled(101),
        platformDefault(-2)
    }

CucsBiosVfRedirectionAfterBIOSPOSTVpRedirectionAfterPOST ::= TEXTUAL-CONVENTION
    STATUS        current
    DESCRIPTION
        ""
    SYNTAX        INTEGER
    {
        platformRecommended(0),
        alwaysEnable(566),
        bootloader(567)
    }

CucsBiosVfResumeOnACPowerLossVpResumeOnACPowerLoss ::= TEXTUAL-CONVENTION
    STATUS        current
    DESCRIPTION
        ""
    SYNTAX        INTEGER
    {
        platformRecommended(0),
        stayOff(70),
        lastState(71),
        reset(72),
        platformDefault(-2)
    }

CucsBiosVfSBMezz1OptionROMVpSBMezz1OptionROM ::= TEXTUAL-CONVENTION
    STATUS        current
    DESCRIPTION
        ""
    SYNTAX        INTEGER
    {
        platformRecommended(0),
        disabled(580),
        enabled(581),
        uefiOnly(582),
        legacyOnly(583)
    }

CucsBiosVfSBNVMe1OptionROMVpSBNVMe1OptionROM ::= TEXTUAL-CONVENTION
    STATUS        current
    DESCRIPTION
        ""
    SYNTAX        INTEGER
    {
        platformRecommended(0),
        disabled(604),
        enabled(605),
        uefiOnly(606),
        legacyOnly(607)
    }

CucsBiosVfSIOC1OptionROMVpSIOC1OptionROM ::= TEXTUAL-CONVENTION
    STATUS        current
    DESCRIPTION
        ""
    SYNTAX        INTEGER
    {
        platformRecommended(0),
        disabled(572),
        enabled(573),
        uefiOnly(574),
        legacyOnly(575)
    }

CucsBiosVfSIOC2OptionROMVpSIOC2OptionROM ::= TEXTUAL-CONVENTION
    STATUS        current
    DESCRIPTION
        ""
    SYNTAX        INTEGER
    {
        platformRecommended(0),
        disabled(576),
        enabled(577),
        uefiOnly(578),
        legacyOnly(579)
    }

CucsBiosVfScrubPoliciesVpDemandScrub ::= TEXTUAL-CONVENTION
    STATUS        current
    DESCRIPTION
        ""
    SYNTAX        INTEGER
    {
        platformRecommended(0),
        disabled(415),
        enabled(416)
    }

CucsBiosVfScrubPoliciesVpPatrolScrub ::= TEXTUAL-CONVENTION
    STATUS        current
    DESCRIPTION
        ""
    SYNTAX        INTEGER
    {
        platformRecommended(0),
        disabled(413),
        enabled(414)
    }

CucsBiosVpSelectMemoryRASConfiguration ::= TEXTUAL-CONVENTION
    STATUS        current
    DESCRIPTION
        ""
    SYNTAX        INTEGER
    {
        platformRecommended(0),
        maximumPerformance(30),
        mirroring(31),
        lockstep(124),
        sparing(125),
        platformDefault(-2)
    }

CucsBiosVfSerialPortAEnableVpSerialPortAEnable ::= TEXTUAL-CONVENTION
    STATUS        current
    DESCRIPTION
        ""
    SYNTAX        INTEGER
    {
        platformRecommended(0),
        disabled(44),
        enabled(45),
        platformDefault(-2)
    }

CucsBiosVfSparingModeVpSparingMode ::= TEXTUAL-CONVENTION
    STATUS        current
    DESCRIPTION
        ""
    SYNTAX        INTEGER
    {
        platformRecommended(0),
        dimmSparing(126),
        rankSparing(127),
        platformDefault(-2)
    }

CucsBiosVfSriovConfigVpSriov ::= TEXTUAL-CONVENTION
    STATUS        current
    DESCRIPTION
        ""
    SYNTAX        INTEGER
    {
        platformRecommended(0),
        disabled(258),
        enabled(259),
        platformDefault(-2)
    }

CucsBiosVfTPMPendingOperationVpTPMPendingOperation ::= TEXTUAL-CONVENTION
    STATUS        current
    DESCRIPTION
        ""
    SYNTAX        INTEGER
    {
        platformRecommended(0),
        none(517),
        tpmppioowneron(518),
        tpmppioowneroff(519),
        tpmclear(520)
    }

CucsBiosVfTPMSupportVpTPMSupport ::= TEXTUAL-CONVENTION
    STATUS        current
    DESCRIPTION
        ""
    SYNTAX        INTEGER
    {
        platformRecommended(0),
        disabled(475),
        enabled(476)
    }

CucsBiosVfTrustedPlatformModuleVpTrustedPlatformModuleSupport ::= TEXTUAL-CONVENTION
    STATUS        current
    DESCRIPTION
        ""
    SYNTAX        INTEGER
    {
        platformRecommended(0),
        disabled(513),
        enabled(514)
    }

CucsBiosVfUCSMBootModeControlVpUEFIBootMode ::= TEXTUAL-CONVENTION
    STATUS        current
    DESCRIPTION
        ""
    SYNTAX        INTEGER
    {
        platformRecommended(0),
        disabled(276),
        enabled(277)
    }

CucsBiosVfUCSMBootOrderRuleControlVpUCSMBootOrderRule ::= TEXTUAL-CONVENTION
    STATUS        current
    DESCRIPTION
        ""
    SYNTAX        INTEGER
    {
        platformRecommended(0),
        strict(198),
        loose(199),
        platformDefault(-2)
    }

CucsBiosVfUEFIOSUseLegacyVideoVpUEFIOSUseLegacyVideo ::= TEXTUAL-CONVENTION
    STATUS        current
    DESCRIPTION
        ""
    SYNTAX        INTEGER
    {
        platformRecommended(0),
        disabled(160),
        enabled(161),
        platformDefault(-2)
    }

CucsBiosVfUSBBootConfigVpLegacyUSBSupport ::= TEXTUAL-CONVENTION
    STATUS        current
    DESCRIPTION
        ""
    SYNTAX        INTEGER
    {
        platformRecommended(0),
        disabled(249),
        enabled(250),
        auto(251),
        platformDefault(-2)
    }

CucsBiosVfUSBBootConfigVpMakeDeviceNonBootable ::= TEXTUAL-CONVENTION
    STATUS        current
    DESCRIPTION
        ""
    SYNTAX        INTEGER
    {
        platformRecommended(0),
        disabled(106),
        enabled(107),
        platformDefault(-2)
    }

CucsBiosVfUSBConfigurationVpLegacyUSBSupport ::= TEXTUAL-CONVENTION
    STATUS        current
    DESCRIPTION
        ""
    SYNTAX        INTEGER
    {
        platformRecommended(0),
        disabled(479),
        enabled(480),
        auto(481)
    }

CucsBiosVfUSBConfigurationVpXHCIMode ::= TEXTUAL-CONVENTION
    STATUS        current
    DESCRIPTION
        ""
    SYNTAX        INTEGER
    {
        platformRecommended(0),
        disabled(477),
        enabled(478)
    }

CucsBiosVfUSBFrontPanelAccessLockVpUSBFrontPanelLock ::= TEXTUAL-CONVENTION
    STATUS        current
    DESCRIPTION
        ""
    SYNTAX        INTEGER
    {
        platformRecommended(0),
        disabled(196),
        enable(197),
        enabled(204),
        platformDefault(-2)
    }

CucsBiosVfUSBPortConfigurationVpPort6064Emulation ::= TEXTUAL-CONVENTION
    STATUS        current
    DESCRIPTION
        ""
    SYNTAX        INTEGER
    {
        platformRecommended(0),
        disabled(391),
        enabled(392)
    }

CucsBiosVfUSBPortConfigurationVpUSBPortFront ::= TEXTUAL-CONVENTION
    STATUS        current
    DESCRIPTION
        ""
    SYNTAX        INTEGER
    {
        platformRecommended(0),
        disabled(395),
        enabled(396)
    }

CucsBiosVfUSBPortConfigurationVpUSBPortInternal ::= TEXTUAL-CONVENTION
    STATUS        current
    DESCRIPTION
        ""
    SYNTAX        INTEGER
    {
        platformRecommended(0),
        disabled(397),
        enabled(398)
    }

CucsBiosVfUSBPortConfigurationVpUSBPortKVM ::= TEXTUAL-CONVENTION
    STATUS        current
    DESCRIPTION
        ""
    SYNTAX        INTEGER
    {
        platformRecommended(0),
        disabled(399),
        enabled(400)
    }

CucsBiosVfUSBPortConfigurationVpUSBPortRear ::= TEXTUAL-CONVENTION
    STATUS        current
    DESCRIPTION
        ""
    SYNTAX        INTEGER
    {
        platformRecommended(0),
        disabled(393),
        enabled(394)
    }

CucsBiosVfUSBPortConfigurationVpUSBPortSDCard ::= TEXTUAL-CONVENTION
    STATUS        current
    DESCRIPTION
        ""
    SYNTAX        INTEGER
    {
        platformRecommended(0),
        disabled(403),
        enabled(404)
    }

CucsBiosVfUSBPortConfigurationVpUSBPortVMedia ::= TEXTUAL-CONVENTION
    STATUS        current
    DESCRIPTION
        ""
    SYNTAX        INTEGER
    {
        platformRecommended(0),
        disabled(401),
        enabled(402)
    }

CucsBiosVfUSBSysIdlePowerOptimizingSettingVpUSBIdlePowerOptimize ::= TEXTUAL-CONVENTION
    STATUS        current
    DESCRIPTION
        ""
    SYNTAX        INTEGER
    {
        platformRecommended(0),
        highPerformance(194),
        lowerIdlePower(195),
        platformDefault(-2)
    }

CucsBiosVfVGAPriorityVpVGAPriority ::= TEXTUAL-CONVENTION
    STATUS        current
    DESCRIPTION
        ""
    SYNTAX        INTEGER
    {
        platformRecommended(0),
        onboard(417),
        offboard(418),
        onboardVgaDisabled(419)
    }

CucsBiosVfWorkloadConfigurationVpWorkloadConfiguration ::= TEXTUAL-CONVENTION
    STATUS        current
    DESCRIPTION
        ""
    SYNTAX        INTEGER
    {
        platformRecommended(0),
        balanced(608),
        ioSensitive(609)
    }

CucsBmcSELCntEqptClassId ::= TEXTUAL-CONVENTION
    STATUS        current
    DESCRIPTION
        ""
    SYNTAX        INTEGER
    {
        unspecified(0),
        processorUnit(142),
        memoryUnit(247),
        computeBoard(605)
    }

CucsBmcSELCntEqptInstIdPropId ::= TEXTUAL-CONVENTION
    STATUS        current
    DESCRIPTION
        ""
    SYNTAX        INTEGER
    {
        unspecified(0),
        processorUnitId(360),
        memoryUnitId(698)
    }

CucsBmcSELCntStatsClassId ::= TEXTUAL-CONVENTION
    STATUS        current
    DESCRIPTION
        ""
    SYNTAX        INTEGER
    {
        unspecified(0),
        computePCIeFatalProtocolStats(882),
        computePCIeFatalReceiveStats(884),
        computePCIeFatalCompletionStats(886),
        computePCIeFatalStats(888),
        processorErrorStats(935),
        memoryErrorStats(940),
        processorExecStats(2601),
        processorCacheMemStats(2602),
        processorPCIBusStats(2603),
        processorPMUStats(2604),
        processorIOStats(2605),
        processorSecurityStats(2606),
        processorMiscStats(2607)
    }

CucsCallhomeAdminState ::= TEXTUAL-CONVENTION
    STATUS        current
    DESCRIPTION
        ""
    SYNTAX        INTEGER
    {
        off(0),
        on(1)
    }

CucsCallhomeAlertGroup ::= TEXTUAL-CONVENTION
    STATUS        current
    DESCRIPTION
        ""
    SYNTAX        INTEGER
    {
        diagnostic(0),
        environmental(1),
        unknown(100)
    }

CucsCallhomeAlertGroups ::= TEXTUAL-CONVENTION
    STATUS        current
    DESCRIPTION
        ""
    SYNTAX        BITS
    {
        system(0),
        environmental(1),
        linecard(2),
        supervisor(3),
        inventory(4),
        test(5),
        ciscoTac(6),
        syslogPort(7),
        license(8),
        lifeCycle(9),
        diagnostic(10)
    }

CucsCallhomeAlertLevel ::= TEXTUAL-CONVENTION
    STATUS        current
    DESCRIPTION
        ""
    SYNTAX        INTEGER
    {
        debug(0),
        normal(1),
        notify(2),
        warning(3),
        minor(4),
        major(5),
        critical(6),
        fatal(7),
        unknown(100)
    }

CucsCallhomeAlertMessageSubtype ::= TEXTUAL-CONVENTION
    STATUS        current
    DESCRIPTION
        ""
    SYNTAX        INTEGER
    {
        nosubtype(0),
        test(1),
        full(2),
        delta(3),
        minor(4),
        major(5),
        goldnormal(6),
        goldminor(7),
        goldmajor(8),
        unknown(100)
    }

CucsCallhomeAlertMessageType ::= TEXTUAL-CONVENTION
    STATUS        current
    DESCRIPTION
        ""
    SYNTAX        INTEGER
    {
        inventory(0),
        syslog(1),
        test(2),
        diag(3),
        env(4),
        conf(5),
        telemetry(6),
        unknown(100)
    }

CucsCallhomeAlertThrottlingAdminState ::= TEXTUAL-CONVENTION
    STATUS        current
    DESCRIPTION
        ""
    SYNTAX        INTEGER
    {
        off(0),
        on(1)
    }

CucsCallhomeAnonymousReportingAdminState ::= TEXTUAL-CONVENTION
    STATUS        current
    DESCRIPTION
        ""
    SYNTAX        INTEGER
    {
        off(0),
        on(1)
    }

CucsCallhomeEpConfigState ::= TEXTUAL-CONVENTION
    STATUS        current
    DESCRIPTION
        ""
    SYNTAX        INTEGER
    {
        ok(0),
        notApplied(1)
    }

CucsCallhomeEpFsmCurrentFsm ::= TEXTUAL-CONVENTION
    STATUS        current
    DESCRIPTION
        ""
    SYNTAX        INTEGER
    {
        nop(0),
        configCallhome(274)
    }

CucsCallhomeEpFsmStageName ::= TEXTUAL-CONVENTION
    STATUS        current
    DESCRIPTION
        ""
    SYNTAX        INTEGER
    {
        nop(0),
        configCallhomeBegin(274),
        configCallhomeSetLocal(275),
        configCallhomeSetPeer(276),
        configCallhomeFail(330),
        configCallhomeSuccess(331)
    }

CucsCallhomeEpFsmTaskItem ::= TEXTUAL-CONVENTION
    STATUS        current
    DESCRIPTION
        ""
    SYNTAX        INTEGER
    {
        nop(0),
        configCallhome(274)
    }

CucsCallhomeFormat ::= TEXTUAL-CONVENTION
    STATUS        current
    DESCRIPTION
        ""
    SYNTAX        INTEGER
    {
        xml(1),
        fullTxt(2),
        shortTxt(4)
    }

CucsCallhomeHolderConfigState ::= TEXTUAL-CONVENTION
    STATUS        current
    DESCRIPTION
        ""
    SYNTAX        INTEGER
    {
        ok(0),
        notApplied(1)
    }

CucsCallhomeHolderFsmCurrentFsm ::= TEXTUAL-CONVENTION
    STATUS        current
    DESCRIPTION
        ""
    SYNTAX        INTEGER
    {
        nop(0),
        configure(421),
        inventory(424)
    }

CucsCallhomeHolderFsmStageName ::= TEXTUAL-CONVENTION
    STATUS        current
    DESCRIPTION
        ""
    SYNTAX        INTEGER
    {
        nop(0),
        configureBegin(421),
        configureEnableSmartCallhome(422),
        configureDisableSmartCallhome(423),
        inventoryBegin(424),
        inventorySendInventory(425),
        configureFail(494),
        configureSuccess(495),
        inventoryFail(496),
        inventorySuccess(497)
    }

CucsCallhomeHolderFsmTaskFlags ::= TEXTUAL-CONVENTION
    STATUS        current
    DESCRIPTION
        ""
    SYNTAX        BITS
    {
        samDmeCallhomeHolderConfigureEnable(7),
        samDmeCallhomeHolderConfigureDisable(8),
        samDmeCallhomeHolderInventoryRegister(9)
    }

CucsCallhomeHolderFsmTaskItem ::= TEXTUAL-CONVENTION
    STATUS        current
    DESCRIPTION
        ""
    SYNTAX        INTEGER
    {
        nop(0),
        configure(421),
        inventory(424)
    }

CucsCallhomeInventoryStatus ::= TEXTUAL-CONVENTION
    STATUS        current
    DESCRIPTION
        ""
    SYNTAX        INTEGER
    {
        invDefault(0),
        invEnable(1),
        invInProgress(2),
        invThrottled(3)
    }

CucsCallhomeLevel ::= TEXTUAL-CONVENTION
    STATUS        current
    DESCRIPTION
        ""
    SYNTAX        INTEGER
    {
        debug(0),
        normal(1),
        notification(2),
        warning(3),
        minor(4),
        major(5),
        critical(6),
        fatal(7),
        disaster(8)
    }

CucsCallhomePolicyAdminState ::= TEXTUAL-CONVENTION
    STATUS        current
    DESCRIPTION
        ""
    SYNTAX        INTEGER
    {
        enabled(1),
        disabled(2)
    }

CucsCallhomeUrgency ::= TEXTUAL-CONVENTION
    STATUS        current
    DESCRIPTION
        ""
    SYNTAX        INTEGER
    {
        emergency(0),
        alert(1),
        critical(2),
        error(3),
        warning(4),
        notice(5),
        info(6),
        debug(7)
    }

CucsCapabilityAdminState ::= TEXTUAL-CONVENTION
    STATUS        current
    DESCRIPTION
        ""
    SYNTAX        INTEGER
    {
        restart(0),
        idle(1)
    }

CucsCapabilityCatalogueFsmCurrentFsm ::= TEXTUAL-CONVENTION
    STATUS        current
    DESCRIPTION
        ""
    SYNTAX        INTEGER
    {
        nop(0),
        deployCatalogue(609),
        activateCatalog(904)
    }

CucsCapabilityCatalogueFsmStageName ::= TEXTUAL-CONVENTION
    STATUS        current
    DESCRIPTION
        ""
    SYNTAX        INTEGER
    {
        nop(0),
        deployCatalogueBegin(609),
        deployCatalogueSyncBladeAGLocal(610),
        deployCatalogueSyncBladeAGRemote(611),
        deployCatalogueSyncNicAGLocal(612),
        deployCatalogueSyncNicAGRemote(613),
        deployCatalogueSyncPortAGLocal(614),
        deployCatalogueSyncPortAGRemote(615),
        deployCatalogueSyncHostagentAGLocal(616),
        deployCatalogueSyncHostagentAGRemote(617),
        deployCatalogueFinalize(618),
        deployCatalogueFail(619),
        deployCatalogueSuccess(620),
        activateCatalogBegin(904),
        activateCatalogUnpackLocal(905),
        activateCatalogCopyRemote(906),
        activateCatalogApplyCatalog(907),
        activateCatalogRescanImages(908),
        activateCatalogEvaluateStatus(909),
        activateCatalogFail(936),
        activateCatalogSuccess(937),
        activateCatalogCopyCatFromRep(1603),
        activateCatalogCopyExternalRepToRemote(1604)
    }

CucsCapabilityCatalogueFsmTaskItem ::= TEXTUAL-CONVENTION
    STATUS        current
    DESCRIPTION
        ""
    SYNTAX        INTEGER
    {
        nop(0),
        deployCatalogue(839),
        activateCatalog(893)
    }

CucsCapabilityFeatureStatus ::= TEXTUAL-CONVENTION
    STATUS        current
    DESCRIPTION
        ""
    SYNTAX        INTEGER
    {
        supported(0),
        unsupported(1)
    }

CucsCapabilityMgmtExtensionFsmCurrentFsm ::= TEXTUAL-CONVENTION
    STATUS        current
    DESCRIPTION
        ""
    SYNTAX        INTEGER
    {
        nop(0),
        activateMgmtExt(910)
    }

CucsCapabilityMgmtExtensionFsmStageName ::= TEXTUAL-CONVENTION
    STATUS        current
    DESCRIPTION
        ""
    SYNTAX        INTEGER
    {
        nop(0),
        activateMgmtExtBegin(910),
        activateMgmtExtUnpackLocal(911),
        activateMgmtExtCopyRemote(912),
        activateMgmtExtApplyCatalog(913),
        activateMgmtExtRescanImages(914),
        activateMgmtExtEvaluateStatus(915),
        activateMgmtExtFail(938),
        activateMgmtExtSuccess(939)
    }

CucsCapabilityMgmtExtensionFsmTaskItem ::= TEXTUAL-CONVENTION
    STATUS        current
    DESCRIPTION
        ""
    SYNTAX        INTEGER
    {
        nop(0),
        activateMgmtExt(899)
    }

CucsCapabilityOperStatus ::= TEXTUAL-CONVENTION
    STATUS        current
    DESCRIPTION
        ""
    SYNTAX        INTEGER
    {
        init(0),
        downloading(1),
        downloaded(2),
        applied(3),
        failed(4)
    }

CucsCapabilityPlatform ::= TEXTUAL-CONVENTION
    STATUS        current
    DESCRIPTION
        ""
    SYNTAX        INTEGER
    {
        ucs6100(0),
        ucs6200(1),
        ucs6324(2),
        ucs6300(3),
        ucs6300UP(4),
        ucs6400(5),
        ucs6500(6),
        ucsx9100(7),
        ucs6600(8)
    }

CucsCapabilityUpdaterFsmCurrentFsm ::= TEXTUAL-CONVENTION
    STATUS        current
    DESCRIPTION
        ""
    SYNTAX        INTEGER
    {
        nop(0),
        updater(582)
    }

CucsCapabilityUpdaterFsmStageName ::= TEXTUAL-CONVENTION
    STATUS        current
    DESCRIPTION
        ""
    SYNTAX        INTEGER
    {
        nop(0),
        updaterBegin(582),
        updaterLocal(583),
        updaterUnpackLocal(584),
        updaterDeleteLocal(585),
        updaterCopyRemote(586),
        updaterApply(587),
        updaterRescanImages(588),
        updaterFail(589),
        updaterSuccess(590),
        updaterEvaluateStatus(903)
    }

CucsCapabilityUpdaterFsmTaskItem ::= TEXTUAL-CONVENTION
    STATUS        current
    DESCRIPTION
        ""
    SYNTAX        INTEGER
    {
        nop(0),
        updater(582)
    }

CucsCertRepairEpFsmCurrentFsm ::= TEXTUAL-CONVENTION
    STATUS        current
    DESCRIPTION
        ""
    SYNTAX        INTEGER
    {
        nop(0),
        repairCert(50)
    }

CucsCertRepairEpFsmStageName ::= TEXTUAL-CONVENTION
    STATUS        current
    DESCRIPTION
        ""
    SYNTAX        INTEGER
    {
        nop(0),
        repairCertBegin(50),
        repairCertRequest(51),
        repairCertVerify(52),
        repairCertFail(99),
        repairCertSuccess(100)
    }

CucsCertRepairEpFsmTaskItem ::= TEXTUAL-CONVENTION
    STATUS        current
    DESCRIPTION
        ""
    SYNTAX        INTEGER
    {
        nop(0),
        repairCert(50)
    }

CucsCertRepairStateType ::= TEXTUAL-CONVENTION
    STATUS        current
    DESCRIPTION
        ""
    SYNTAX        INTEGER
    {
        done(0),
        notDone(1)
    }

CucsChangeEpFsmCurrentFsm ::= TEXTUAL-CONVENTION
    STATUS        current
    DESCRIPTION
        ""
    SYNTAX        INTEGER
    {
        nop(0),
        syncChangeUCS(369)
    }

CucsChangeEpFsmStageName ::= TEXTUAL-CONVENTION
    STATUS        current
    DESCRIPTION
        ""
    SYNTAX        INTEGER
    {
        nop(0),
        syncChangeUCSBegin(369),
        syncChangeUCSSync(370),
        syncChangeUCSFail(371),
        syncChangeUCSSuccess(372)
    }

CucsChangeEpFsmTaskItem ::= TEXTUAL-CONVENTION
    STATUS        current
    DESCRIPTION
        ""
    SYNTAX        INTEGER
    {
        nop(0),
        syncChangeUCS(369)
    }

CucsChangeStatus ::= TEXTUAL-CONVENTION
    STATUS        current
    DESCRIPTION
        ""
    SYNTAX        INTEGER
    {
        modified(0),
        created(1),
        deleted(2),
        intentDeletion(3)
    }

CucsCimcvmediaAuthProtocol ::= TEXTUAL-CONVENTION
    STATUS        current
    DESCRIPTION
        ""
    SYNTAX        INTEGER
    {
        default(0),
        none(1),
        ntlm(4),
        ntlmi(5),
        ntlmv2(6),
        ntlmv2i(7),
        ntlmssp(8),
        ntlmsspi(9)
    }

CucsCimcvmediaDeviceType ::= TEXTUAL-CONVENTION
    STATUS        current
    DESCRIPTION
        ""
    SYNTAX        INTEGER
    {
        unknown(0),
        cdd(1),
        hdd(2)
    }

CucsCimcvmediaErrorType ::= TEXTUAL-CONVENTION
    STATUS        current
    DESCRIPTION
        ""
    SYNTAX        INTEGER
    {
        unknown(0),
        none(1),
        genericFailure(2),
        connectionTimeout(3),
        connectionRejected(4),
        authenticationFailed(5),
        badPath(6),
        badParam(7),
        invalidVdiskUsage(8),
        invalidVdiskType(9),
        alreadyMapped(10),
        imageStoreFull(11),
        fileNotFound(12),
        openRoFailed(13),
        openRwFailed(14),
        diskEjected(15),
        diskIoFailure(16),
        writeToReadonlyFile(17),
        mountInUse(18),
        invalidArgument(19),
        imgageDeleted(20),
        postmapError(21),
        httpServerNoContentLength(22),
        httpServerNoRangeSupport(23)
    }

CucsCimcvmediaImageNameVariable ::= TEXTUAL-CONVENTION
    STATUS        current
    DESCRIPTION
        ""
    SYNTAX        INTEGER
    {
        none(0),
        serviceProfileName(1)
    }

CucsCimcvmediaMountConfigRetryOnMountFail ::= TEXTUAL-CONVENTION
    STATUS        current
    DESCRIPTION
        ""
    SYNTAX        INTEGER
    {
        no(0),
        yes(1)
    }

CucsCimcvmediaMountStatus ::= TEXTUAL-CONVENTION
    STATUS        current
    DESCRIPTION
        ""
    SYNTAX        INTEGER
    {
        unknown(0),
        mounting(1),
        mounted(2),
        unmounting(3),
        notMounted(4),
        mountFailed(5),
        unmountFailed(6),
        mountEjectedByOs(7)
    }

CucsCimcvmediaTransport ::= TEXTUAL-CONVENTION
    STATUS        current
    DESCRIPTION
        ""
    SYNTAX        INTEGER
    {
        unknown(0),
        nfs(1),
        cifs(2),
        http(3),
        https(4)
    }

CucsCloudAdminState ::= TEXTUAL-CONVENTION
    STATUS        current
    DESCRIPTION
        ""
    SYNTAX        INTEGER
    {
        unknown(0),
        enabled(1),
        disabled(2)
    }

CucsCloudClaimState ::= TEXTUAL-CONVENTION
    STATUS        current
    DESCRIPTION
        ""
    SYNTAX        INTEGER
    {
        none(1),
        claimed(2),
        unclaimed(3)
    }

CucsCommAdminState ::= TEXTUAL-CONVENTION
    STATUS        current
    DESCRIPTION
        ""
    SYNTAX        INTEGER
    {
        enabled(1),
        disabled(2)
    }

CucsCommChannel ::= TEXTUAL-CONVENTION
    STATUS        current
    DESCRIPTION
        ""
    SYNTAX        INTEGER
    {
        fullssl(0),
        noencssl(1),
        plain(2)
    }

CucsCommCimxmlAdminState ::= TEXTUAL-CONVENTION
    STATUS        current
    DESCRIPTION
        ""
    SYNTAX        INTEGER
    {
        enabled(1),
        disabled(2)
    }

CucsCommCipherSuiteMode ::= TEXTUAL-CONVENTION
    STATUS        current
    DESCRIPTION
        ""
    SYNTAX        INTEGER
    {
        highStrength(1),
        mediumStrength(2),
        lowStrength(3),
        custom(4)
    }

CucsCommClientAdminState ::= TEXTUAL-CONVENTION
    STATUS        current
    DESCRIPTION
        ""
    SYNTAX        INTEGER
    {
        enabled(1),
        disabled(2)
    }

CucsCommCoreFileFileTransferProto ::= TEXTUAL-CONVENTION
    STATUS        current
    DESCRIPTION
        ""
    SYNTAX        INTEGER
    {
        none(0),
        ftp(1),
        tftp(2),
        scp(3),
        http(4),
        sftp(5),
        nfsCopy(6)
    }

CucsCommCoreFileProto ::= TEXTUAL-CONVENTION
    STATUS        current
    DESCRIPTION
        ""
    SYNTAX        INTEGER
    {
        none(0),
        tcp(1),
        udp(2),
        all(3)
    }

CucsCommDateTimeFsmCurrentFsm ::= TEXTUAL-CONVENTION
    STATUS        current
    DESCRIPTION
        ""
    SYNTAX        INTEGER
    {
        nop(0),
        timezone(536)
    }

CucsCommDateTimeFsmStageName ::= TEXTUAL-CONVENTION
    STATUS        current
    DESCRIPTION
        ""
    SYNTAX        INTEGER
    {
        nop(0),
        timezoneBegin(536),
        timezoneChange(537),
        timezoneFail(538),
        timezoneSuccess(539)
    }

CucsCommDateTimeFsmTaskItem ::= TEXTUAL-CONVENTION
    STATUS        current
    DESCRIPTION
        ""
    SYNTAX        INTEGER
    {
        nop(0),
        timezone(536)
    }

CucsCommDnsProviderAdminState ::= TEXTUAL-CONVENTION
    STATUS        current
    DESCRIPTION
        ""
    SYNTAX        INTEGER
    {
        enabled(1),
        disabled(2)
    }

CucsCommFabricInterconnectAuditLogsAdminState ::= TEXTUAL-CONVENTION
    STATUS        current
    DESCRIPTION
        ""
    SYNTAX        INTEGER
    {
        enabled(1),
        disabled(2)
    }

CucsCommFilePathProtocol ::= TEXTUAL-CONVENTION
    STATUS        current
    DESCRIPTION
        ""
    SYNTAX        INTEGER
    {
        none(0),
        workspace(1),
        volatile(2),
        ftp(3),
        tftp(4),
        scp(5),
        sftp(6),
        usbdrive(7),
        usbA(8),
        usbB(9)
    }

CucsCommHttpRedirectState ::= TEXTUAL-CONVENTION
    STATUS        current
    DESCRIPTION
        ""
    SYNTAX        INTEGER
    {
        enabled(1),
        disabled(2)
    }

CucsCommLogComponentSeverity ::= TEXTUAL-CONVENTION
    STATUS        current
    DESCRIPTION
        ""
    SYNTAX        INTEGER
    {
        emergencies(0),
        alerts(1),
        critical(2),
        errors(3),
        warnings(4),
        notifications(5),
        information(6),
        debugging(7)
    }

CucsCommNtpProviderAdminState ::= TEXTUAL-CONVENTION
    STATUS        current
    DESCRIPTION
        ""
    SYNTAX        INTEGER
    {
        enabled(1),
        disabled(2)
    }

CucsCommProtocol ::= TEXTUAL-CONVENTION
    STATUS        current
    DESCRIPTION
        ""
    SYNTAX        INTEGER
    {
        none(0),
        tcp(1),
        udp(2),
        all(3)
    }

CucsCommShellProto ::= TEXTUAL-CONVENTION
    STATUS        current
    DESCRIPTION
        ""
    SYNTAX        INTEGER
    {
        none(0),
        tcp(1),
        udp(2),
        all(3)
    }

CucsCommSmashCLPProto ::= TEXTUAL-CONVENTION
    STATUS        current
    DESCRIPTION
        ""
    SYNTAX        INTEGER
    {
        none(0),
        tcp(1),
        udp(2),
        all(3)
    }

CucsCommSnmpAdminState ::= TEXTUAL-CONVENTION
    STATUS        current
    DESCRIPTION
        ""
    SYNTAX        INTEGER
    {
        enabled(1),
        disabled(2)
    }

CucsCommSnmpConfigState ::= TEXTUAL-CONVENTION
    STATUS        current
    DESCRIPTION
        ""
    SYNTAX        INTEGER
    {
        ok(0),
        notApplied(1)
    }

CucsCommSnmpProto ::= TEXTUAL-CONVENTION
    STATUS        current
    DESCRIPTION
        ""
    SYNTAX        INTEGER
    {
        none(0),
        tcp(1),
        udp(2),
        all(3)
    }

CucsCommSnmpProtocol ::= TEXTUAL-CONVENTION
    STATUS        current
    DESCRIPTION
        ""
    SYNTAX        INTEGER
    {
        none(0),
        tcp(1),
        udp(2),
        all(3)
    }

CucsCommSnmpAuth ::= TEXTUAL-CONVENTION
    STATUS        current
    DESCRIPTION
        ""
    SYNTAX        INTEGER
    {
        md5(1),
        sha(2)
    }

CucsCommSnmpEncryptionAlgoType ::= TEXTUAL-CONVENTION
    STATUS        current
    DESCRIPTION
        ""
    SYNTAX        INTEGER
    {
        none(1),
        aes(2)
    }

CucsCommSnmpNotificationType ::= TEXTUAL-CONVENTION
    STATUS        current
    DESCRIPTION
        ""
    SYNTAX        INTEGER
    {
        traps(1),
        informs(2)
    }

CucsCommSnmpV3Privilege ::= TEXTUAL-CONVENTION
    STATUS        current
    DESCRIPTION
        ""
    SYNTAX        INTEGER
    {
        auth(1),
        noauth(2),
        priv(3)
    }

CucsCommSnmpVersion ::= TEXTUAL-CONVENTION
    STATUS        current
    DESCRIPTION
        ""
    SYNTAX        INTEGER
    {
        v1(1),
        v2c(2),
        v3(3)
    }

CucsCommSshAdminState ::= TEXTUAL-CONVENTION
    STATUS        current
    DESCRIPTION
        ""
    SYNTAX        INTEGER
    {
        enabled(1),
        disabled(2)
    }

CucsCommSslProtocol ::= TEXTUAL-CONVENTION
    STATUS        current
    DESCRIPTION
        ""
    SYNTAX        INTEGER
    {
        all(0),
        tlsv12(3),
        tlsv13(4)
    }

CucsCommSvcEpFsmCurrentFsm ::= TEXTUAL-CONVENTION
    STATUS        current
    DESCRIPTION
        ""
    SYNTAX        INTEGER
    {
        nop(0),
        updateSvcEp(190),
        restartWebSvc(193)
    }

CucsCommSvcEpFsmStageName ::= TEXTUAL-CONVENTION
    STATUS        current
    DESCRIPTION
        ""
    SYNTAX        INTEGER
    {
        nop(0),
        restartWebSvcRestart(62),
        updateSvcEpBegin(190),
        updateSvcEpSetEpLocal(191),
        updateSvcEpSetEpPeer(192),
        restartWebSvcBegin(193),
        restartWebSvcFail(332),
        restartWebSvcSuccess(333),
        updateSvcEpFail(334),
        updateSvcEpSuccess(335),
        updateSvcEpPropogateEpSettings(532),
        updateSvcEpPropogateEpTimeZoneSettingsLocal(592),
        updateSvcEpPropogateEpTimeZoneSettingsPeer(593),
        updateSvcEpPropogateEpTimeZoneSettingsToAdaptorsLocal(877),
        updateSvcEpPropogateEpTimeZoneSettingsToAdaptorsPeer(878),
        updateSvcEpPropogateEpTimeZoneSettingsToFexIomLocal(1046),
        updateSvcEpPropogateEpTimeZoneSettingsToFexIomPeer(1047),
        restartWebSvcLocal(1165),
        restartWebSvcPeer(1166),
        updateSvcEpInitIptablesLocal(2017),
        updateSvcEpInitIptablesPeer(2018)
    }

CucsCommSvcEpFsmTaskFlags ::= TEXTUAL-CONVENTION
    STATUS        current
    DESCRIPTION
        ""
    SYNTAX        BITS
    {
        samDmeCommSvcEpUpdateSvcEpEpChange(21),
        samDmeCommSvcEpUpdateSvcEpPropogateSettings(22)
    }

CucsCommSvcEpFsmTaskItem ::= TEXTUAL-CONVENTION
    STATUS        current
    DESCRIPTION
        ""
    SYNTAX        INTEGER
    {
        nop(0),
        updateSvcEp(190),
        restartWebSvc(193)
    }

CucsCommSyslogProto ::= TEXTUAL-CONVENTION
    STATUS        current
    DESCRIPTION
        ""
    SYNTAX        INTEGER
    {
        none(0),
        tcp(1),
        udp(2),
        all(3)
    }

CucsCommSyslogRfc5424Compliance ::= TEXTUAL-CONVENTION
    STATUS        current
    DESCRIPTION
        ""
    SYNTAX        INTEGER
    {
        enabled(1),
        disabled(2)
    }

CucsCommSyslogAdminState ::= TEXTUAL-CONVENTION
    STATUS        current
    DESCRIPTION
        ""
    SYNTAX        INTEGER
    {
        enabled(1),
        disabled(2)
    }

CucsCommSyslogClientAdminState ::= TEXTUAL-CONVENTION
    STATUS        current
    DESCRIPTION
        ""
    SYNTAX        INTEGER
    {
        enabled(1),
        disabled(2)
    }

CucsCommSyslogClientEnum ::= TEXTUAL-CONVENTION
    STATUS        current
    DESCRIPTION
        ""
    SYNTAX        INTEGER
    {
        primary(1),
        secondary(2),
        tertiary(3)
    }

CucsCommSyslogConsoleAdminState ::= TEXTUAL-CONVENTION
    STATUS        current
    DESCRIPTION
        ""
    SYNTAX        INTEGER
    {
        enabled(1),
        disabled(2)
    }

CucsCommSyslogConsoleSeverity ::= TEXTUAL-CONVENTION
    STATUS        current
    DESCRIPTION
        ""
    SYNTAX        INTEGER
    {
        emergencies(0),
        alerts(1),
        critical(2)
    }

CucsCommSyslogFileSize ::= TEXTUAL-CONVENTION
    STATUS        current
    DESCRIPTION
        ""
    SYNTAX        Gauge32 (4096..4194304)

CucsCommSyslogForwardingFacility ::= TEXTUAL-CONVENTION
    STATUS        current
    DESCRIPTION
        ""
    SYNTAX        INTEGER
    {
        local0(0),
        local1(1),
        local2(2),
        local3(3),
        local4(4),
        local5(5),
        local6(6),
        local7(7),
        auth(8),
        authpriv(9),
        cron(10),
        daemon(11),
        ftp(12),
        kernel(13),
        lpr(14),
        mail(15),
        news(16),
        syslog(17),
        user(18),
        uucp(19)
    }

CucsCommSyslogMonitorAdminState ::= TEXTUAL-CONVENTION
    STATUS        current
    DESCRIPTION
        ""
    SYNTAX        INTEGER
    {
        enabled(1),
        disabled(2)
    }

CucsCommSyslogRestrictedSeverity ::= TEXTUAL-CONVENTION
    STATUS        current
    DESCRIPTION
        ""
    SYNTAX        INTEGER
    {
        emergencies(0),
        alerts(1),
        critical(2)
    }

CucsCommSyslogSeverity ::= TEXTUAL-CONVENTION
    STATUS        current
    DESCRIPTION
        ""
    SYNTAX        INTEGER
    {
        emergencies(0),
        alerts(1),
        critical(2),
        errors(3),
        warnings(4),
        notifications(5),
        information(6),
        debugging(7)
    }

CucsCommSyslogSourceAudits ::= TEXTUAL-CONVENTION
    STATUS        current
    DESCRIPTION
        ""
    SYNTAX        INTEGER
    {
        enabled(1),
        disabled(2)
    }

CucsCommSyslogSourceEvents ::= TEXTUAL-CONVENTION
    STATUS        current
    DESCRIPTION
        ""
    SYNTAX        INTEGER
    {
        enabled(1),
        disabled(2)
    }

CucsCommSyslogSourceFaults ::= TEXTUAL-CONVENTION
    STATUS        current
    DESCRIPTION
        ""
    SYNTAX        INTEGER
    {
        enabled(1),
        disabled(2)
    }

CucsCommTelnetAdminState ::= TEXTUAL-CONVENTION
    STATUS        current
    DESCRIPTION
        ""
    SYNTAX        INTEGER
    {
        enabled(1),
        disabled(2)
    }

CucsCommTimeZoneConfigState ::= TEXTUAL-CONVENTION
    STATUS        current
    DESCRIPTION
        ""
    SYNTAX        INTEGER
    {
        success(0),
        failure(1)
    }

CucsCommWebProto ::= TEXTUAL-CONVENTION
    STATUS        current
    DESCRIPTION
        ""
    SYNTAX        INTEGER
    {
        none(0),
        tcp(1),
        udp(2),
        all(3)
    }

CucsCommWsmanAdminState ::= TEXTUAL-CONVENTION
    STATUS        current
    DESCRIPTION
        ""
    SYNTAX        INTEGER
    {
        enabled(1),
        disabled(2)
    }

CucsCommXmlClConnPolicyClientType ::= TEXTUAL-CONVENTION
    STATUS        current
    DESCRIPTION
        ""
    SYNTAX        INTEGER
    {
        javaUi(0),
        flexUi(1),
        extrenalApiClient(2)
    }

CucsComputeABoardPower ::= TEXTUAL-CONVENTION
    STATUS        current
    DESCRIPTION
        ""
    SYNTAX        INTEGER
    {
        unknown(0),
        on(1),
        test(2),
        off(3),
        online(4),
        offline(5),
        offduty(6),
        degraded(7),
        powerSave(8),
        error(9),
        ok(10),
        failed(11),
        notSupported(100)
    }

CucsComputeAdminLinkAggregation ::= TEXTUAL-CONVENTION
    STATUS        current
    DESCRIPTION
        ""
    SYNTAX        INTEGER
    {
        none(0),
        portChannel(1),
        global(2)
    }

CucsComputeAdminMemoryState ::= TEXTUAL-CONVENTION
    STATUS        current
    DESCRIPTION
        ""
    SYNTAX        INTEGER
    {
        policy(1),
        resetMemoryErrors(2),
        resetInProgress(3)
    }

CucsComputeAdminPowerState ::= TEXTUAL-CONVENTION
    STATUS        current
    DESCRIPTION
        ""
    SYNTAX        INTEGER
    {
        cycleImmediate(2),
        cycleWait(3),
        hardResetImmediate(4),
        hardResetWait(5),
        cmosResetImmediate(12),
        bmcResetImmediate(13),
        bmcResetWait(14),
        diagnosticInterrupt(15),
        kvmReset(16),
        biosPasswordResetImmediate(18),
        policy(30),
        adminUp(31),
        adminDown(32),
        ipmiReset(33)
    }

CucsComputeAdminState ::= TEXTUAL-CONVENTION
    STATUS        current
    DESCRIPTION
        ""
    SYNTAX        INTEGER
    {
        inService(1),
        outOfService(2),
        inMaintenance(3)
    }

CucsComputeAdminTrigger ::= TEXTUAL-CONVENTION
    STATUS        current
    DESCRIPTION
        ""
    SYNTAX        INTEGER
    {
        undiscovered(0),
        rediscover(1),
        resetToFactory(2),
        discovered(3),
        remove(4),
        migrate(5),
        decommission(6),
        upgradeFirmware(7)
    }

CucsComputeAlarmSeverity ::= TEXTUAL-CONVENTION
    STATUS        current
    DESCRIPTION
        ""
    SYNTAX        INTEGER
    {
        minor(1),
        severe(2)
    }

CucsComputeAssociation ::= TEXTUAL-CONVENTION
    STATUS        current
    DESCRIPTION
        ""
    SYNTAX        INTEGER
    {
        none(0),
        establishing(1),
        associated(2),
        removing(3),
        failed(4),
        throttled(5)
    }

CucsComputeAvailability ::= TEXTUAL-CONVENTION
    STATUS        current
    DESCRIPTION
        ""
    SYNTAX        INTEGER
    {
        unavailable(0),
        available(1)
    }

CucsComputeBackplaneSpeed ::= TEXTUAL-CONVENTION
    STATUS        current
    DESCRIPTION
        ""
    SYNTAX        INTEGER
    {
        n40G(0),
        n4x10G(1)
    }

CucsComputeBackplaneSpeedChassisPref ::= TEXTUAL-CONVENTION
    STATUS        current
    DESCRIPTION
        ""
    SYNTAX        INTEGER
    {
        n40G(0),
        n4x10G(1),
        global(2)
    }

CucsComputeBlackListing ::= TEXTUAL-CONVENTION
    STATUS        current
    DESCRIPTION
        ""
    SYNTAX        INTEGER
    {
        disabled(0),
        enabled(1)
    }

CucsComputeBladeSlotId ::= TEXTUAL-CONVENTION
    STATUS        current
    DESCRIPTION
        ""
    SYNTAX        Gauge32 (1..8)

CucsComputeBladeEpId ::= TEXTUAL-CONVENTION
    STATUS        current
    DESCRIPTION
        ""
    SYNTAX        Gauge32 (1..2)

CucsComputeBladeEpSlotId ::= TEXTUAL-CONVENTION
    STATUS        current
    DESCRIPTION
        ""
    SYNTAX        Gauge32 (1..8)

CucsComputeBladeFsmCurrentFsm ::= TEXTUAL-CONVENTION
    STATUS        current
    DESCRIPTION
        ""
    SYNTAX        INTEGER
    {
        nop(0),
        discover(23),
        diag(144),
        updateBoardController(604),
        associate(665),
        disassociate(727),
        powerCap(767),
        decommission(769),
        softShutdown(771),
        hardShutdown(773),
        turnup(775),
        powercycle(777),
        hardreset(781),
        softreset(785),
        swConnUpd(789),
        biosRecovery(792),
        cmosReset(806),
        resetBmc(815),
        updateExtUsers(879),
        updateAdaptor(891),
        activateAdaptor(898),
        configSoL(932),
        unconfigSoL(934),
        diagnosticInterrupt(1036),
        resetKvm(1055),
        updateBIOS(1152),
        activateBIOS(1157),
        resetIpmi(1254),
        fwUpgrade(1256),
        cimcSessionDelete(1478),
        serviceInfraDeploy(1513),
        serviceInfraWithdraw(1518),
        configBoard(1531),
        resetMemoryErrors(1533),
        flashController(1592),
        enableCimcSecureBoot(1611),
        oobStorageAdminConfig(1722),
        clearTPM(1945),
        diskZoningInventory(2045),
        cimcSecurityConfig(2242),
        executeActions(2337),
        nvmeSwitchRecovery(2345),
        reinitializeVirtualDrive(2375),
        configureServerPersonality(2401),
        biosPasswordReset(2407),
        cimcSecurityUnconfig(2416),
        dataSanitization(2454)
    }

CucsComputeBladeFsmStageName ::= TEXTUAL-CONVENTION
    STATUS        current
    DESCRIPTION
        ""
    SYNTAX        INTEGER
    {
        nop(0),
        discoverBegin(23),
        discoverBmcPresence(24),
        discoverBmcInventory(25),
        discoverConfigFeLocal(26),
        discoverConfigFePeer(27),
        discoverConfigUserAccess(28),
        discoverBladePowerOn(29),
        discoverSwConfigPnuOSLocal(33),
        discoverSwConfigPnuOSPeer(34),
        discoverBladeBootPnuos(35),
        discoverBladeReadSmbios(36),
        discoverHagConnect(37),
        discoverPnuOSIdent(38),
        discoverPnuOSPolicy(39),
        discoverPnuOSInventory(40),
        discoverPnuOSSelfTest(41),
        discoverSwUnconfigPnuOSLocal(43),
        discoverSwUnconfigPnuOSPeer(44),
        discoverHagDisconnect(45),
        discoverBmcShutdownDiscovered(46),
        discoverHandlePooling(47),
        discoverSuccess(48),
        discoverFail(49),
        diagBegin(144),
        diagBmcPresence(145),
        diagBmcInventory(146),
        diagConfigFeLocal(147),
        diagConfigFePeer(148),
        diagBladePowerOn(149),
        diagDeriveConfig(152),
        diagConfigUserAccess(153),
        diagSwConfigLocal(155),
        diagSwConfigPeer(156),
        diagSetupVMediaLocal(158),
        diagSetupVMediaPeer(159),
        diagBladeBoot(160),
        diagBladeReadSmbios(161),
        diagHostConnect(162),
        diagHostIdent(165),
        diagHostPolicy(166),
        diagSetDiagUser(167),
        diagHostInventory(168),
        diagGenerateReport(171),
        diagRemoveConfig(172),
        diagRemoveVMediaLocal(173),
        diagRemoveVMediaPeer(174),
        diagSwUnconfigLocal(176),
        diagSwUnconfigPeer(177),
        diagUnconfigUserAccess(178),
        diagHostDisconnect(180),
        diagBmcShutdownDiagCompleted(181),
        diagSuccess(182),
        diagFail(183),
        discoverPnuOSScrub(458),
        diagHostServerDiag(479),
        diagHostServerDiagStatus(480),
        diagDisableServerConnSwB(481),
        diagStartFabricATrafficTest(482),
        diagFabricATrafficTestStatus(483),
        diagEnableServerConnSwB(484),
        diagDisableServerConnSwA(485),
        diagStartFabricBTrafficTest(486),
        diagFabricBTrafficTestStatus(487),
        diagEnableServerConnSwA(488),
        discoverBladeBootWait(504),
        diagBladeBootWait(519),
        diagBiosPostCompletion(520),
        discoverBiosPostCompletion(521),
        diagRestoreConfigFeLocal(526),
        diagRestoreConfigFePeer(527),
        discoverSetupVmediaLocal(528),
        discoverSetupVmediaPeer(529),
        discoverTeardownVmediaLocal(530),
        discoverTeardownVmediaPeer(531),
        diagGenerateLogWait(533),
        diagStopVMediaLocal(534),
        diagStopVMediaPeer(535),
        discoverSanitize(545),
        discoverPreSanitize(567),
        diagDebugWait(591),
        diagEvaluateStatus(599),
        updateBoardControllerBegin(604),
        updateBoardControllerBladePowerOff(605),
        updateBoardControllerUpdateRequest(606),
        updateBoardControllerPollUpdateStatus(607),
        updateBoardControllerBladePowerOn(608),
        updateBoardControllerFail(621),
        updateBoardControllerSuccess(622),
        updateBoardControllerPrepareForUpdate(629),
        diagNicPresenceLocal(647),
        diagNicPresencePeer(648),
        diagNicInventoryLocal(649),
        diagNicInventoryPeer(650),
        diagNicConfigLocal(651),
        diagNicConfigPeer(652),
        diagNicUnconfigLocal(653),
        diagNicUnconfigPeer(654),
        discoverNicPresenceLocal(657),
        discoverNicPresencePeer(658),
        discoverNicConfigPnuOSLocal(659),
        discoverNicConfigPnuOSPeer(660),
        discoverNicUnconfigPnuOSLocal(663),
        discoverNicUnconfigPnuOSPeer(664),
        associateBegin(665),
        associateUpdateIBMCFw(668),
        associateWaitForIBMCFwUpdate(669),
        associateActivateIBMCFw(670),
        associateResetIBMC(671),
        associatePreSanitize(672),
        associateSanitize(673),
        associateConfigUserAccess(674),
        associateBladePowerOff(675),
        associateUpdateBoardCtrlRequest(676),
        associatePollBoardCtrlUpdateStatus(677),
        associatePowerOn(678),
        associateBmcPreconfigPnuOSLocal(679),
        associateBmcPreconfigPnuOSPeer(680),
        associateBmcConfigPnuOS(681),
        associateSwConfigPnuOSLocal(682),
        associateSwConfigPnuOSPeer(683),
        associateUpdateAdaptorNwFwLocal(684),
        associateUpdateAdaptorNwFwPeer(685),
        associateWaitForAdaptorNwFwUpdateLocal(686),
        associateWaitForAdaptorNwFwUpdatePeer(687),
        associateActivateAdaptorNwFwLocal(688),
        associateActivateAdaptorNwFwPeer(689),
        associateNicConfigPnuOSLocal(690),
        associateNicConfigPnuOSPeer(691),
        associateBootPnuos(692),
        associateBootWait(693),
        associateBiosPostCompletion(694),
        associateHagPnuOSConnect(695),
        associatePnuOSIdent(696),
        associatePnuOSPolicy(697),
        associatePnuOSValidate(698),
        associatePnuOSSelfTest(699),
        associateBiosImgUpdate(700),
        associateStorageCtlrImgUpdate(701),
        associateHbaImgUpdate(702),
        associateNicImgUpdate(703),
        associatePnuOSInventory(704),
        associatePnuOSConfig(705),
        associatePnuOSLocalDiskConfig(706),
        associatePnuOSUnloadDrivers(707),
        associateBmcUnconfigPnuOS(708),
        associateNicUnconfigPnuOSLocal(709),
        associateNicUnconfigPnuOSPeer(710),
        associateSwUnconfigPnuOSLocal(711),
        associateSwUnconfigPnuOSPeer(712),
        associateSwConfigHostOSLocal(713),
        associateSwConfigHostOSPeer(714),
        associateNicConfigHostOSLocal(715),
        associateNicConfigHostOSPeer(716),
        associateHagPnuOSDisconnect(717),
        associateConfigSoL(718),
        associatePrepareForBoot(719),
        associateConfigUuid(720),
        associateBootHost(721),
        associateHagHostOSConnect(722),
        associateHostOSIdent(723),
        associateHostOSPolicy(724),
        associateHostOSValidate(725),
        associateHostOSConfig(726),
        disassociateBegin(727),
        disassociateConfigUserAccess(730),
        disassociatePowerOn(731),
        disassociatePreSanitize(732),
        disassociateSanitize(733),
        disassociateNicUnconfigHostOSLocal(734),
        disassociateNicUnconfigHostOSPeer(735),
        disassociateSwUnconfigHostOSLocal(736),
        disassociateSwUnconfigHostOSPeer(737),
        disassociateBmcPreconfigPnuOSLocal(738),
        disassociateBmcPreconfigPnuOSPeer(739),
        disassociateBmcConfigPnuOS(740),
        disassociateSwConfigPnuOSLocal(741),
        disassociateSwConfigPnuOSPeer(742),
        disassociateNicConfigPnuOSLocal(743),
        disassociateNicConfigPnuOSPeer(744),
        disassociateConfigBios(745),
        disassociateBootPnuos(746),
        disassociateBootWait(747),
        disassociateBiosPostCompletion(748),
        disassociateHagPnuOSConnect(749),
        disassociatePnuOSIdent(750),
        disassociatePnuOSPolicy(751),
        disassociatePnuOSValidate(752),
        disassociatePnuOSUnconfig(753),
        disassociatePnuOSScrub(754),
        disassociatePnuOSSelfTest(755),
        disassociateBmcUnconfigPnuOS(756),
        disassociateNicUnconfigPnuOSLocal(757),
        disassociateNicUnconfigPnuOSPeer(758),
        disassociateHagPnuOSDisconnect(759),
        disassociateUnconfigUuid(760),
        disassociateShutdown(761),
        disassociateUnconfigBios(762),
        disassociateSwUnconfigPnuOSLocal(763),
        disassociateSwUnconfigPnuOSPeer(764),
        disassociateUnconfigSoL(765),
        disassociateHandlePooling(766),
        powerCapBegin(767),
        powerCapConfig(768),
        decommissionBegin(769),
        decommissionExecute(770),
        softShutdownBegin(771),
        softShutdownExecute(772),
        hardShutdownBegin(773),
        hardShutdownExecute(774),
        turnupBegin(775),
        turnupExecute(776),
        powercycleBegin(777),
        powercyclePreSanitize(778),
        powercycleSanitize(779),
        powercycleExecute(780),
        hardresetBegin(781),
        hardresetPreSanitize(782),
        hardresetSanitize(783),
        hardresetExecute(784),
        softresetBegin(785),
        softresetPreSanitize(786),
        softresetSanitize(787),
        softresetExecute(788),
        swConnUpdBegin(789),
        swConnUpdA(790),
        swConnUpdB(791),
        biosRecoveryBegin(792),
        biosRecoveryShutdown(793),
        biosRecoveryPreSanitize(794),
        biosRecoverySanitize(795),
        biosRecoverySetupVmediaLocal(796),
        biosRecoverySetupVmediaPeer(797),
        biosRecoveryStart(798),
        biosRecoveryWait(799),
        biosRecoveryCleanup(800),
        biosRecoveryReset(801),
        biosRecoveryTeardownVmediaLocal(802),
        biosRecoveryTeardownVmediaPeer(803),
        cmosResetBegin(806),
        cmosResetPreSanitize(807),
        cmosResetSanitize(808),
        cmosResetExecute(809),
        cmosResetReconfigBios(810),
        cmosResetReconfigUuid(811),
        cmosResetBladePowerOn(812),
        resetBmcBegin(815),
        resetBmcExecute(816),
        updateExtUsersBegin(879),
        updateExtUsersDeploy(880),
        updateAdaptorBegin(891),
        updateAdaptorPowerOn(892),
        updateAdaptorUpdateRequestLocal(893),
        updateAdaptorUpdateRequestPeer(894),
        updateAdaptorPollUpdateStatusLocal(895),
        updateAdaptorPollUpdateStatusPeer(896),
        updateAdaptorPowerOff(897),
        activateAdaptorBegin(898),
        activateAdaptorPowerOn(899),
        activateAdaptorActivateLocal(900),
        activateAdaptorActivatePeer(901),
        activateAdaptorReset(902),
        configSoLBegin(932),
        configSoLExecute(933),
        unconfigSoLBegin(934),
        unconfigSoLExecute(935),
        activateAdaptorFail(940),
        activateAdaptorSuccess(941),
        associateFail(942),
        associateSuccess(943),
        biosRecoveryFail(946),
        biosRecoverySuccess(947),
        cmosResetFail(948),
        cmosResetSuccess(949),
        configSoLFail(950),
        configSoLSuccess(951),
        decommissionFail(952),
        decommissionSuccess(953),
        disassociateFail(954),
        disassociateSuccess(955),
        hardShutdownFail(956),
        hardShutdownSuccess(957),
        hardresetFail(958),
        hardresetSuccess(959),
        powerCapFail(960),
        powerCapSuccess(961),
        powercycleFail(962),
        powercycleSuccess(963),
        resetBmcFail(964),
        resetBmcSuccess(965),
        softShutdownFail(966),
        softShutdownSuccess(967),
        softresetFail(968),
        softresetSuccess(969),
        swConnUpdFail(970),
        swConnUpdSuccess(971),
        turnupFail(972),
        turnupSuccess(973),
        unconfigSoLFail(974),
        unconfigSoLSuccess(975),
        updateAdaptorFail(976),
        updateAdaptorSuccess(977),
        updateExtUsersFail(978),
        updateExtUsersSuccess(979),
        decommissionStopVMediaLocal(1019),
        decommissionStopVMediaPeer(1020),
        biosRecoveryStopVMediaLocal(1021),
        biosRecoveryStopVMediaPeer(1022),
        diagCleanupServerConnSwA(1032),
        diagCleanupServerConnSwB(1033),
        diagnosticInterruptBegin(1036),
        diagnosticInterruptExecute(1037),
        diagnosticInterruptFail(1038),
        diagnosticInterruptSuccess(1039),
        associateLocalDiskFwUpdate(1040),
        resetKvmBegin(1055),
        resetKvmExecute(1056),
        resetKvmFail(1057),
        resetKvmSuccess(1058),
        associateSwConfigPortNivLocal(1069),
        associateSwConfigPortNivPeer(1070),
        disassociateSwConfigPortNivLocal(1071),
        disassociateSwConfigPortNivPeer(1072),
        discoverBmcPreConfigPnuOSLocal(1078),
        discoverBmcPreConfigPnuOSPeer(1079),
        discoverBmcConfigPnuOS(1080),
        diagBmcConfigPnuOS(1089),
        diagSolRedirectEnable(1096),
        diagSerialDebugConnect(1097),
        diagSerialDebugDisconnect(1098),
        diagSolRedirectDisable(1099),
        discoverSolRedirectEnable(1100),
        discoverSerialDebugConnect(1101),
        discoverSerialDebugDisconnect(1102),
        discoverSolRedirectDisable(1103),
        associateSolRedirectEnable(1104),
        associateSerialDebugPnuOSConnect(1105),
        associateSerialDebugPnuOSDisconnect(1106),
        associateSolRedirectDisable(1107),
        disassociateSolRedirectEnable(1108),
        disassociateSerialDebugPnuOSConnect(1109),
        disassociateSerialDebugPnuOSDisconnect(1110),
        disassociateSolRedirectDisable(1111),
        decommissionCleanupCIMC(1112),
        updateBIOSBegin(1152),
        updateBIOSClear(1153),
        updateBIOSPollClearStatus(1154),
        updateBIOSUpdateRequest(1155),
        updateBIOSPollUpdateStatus(1156),
        activateBIOSBegin(1157),
        activateBIOSPowerOff(1158),
        activateBIOSClear(1159),
        activateBIOSPollClearStatus(1160),
        activateBIOSActivate(1161),
        activateBIOSPollActivateStatus(1162),
        activateBIOSUpdateTokens(1163),
        activateBIOSPowerOn(1164),
        diagHostCatalog(1167),
        discoverPnuOSCatalog(1168),
        associateClearBiosUpdate(1169),
        associatePollClearBiosUpdateStatus(1170),
        associateUpdateBiosRequest(1171),
        associatePollBiosUpdateStatus(1172),
        associateActivateBios(1173),
        associatePollBiosActivateStatus(1174),
        associatePnuOSCatalog(1175),
        disassociatePnuOSCatalog(1176),
        activateBIOSFail(1178),
        activateBIOSSuccess(1179),
        updateBIOSFail(1180),
        updateBIOSSuccess(1181),
        discoverCheckPowerAvailability(1246),
        associateMarkAdapterForReboot(1247),
        associateDeassertResetBypass(1248),
        associateVerifyFcZoneConfig(1249),
        disassociateDeassertResetBypass(1250),
        disassociateVerifyFcZoneConfig(1251),
        decommissionCleanupPortConfigLocal(1252),
        decommissionCleanupPortConfigPeer(1253),
        resetIpmiBegin(1254),
        resetIpmiExecute(1255),
        fwUpgradeBegin(1256),
        fwUpgradeUpdateIBMCFw(1257),
        fwUpgradeWaitForIBMCFwUpdate(1258),
        fwUpgradeActivateIBMCFw(1259),
        fwUpgradeResetIBMC(1260),
        fwUpgradePreSanitize(1261),
        fwUpgradeSanitize(1262),
        fwUpgradeBladePowerOff(1263),
        fwUpgradeUpdateBoardCtrlRequest(1264),
        fwUpgradePollBoardCtrlUpdateStatus(1265),
        fwUpgradeClearBiosUpdate(1266),
        fwUpgradePollClearBiosUpdateStatus(1267),
        fwUpgradeUpdateBiosRequest(1268),
        fwUpgradePollBiosUpdateStatus(1269),
        fwUpgradeActivateBios(1270),
        fwUpgradePollBiosActivateStatus(1271),
        fwUpgradePowerOn(1272),
        fwUpgradeBmcPreconfigPnuOSLocal(1273),
        fwUpgradeBmcPreconfigPnuOSPeer(1274),
        fwUpgradeSwConfigPortNivLocal(1275),
        fwUpgradeSwConfigPortNivPeer(1276),
        fwUpgradeSwConfigPnuOSLocal(1277),
        fwUpgradeSwConfigPnuOSPeer(1278),
        fwUpgradeUpdateAdaptorNwFwLocal(1279),
        fwUpgradeUpdateAdaptorNwFwPeer(1280),
        fwUpgradeWaitForAdaptorNwFwUpdateLocal(1281),
        fwUpgradeWaitForAdaptorNwFwUpdatePeer(1282),
        fwUpgradeActivateAdaptorNwFwLocal(1283),
        fwUpgradeActivateAdaptorNwFwPeer(1284),
        fwUpgradeNicConfigPnuOSLocal(1285),
        fwUpgradeNicConfigPnuOSPeer(1286),
        fwUpgradeBmcConfigPnuOS(1287),
        fwUpgradeSolRedirectEnable(1288),
        fwUpgradeSerialDebugPnuOSConnect(1289),
        fwUpgradeBootPnuos(1290),
        fwUpgradeBootWait(1291),
        fwUpgradeBiosPostCompletion(1292),
        fwUpgradeHagPnuOSConnect(1293),
        fwUpgradePnuOSIdent(1294),
        fwUpgradePnuOSPolicy(1295),
        fwUpgradePnuOSCatalog(1296),
        fwUpgradePnuOSValidate(1297),
        fwUpgradePnuOSSelfTest(1298),
        fwUpgradeStorageCtlrImgUpdate(1299),
        fwUpgradeHbaImgUpdate(1300),
        fwUpgradeNicImgUpdate(1301),
        fwUpgradeLocalDiskFwUpdate(1302),
        fwUpgradePnuOSConfig(1303),
        fwUpgradePnuOSInventory(1304),
        fwUpgradeBiosImgUpdate(1305),
        fwUpgradePnuOSUnloadDrivers(1306),
        fwUpgradeBmcUnconfigPnuOS(1307),
        fwUpgradeNicUnconfigPnuOSLocal(1308),
        fwUpgradeNicUnconfigPnuOSPeer(1309),
        fwUpgradeSwUnconfigPnuOSLocal(1310),
        fwUpgradeSwUnconfigPnuOSPeer(1311),
        fwUpgradeHagPnuOSDisconnect(1312),
        fwUpgradeSerialDebugPnuOSDisconnect(1313),
        fwUpgradeSolRedirectDisable(1314),
        fwUpgradeShutdown(1315),
        activateAdaptorDeassertResetBypass(1361),
        fwUpgradeDeassertResetBypass(1363),
        fwUpgradeFail(1385),
        fwUpgradeSuccess(1386),
        resetIpmiFail(1387),
        resetIpmiSuccess(1388),
        associateConfigFlexFlash(1471),
        associateSyncPowerState(1472),
        disassociateUnconfigFlexFlash(1473),
        cimcSessionDeleteBegin(1478),
        cimcSessionDeleteExecute(1479),
        cimcSessionDeleteFail(1480),
        cimcSessionDeleteSuccess(1481),
        discoverOobStorageInventory(1499),
        discoverConfigFlexFlashScrub(1500),
        associatePowerOnPreConfig(1501),
        associateOobStorageInventory(1502),
        associateSwConfigServiceInfraLocal(1503),
        associateSwConfigServiceInfraPeer(1504),
        associateNicConfigServiceInfraLocal(1505),
        associateNicConfigServiceInfraPeer(1506),
        disassociateNicUnconfigServiceInfraLocal(1507),
        disassociateNicUnconfigServiceInfraPeer(1508),
        disassociateConfigFlexFlashScrub(1509),
        serviceInfraDeployBegin(1513),
        serviceInfraDeploySwConfigLocal(1514),
        serviceInfraDeploySwConfigPeer(1515),
        serviceInfraDeployNicConfigLocal(1516),
        serviceInfraDeployNicConfigPeer(1517),
        serviceInfraWithdrawBegin(1518),
        serviceInfraWithdrawSwUnConfigLocal(1519),
        serviceInfraWithdrawSwUnConfigPeer(1520),
        serviceInfraWithdrawNicUnConfigLocal(1521),
        serviceInfraWithdrawNicUnConfigPeer(1522),
        updateBoardControllerServerPowerOff(1527),
        updateBoardControllerServerPowerOn(1530),
        configBoardBegin(1531),
        configBoardConfigMemoryPolicy(1532),
        resetMemoryErrorsBegin(1533),
        resetMemoryErrorsExecute(1534),
        configBoardFail(1542),
        configBoardSuccess(1543),
        resetMemoryErrorsFail(1544),
        resetMemoryErrorsSuccess(1545),
        serviceInfraDeployFail(1546),
        serviceInfraDeploySuccess(1547),
        serviceInfraWithdrawFail(1548),
        serviceInfraWithdrawSuccess(1549),
        disassociateResetSecureBootConfig(1561),
        discoverUnconfigExtMgmtRules(1566),
        discoverUnconfigExtMgmtGw(1567),
        discoverUnconfigCimcVMedia(1568),
        associateUnconfigExtMgmtRules(1569),
        associateUnconfigExtMgmtGw(1570),
        associateUnconfigCimcVMedia(1571),
        associateConfigExtMgmtRules(1572),
        associateConfigExtMgmtGw(1573),
        associateConfigCimcVMedia(1574),
        associateGraphicsImageUpdate(1575),
        disassociateConfigKvmMgmtDefaultSetting(1576),
        disassociateUnconfigExtMgmtRules(1577),
        disassociateUnconfigExtMgmtGw(1578),
        disassociateUnconfigCimcVMedia(1579),
        decommissionUnconfigExtMgmtRules(1580),
        decommissionUnconfigExtMgmtGw(1581),
        fwUpgradeUnconfigExtMgmtRules(1582),
        fwUpgradeUnconfigExtMgmtGw(1583),
        fwUpgradeUnconfigCimcVMedia(1584),
        fwUpgradeGraphicsImageUpdate(1585),
        associateDownloadImages(1588),
        associateCopyRemote(1589),
        fwUpgradeDownloadImages(1590),
        fwUpgradeCopyRemote(1591),
        flashControllerBegin(1592),
        flashControllerUpdateFlashLife(1593),
        flashControllerFail(1595),
        flashControllerSuccess(1596),
        associateDeleteCurlDownloadedImages(1598),
        fwUpgradeDeleteCurlDownloadedImages(1599),
        enableCimcSecureBootBegin(1611),
        enableCimcSecureBootUpdateRequest(1612),
        enableCimcSecureBootPollUpdateStatus(1613),
        enableCimcSecureBootActivate(1614),
        enableCimcSecureBootReset(1615),
        enableCimcSecureBootFail(1620),
        enableCimcSecureBootSuccess(1621),
        discoverConfigBMCPowerParams(1692),
        discoverPowerDeployWait(1694),
        discoverPnuOSPowerProfiling(1695),
        discoverSendBmcProfilingInit(1696),
        discoverSendBmcProfilingDone(1697),
        associateCheckPowerAvailability(1698),
        associatePowerDeployWait(1699),
        associateOobStorageConfig(1700),
        associateVerifyRemoteStorageConfig(1701),
        associateNicConfigParamsHostOSLocal(1702),
        associateNicConfigParamsHostOSPeer(1703),
        associateBmcUpdateHostPreBoot(1704),
        disassociateWaitForUnConfigAppliances(1705),
        disassociateCheckPowerAvailability(1706),
        disassociatePowerDeployWait(1707),
        turnupCheckPowerAvailability(1708),
        turnupPowerDeployWait(1709),
        powercycleCheckPowerAvailability(1710),
        powercyclePowerDeployWait(1711),
        hardresetCheckPowerAvailability(1712),
        hardresetPowerDeployWait(1713),
        softresetCheckPowerAvailability(1714),
        softresetPowerDeployWait(1715),
        biosRecoveryCheckPowerAvailability(1716),
        biosRecoveryPowerDeployWait(1717),
        cmosResetCheckPowerAvailability(1718),
        cmosResetPowerDeployWait(1719),
        fwUpgradeCheckPowerAvailability(1720),
        fwUpgradePowerDeployWait(1721),
        oobStorageAdminConfigBegin(1722),
        oobStorageAdminConfigPreSanitize(1723),
        oobStorageAdminConfigSanitize(1724),
        oobStorageAdminConfigTearDownVMediaLocal(1725),
        oobStorageAdminConfigTearDownVMediaPeer(1726),
        oobStorageAdminConfigBootHost(1727),
        oobStorageAdminConfigBootWait(1728),
        oobStorageAdminConfigOobStorageConfig(1729),
        oobStorageAdminConfigOobStorageInventory(1730),
        oobStorageAdminConfigShutdown(1731),
        activateBIOSCheckPowerAvailability(1800),
        activateBIOSPowerDeployWait(1801),
        updateAdaptorCheckPowerAvailability(1802),
        updateAdaptorPowerDeployWait(1803),
        activateAdaptorCheckPowerAvailability(1804),
        activateAdaptorPowerDeployWait(1805),
        updateBoardControllerCheckPowerAvailability(1806),
        updateBoardControllerPowerDeployWait(1807),
        oobStorageAdminConfigFail(1813),
        oobStorageAdminConfigSuccess(1814),
        associateDeleteImagesRemote(1880),
        disassociateOobDiskScrub(1881),
        fwUpgradeDeleteImagesRemote(1882),
        associateUnlockFirmwareImage(1943),
        decommissionPrecleanupPortConfig(1944),
        clearTPMBegin(1945),
        clearTPMPreSanitize(1946),
        clearTPMSanitize(1947),
        clearTPMClear(1948),
        clearTPMBootHost(1949),
        clearTPMBiosPostCompletion(1950),
        clearTPMReadSmBios(1951),
        clearTPMBladePowerOff(1952),
        clearTPMReconfigBios(1953),
        clearTPMBladePowerOn(1954),
        fwUpgradeUnlockFirmwareImage(1955),
        clearTPMFail(1957),
        clearTPMSuccess(1958),
        clearTPMStopVMediaLocal(1964),
        clearTPMStopVMediaPeer(1965),
        clearTPMSetupVmedia(1966),
        clearTPMUnconfigVmedia(1967),
        updateBoardControllerPowerCycleBoard(1968),
        updateBoardControllerPollBoardCtrlPowerCycle(1969),
        associatePowerCycleBoard(1970),
        associatePollBoardCtrlPowerCycle(1971),
        fwUpgradePowerCycleBoard(1972),
        fwUpgradePollBoardCtrlPowerCycle(1973),
        discoverCheckAdaptorFw40GCap(1977),
        associateCalculateVlanGroupForHostOSLocal(1978),
        associateCalculateVlanGroupForHostOSPeer(1979),
        associateConfigFanSpeed(1998),
        associateSasExpanderImgUpdate(1999),
        fwUpgradeSasExpanderImgUpdate(2000),
        fwUpgradeOobStorageInventory(2001),
        discoverBmcFactoryReset(2011),
        discoverPostScrubOobStorageInventory(2029),
        associateOobSasExpanderImgUpdate(2030),
        associateOobPollSasExpanderUpdateStatus(2031),
        associateOobSasExpanderImgActivate(2032),
        associateOobPollSasExpanderActivateStatus(2033),
        associateCiscoOSOpenGate(2034),
        fwUpgradeOobSasExpanderImgUpdate(2037),
        fwUpgradeOobPollSasExpanderUpdateStatus(2038),
        fwUpgradeOobSasExpanderImgActivate(2039),
        fwUpgradeOobPollSasExpanderActivateStatus(2040),
        fwUpgradeCiscoOSOpenGate(2041),
        oobStorageAdminConfigCheckPowerAvailability(2043),
        oobStorageAdminConfigPowerDeployWait(2044),
        diskZoningInventoryBegin(2045),
        diskZoningInventoryPreSanitize(2046),
        diskZoningInventorySanitize(2047),
        diskZoningInventoryBootHost(2048),
        diskZoningInventoryBootWait(2049),
        diskZoningInventoryStorageInventory(2050),
        diskZoningInventoryShutdown(2051),
        diskZoningInventoryFail(2161),
        diskZoningInventorySuccess(2162),
        activateAdaptorAssertBypassWait(2200),
        diagPreSanitize(2210),
        diagSanitize(2211),
        diagCheckPowerAvailability(2212),
        diagDisableScriptableVMedia(2213),
        diagPreconfigVmediaLocal(2214),
        diagPreconfigVmediaPeer(2215),
        diagSetupVmediaLocal(2216),
        diagSetupVmediaPeer(2217),
        diagSetupBootEnvironment(2218),
        diagPowerOn(2220),
        diagPowerOnWait(2221),
        diagHagConnect(2223),
        diagPnuOSIdent(2224),
        diagRunTests(2225),
        diagLogTransfer(2226),
        diagWaitForDebug(2227),
        diagTeardownVmediaLocal(2228),
        diagTeardownVmediaPeer(2229),
        diagHagDisconnect(2230),
        diagTearDownBootEnvironment(2232),
        diagShutdown(2233),
        associatePnuOSPeripheralComponentConfig(2234),
        associateConfigMgmtIpRules(2235),
        associateAssertBypassWait(2236),
        associateHostOSConnect(2237),
        associateConfigHostOsAnnotations(2238),
        associateConfigServerIdentity(2239),
        disassociateUnconfigServerIdentity(2240),
        fwUpgradeAssertBypassWait(2241),
        cimcSecurityConfigBegin(2242),
        cimcSecurityConfigKmipCertConfig(2243),
        cimcSecurityConfigKmipSaveCert(2244),
        cimcSecurityConfigFail(2257),
        cimcSecurityConfigSuccess(2258),
        associateRestoreVdStatus(2271),
        associateOobSasExpanderBootImgActivate(2301),
        associateOobPollSasExpanderBootImgActivateStatus(2302),
        associateMswitchImgUpdate(2303),
        fwUpgradeOobSasExpanderBootImgActivate(2304),
        fwUpgradeOobPollSasExpanderBootImgActivateStatus(2305),
        fwUpgradeMswitchImgUpdate(2306),
        discoverSharedComponentsOobInventory(2323),
        discoverSharedComponentsOobInventoryPeer(2324),
        associatePciSwitchImageUpdate(2325),
        associateSharedComponentsOobInventory(2326),
        associateSharedComponentsOobInventoryPeer(2327),
        fwUpgradePciSwitchImageUpdate(2328),
        associatePersistentMemoryDimmFwUpdate(2334),
        associateWaitForBorderConfigCompletionLocal(2335),
        associateWaitForBorderConfigCompletionPeer(2336),
        executeActionsBegin(2337),
        executeActionsSoftShutdown(2338),
        executeActionsExecutePMAction(2339),
        executeActionsPowerOn(2340),
        executeActionsBiosPostCompletion(2341),
        fwUpgradePersistentMemoryDimmFwUpdate(2344),
        nvmeSwitchRecoveryBegin(2345),
        nvmeSwitchRecoveryWaitForAck(2346),
        nvmeSwitchRecoveryExecute(2347),
        nvmeSwitchRecoveryCheckStatus(2348),
        executeActionsFail(2363),
        executeActionsSuccess(2364),
        nvmeSwitchRecoveryFail(2365),
        nvmeSwitchRecoverySuccess(2366),
        reinitializeVirtualDriveBegin(2375),
        reinitializeVirtualDriveExecuteVDAction(2376),
        reinitializeVirtualDriveFail(2377),
        reinitializeVirtualDriveSuccess(2378),
        configureServerPersonalityBegin(2401),
        configureServerPersonalityExecute(2402),
        configureServerPersonalityFail(2403),
        configureServerPersonalitySuccess(2404),
        biosPasswordResetBegin(2407),
        biosPasswordResetPreSanitize(2408),
        biosPasswordResetSanitize(2409),
        biosPasswordResetExecute(2410),
        biosPasswordResetReconfigBios(2411),
        biosPasswordResetReconfigUuid(2412),
        biosPasswordResetCheckPowerAvailability(2413),
        biosPasswordResetPowerDeployWait(2414),
        biosPasswordResetBladePowerOn(2415),
        cimcSecurityUnconfigBegin(2416),
        cimcSecurityUnconfigKmipDelCert(2417),
        biosPasswordResetFail(2418),
        biosPasswordResetSuccess(2419),
        cimcSecurityUnconfigFail(2420),
        cimcSecurityUnconfigSuccess(2421),
        diagPowerDeployWait(2422),
        discoverFruComponentInventory(2423),
        associateUpdateFruComponents(2424),
        associateWaitForUpdateFruComponents(2425),
        associateWaitForBiosPostCompletion(2426),
        associateUpdateNwSbAdaptorFw(2427),
        associateWaitForNwSbAdaptorFwUpdate(2428),
        associateActivateNwSbAdaptorFw(2429),
        associateWaitForNwSbAdaptorFwActivate(2430),
        fwUpgradeUpdateFruComponents(2433),
        fwUpgradeWaitForUpdateFruComponents(2434),
        fwUpgradeWaitForBiosPostCompletion(2435),
        fwUpgradeUpdateNwSbAdaptorFw(2436),
        fwUpgradeWaitForNwSbAdaptorFwUpdate(2437),
        fwUpgradeActivateNwSbAdaptorFw(2438),
        fwUpgradeWaitForNwSbAdaptorFwActivate(2439),
        discoverPcieNodeDiscover(2445),
        associateHybridDriveSlotConfig(2446),
        associateUpdateFruComponentsAfterPoweredOn(2447),
        associateWaitForUpdateFruComponentsAfterPoweredOn(2448),
        associatePowerOffForSbAdaptorActivation(2449),
        associateNVMEVDConfig(2450),
        fwUpgradeUpdateFruComponentsAfterPoweredOn(2451),
        fwUpgradeWaitForUpdateFruComponentsAfterPoweredOn(2452),
        fwUpgradePowerOffForSbAdaptorActivation(2453),
        dataSanitizationBegin(2454),
        dataSanitizationPreSanitize(2455),
        dataSanitizationSanitize(2456),
        dataSanitizationCheckPowerAvailability(2457),
        dataSanitizationPowerDeployWait(2458),
        dataSanitizationDisableScriptableVMedia(2459),
        dataSanitizationPreconfigVmediaLocal(2460),
        dataSanitizationPreconfigVmediaPeer(2461),
        dataSanitizationSetupVmediaLocal(2462),
        dataSanitizationSetupVmediaPeer(2463),
        dataSanitizationSetupBootEnvironment(2464),
        dataSanitizationSerialDebugConnect(2465),
        dataSanitizationPowerOn(2466),
        dataSanitizationPowerOnWait(2467),
        dataSanitizationBiosPostCompletion(2468),
        dataSanitizationHagConnect(2469),
        dataSanitizationPnuOSIdent(2470),
        dataSanitizationStorageComponents(2471),
        dataSanitizationWaitForStorageComponent(2472),
        dataSanitizationTeardownVmediaLocal(2473),
        dataSanitizationTeardownVmediaPeer(2474),
        dataSanitizationHagDisconnect(2475),
        dataSanitizationSerialDebugDisconnect(2476),
        dataSanitizationTearDownBootEnvironment(2477),
        dataSanitizationNetworkAdapter(2478),
        dataSanitizationWaitForNetworkAdapter(2479),
        dataSanitizationHostComponents(2480),
        dataSanitizationWaitForHostComponents(2481),
        dataSanitizationBoardComponents(2482),
        dataSanitizationWaitForBoardComponents(2483),
        dataSanitizationShutdown(2484),
        dataSanitizationFail(2488),
        dataSanitizationSuccess(2489),
        associatePowerOnForStorageInit(2492),
        associateWaitForStorageInit(2493),
        associateConfigStorageRemoteSecurity(2494),
        associatePowerOff(2495),
        associateFetchBiosHealthReport(2496),
        disassociateOobStorageInventory(2497),
        associateSyncPowerStateForStorageInit(2507),
        associatePowerOnPreConfigForStorageInit(2508),
        associateCheckPowerAvailabilityForStorageInit(2509),
        associatePowerDeployWaitForStorageInit(2510)
    }

CucsComputeBladeFsmTaskFlags ::= TEXTUAL-CONVENTION
    STATUS        current
    DESCRIPTION
        ""
    SYNTAX        BITS
    {
        samDmeComputeBladeDiscoverCheckPoint(0),
        samDmeComputeBladeDiagEfiDiag(18),
        samDmeComputeBladeDiagDetailDiag(20),
        samDmeComputeBladeDiagCancelDiag(23),
        samDmeComputeBladeDiscoverSkipPnuos(24)
    }

CucsComputeBladeFsmTaskItem ::= TEXTUAL-CONVENTION
    STATUS        current
    DESCRIPTION
        ""
    SYNTAX        INTEGER
    {
        nop(0),
        discover(23),
        diag(144),
        updateBoardController(834)
    }

CucsComputeBoardPower ::= TEXTUAL-CONVENTION
    STATUS        current
    DESCRIPTION
        ""
    SYNTAX        INTEGER
    {
        unknown(0),
        on(1),
        test(2),
        off(3),
        online(4),
        offline(5),
        offduty(6),
        degraded(7),
        powerSave(8),
        error(9),
        ok(10),
        failed(11),
        notSupported(100)
    }

CucsComputeCartridgeDiscovery ::= TEXTUAL-CONVENTION
    STATUS        current
    DESCRIPTION
        ""
    SYNTAX        INTEGER
    {
        undiscovered(0),
        inProgress(1),
        malformedFruInfo(2),
        fruNotReady(3),
        insufficientlyEquipped(4),
        invalidAdaptorIocard(5),
        failed(8),
        complete(16),
        retry(32),
        throttled(64),
        illegalFru(128),
        fruIdentityIndeterminate(129),
        fruStateIndeterminate(130),
        diagnosticsInProgress(131),
        efidiagnosticsInProgress(132),
        diagnosticsFailed(133),
        diagnosticsComplete(134),
        waitingForUserAck(135),
        userAcknowledged(136),
        waitingForMgmtAck(137)
    }

CucsComputeCartridgeSlotId ::= TEXTUAL-CONVENTION
    STATUS        current
    DESCRIPTION
        ""
    SYNTAX        Gauge32 (1..8)

CucsComputeChassisConnPolicyChassisId ::= TEXTUAL-CONVENTION
    STATUS        current
    DESCRIPTION
        ""
    SYNTAX        Gauge32 (0..255)

CucsComputeChassisDiscAction ::= TEXTUAL-CONVENTION
    STATUS        current
    DESCRIPTION
        ""
    SYNTAX        INTEGER
    {
        immediate(0),
        userAcknowledged(1),
        n1Link(2),
        n2Link(3),
        n4Link(4),
        n8Link(5),
        platformMax(6)
    }

CucsComputeChassisDiscPolicyMulticastHwHash ::= TEXTUAL-CONVENTION
    STATUS        current
    DESCRIPTION
        ""
    SYNTAX        INTEGER
    {
        disabled(0),
        enabled(1)
    }

CucsComputeChassisFeatureMask ::= TEXTUAL-CONVENTION
    STATUS        current
    DESCRIPTION
        ""
    SYNTAX        BITS
    {
        computeConnPolicyFeatureMask(0),
        lightWeightPatchingFeatureMask(1)
    }

CucsComputeChassisQualMaxId ::= TEXTUAL-CONVENTION
    STATUS        current
    DESCRIPTION
        ""
    SYNTAX        Gauge32 (1..255)

CucsComputeChassisQualMinId ::= TEXTUAL-CONVENTION
    STATUS        current
    DESCRIPTION
        ""
    SYNTAX        Gauge32 (1..255)

CucsComputeCheckPoint ::= TEXTUAL-CONVENTION
    STATUS        current
    DESCRIPTION
        ""
    SYNTAX        INTEGER
    {
        unknown(0),
        removing(1),
        shallowCheckpoint(2),
        deepCheckpoint(3),
        discovered(4)
    }

CucsComputeClear ::= TEXTUAL-CONVENTION
    STATUS        current
    DESCRIPTION
        ""
    SYNTAX        INTEGER
    {
        no(0),
        yes(1)
    }

CucsComputeConfigState ::= TEXTUAL-CONVENTION
    STATUS        current
    DESCRIPTION
        ""
    SYNTAX        INTEGER
    {
        ok(1),
        notApplied(2)
    }

CucsComputeConnectivityRebalancing ::= TEXTUAL-CONVENTION
    STATUS        current
    DESCRIPTION
        ""
    SYNTAX        INTEGER
    {
        immediate(0),
        userAcknowledged(1)
    }

CucsComputeDiscovery ::= TEXTUAL-CONVENTION
    STATUS        current
    DESCRIPTION
        ""
    SYNTAX        INTEGER
    {
        undiscovered(0),
        inProgress(1),
        malformedFruInfo(2),
        fruNotReady(3),
        insufficientlyEquipped(4),
        invalidAdaptorIocard(5),
        failed(8),
        complete(16),
        retry(32),
        throttled(64),
        illegalFru(128),
        fruIdentityIndeterminate(129),
        fruStateIndeterminate(130),
        diagnosticsInProgress(131),
        efidiagnosticsInProgress(132),
        diagnosticsFailed(133),
        diagnosticsComplete(134),
        waitingForUserAck(135),
        userAcknowledged(136),
        waitingForMgmtAck(137)
    }

CucsComputeDomainHwChangeDiscPolicyAction ::= TEXTUAL-CONVENTION
    STATUS        current
    DESCRIPTION
        ""
    SYNTAX        INTEGER
    {
        userAcknowledged(0),
        autoAcknowledged(1)
    }

CucsComputeDomainPortDiscPolicyEthBreakoutAutoDiscovery ::= TEXTUAL-CONVENTION
    STATUS        current
    DESCRIPTION
        ""
    SYNTAX        INTEGER
    {
        disabled(0),
        enabled(1)
    }

CucsComputeDomainPortDiscPolicyEthSvrAutoDiscovery ::= TEXTUAL-CONVENTION
    STATUS        current
    DESCRIPTION
        ""
    SYNTAX        INTEGER
    {
        disabled(0),
        enabled(1)
    }

CucsComputeEnvFeatureMask ::= TEXTUAL-CONVENTION
    STATUS        current
    DESCRIPTION
        ""
    SYNTAX        BITS
    {
        ucsRegistrationFeatureMask(0),
        powerGroupFeatureMask(1),
        healthReportingFeatureMask(2),
        dcPowerGroupFeatureMask(3),
        remoteOperationFeatureMask(4),
        estimateImpactOnReconnectFeatureMask(5),
        ssoUcsmCrossLaunchFeatureMask(6),
        domainSettingFeatureMask(7),
        ucsManagerContextLaunchFeatureMask(8),
        html5KvmClientFeatureMask(9)
    }

CucsComputeEquipmentConstraintType ::= TEXTUAL-CONVENTION
    STATUS        current
    DESCRIPTION
        ""
    SYNTAX        INTEGER
    {
        unknown(0),
        localDisk(1),
        adaptor(2),
        dimm(3)
    }

CucsComputeFactoryResetStatus ::= TEXTUAL-CONVENTION
    STATUS        current
    DESCRIPTION
        ""
    SYNTAX        INTEGER
    {
        idle(0),
        running(1),
        cimcResetInProgress(2),
        cimcResetComplete(3),
        scrubStageComplete(4)
    }

CucsComputeFactoryResetTrigger ::= TEXTUAL-CONVENTION
    STATUS        current
    DESCRIPTION
        ""
    SYNTAX        INTEGER
    {
        idle(0),
        triggered(1),
        canceled(2)
    }

CucsComputeFanPolicySpeed ::= TEXTUAL-CONVENTION
    STATUS        current
    DESCRIPTION
        ""
    SYNTAX        INTEGER
    {
        balanced(0),
        lowPower(1)
    }

CucsComputeGraphicsCardPolicyGraphicsCardMode ::= TEXTUAL-CONVENTION
    STATUS        current
    DESCRIPTION
        ""
    SYNTAX        INTEGER
    {
        compute(0),
        graphics(1),
        anyConfiguration(2)
    }

CucsComputeGroupMembershipOwner ::= TEXTUAL-CONVENTION
    STATUS        current
    DESCRIPTION
        ""
    SYNTAX        INTEGER
    {
        policy(1),
        management(2)
    }

CucsComputeHwChangeDiscPolicyAction ::= TEXTUAL-CONVENTION
    STATUS        current
    DESCRIPTION
        ""
    SYNTAX        INTEGER
    {
        userAcknowledged(0),
        autoAcknowledged(1)
    }

CucsComputeIOHubEnvStatsThresholded ::= TEXTUAL-CONVENTION
    STATUS        current
    DESCRIPTION
        ""
    SYNTAX        BITS
    {
        temperature(0),
        temperatureAvg(1),
        temperatureMax(2),
        temperatureMin(3)
    }

CucsComputeIOHubEnvStatsHistThresholded ::= TEXTUAL-CONVENTION
    STATUS        current
    DESCRIPTION
        ""
    SYNTAX        BITS
    {
        temperature(0),
        temperatureAvg(1),
        temperatureMax(2),
        temperatureMin(3)
    }

CucsComputeInstanceIdQualMaxId ::= TEXTUAL-CONVENTION
    STATUS        current
    DESCRIPTION
        ""
    SYNTAX        Gauge32 (1..8)

CucsComputeInstanceIdQualMinId ::= TEXTUAL-CONVENTION
    STATUS        current
    DESCRIPTION
        ""
    SYNTAX        Gauge32 (1..8)

CucsComputeInventoryStatus ::= TEXTUAL-CONVENTION
    STATUS        current
    DESCRIPTION
        ""
    SYNTAX        INTEGER
    {
        ok(0),
        mismatch(1),
        throttled(2),
        removal(4),
        replacement(8),
        pciConfigMismatch(16),
        persistentMemoryDetection(32)
    }

CucsComputeIssues ::= TEXTUAL-CONVENTION
    STATUS        current
    DESCRIPTION
        ""
    SYNTAX        BITS
    {
        computeThermal(0),
        computeInoperable(1),
        computeVoltage(2),
        computePerf(3),
        computePower(4),
        removed(5),
        config(6),
        computePostFailure(7),
        cpuThermal(8),
        cpuInoperable(9),
        cpuVoltage(10),
        cpuPerf(11),
        cpuPower(12),
        memoryThermal(13),
        memoryInoperable(14),
        memoryVoltage(15),
        memoryPerf(16),
        memoryPower(17),
        adaptorThermal(18),
        adaptorInoperable(19),
        adaptorVoltage(20),
        adaptorPerf(21),
        adaptorPower(22),
        nicThermal(23),
        nicInoperable(24),
        nicVoltage(25),
        nicPerf(26),
        nicPower(27),
        hbaThermal(28),
        hbaInoperable(29),
        hbaVoltage(30),
        hbaPerf(31),
        hbaPower(32),
        mismatch(33),
        powerInoperable(34),
        networkMisconfig(35),
        adaptorMismatch(36)
    }

CucsComputeKvmMgmtPolicyVmediaEncryption ::= TEXTUAL-CONVENTION
    STATUS        current
    DESCRIPTION
        ""
    SYNTAX        INTEGER
    {
        disable(0),
        enable(1)
    }

CucsComputeLinkAggregation ::= TEXTUAL-CONVENTION
    STATUS        current
    DESCRIPTION
        ""
    SYNTAX        INTEGER
    {
        none(0),
        portChannel(1)
    }

CucsComputeLinkAggregationCap ::= TEXTUAL-CONVENTION
    STATUS        current
    DESCRIPTION
        ""
    SYNTAX        BITS
    {
        portChannel(0)
    }

CucsComputeLinkGroupingPref ::= TEXTUAL-CONVENTION
    STATUS        current
    DESCRIPTION
        ""
    SYNTAX        INTEGER
    {
        none(0),
        portChannel(1)
    }

CucsComputeMbPowerStatsThresholded ::= TEXTUAL-CONVENTION
    STATUS        current
    DESCRIPTION
        ""
    SYNTAX        BITS
    {
        consumedPower(0),
        consumedPowerAvg(1),
        consumedPowerMax(2),
        consumedPowerMin(3),
        inputCurrent(4),
        inputCurrentAvg(5),
        inputCurrentMax(6),
        inputCurrentMin(7),
        inputVoltage(8),
        inputVoltageAvg(9),
        inputVoltageMax(10),
        inputVoltageMin(11)
    }

CucsComputeMbPowerStatsHistThresholded ::= TEXTUAL-CONVENTION
    STATUS        current
    DESCRIPTION
        ""
    SYNTAX        BITS
    {
        consumedPower(0),
        consumedPowerAvg(1),
        consumedPowerMax(2),
        consumedPowerMin(3),
        inputCurrent(4),
        inputCurrentAvg(5),
        inputCurrentMax(6),
        inputCurrentMin(7),
        inputVoltage(8),
        inputVoltageAvg(9),
        inputVoltageMax(10),
        inputVoltageMin(11)
    }

CucsComputeMbTempStatsThresholded ::= TEXTUAL-CONVENTION
    STATUS        current
    DESCRIPTION
        ""
    SYNTAX        BITS
    {
        fmTempSenIo(0),
        fmTempSenIoAvg(1),
        fmTempSenIoMax(2),
        fmTempSenIoMin(3),
        fmTempSenRear(4),
        fmTempSenRearAvg(5),
        fmTempSenRearL(6),
        fmTempSenRearLAvg(7),
        fmTempSenRearLMax(8),
        fmTempSenRearLMin(9),
        fmTempSenRearMax(10),
        fmTempSenRearMin(11),
        fmTempSenRearR(12),
        fmTempSenRearRAvg(13),
        fmTempSenRearRMax(14),
        fmTempSenRearRMin(15)
    }

CucsComputeMbTempStatsHistThresholded ::= TEXTUAL-CONVENTION
    STATUS        current
    DESCRIPTION
        ""
    SYNTAX        BITS
    {
        fmTempSenIo(0),
        fmTempSenIoAvg(1),
        fmTempSenIoMax(2),
        fmTempSenIoMin(3),
        fmTempSenRear(4),
        fmTempSenRearAvg(5),
        fmTempSenRearL(6),
        fmTempSenRearLAvg(7),
        fmTempSenRearLMax(8),
        fmTempSenRearLMin(9),
        fmTempSenRearMax(10),
        fmTempSenRearMin(11),
        fmTempSenRearR(12),
        fmTempSenRearRAvg(13),
        fmTempSenRearRMax(14),
        fmTempSenRearRMin(15)
    }

CucsComputeMemoryUnitConstraintType ::= TEXTUAL-CONVENTION
    STATUS        current
    DESCRIPTION
        ""
    SYNTAX        INTEGER
    {
        unknown(0),
        kit(1)
    }

CucsComputeMode ::= TEXTUAL-CONVENTION
    STATUS        current
    DESCRIPTION
        ""
    SYNTAX        INTEGER
    {
        none(0),
        single(1),
        scaled(2)
    }

CucsComputeModularChassisFanPolicySpeed ::= TEXTUAL-CONVENTION
    STATUS        current
    DESCRIPTION
        ""
    SYNTAX        INTEGER
    {
        balanced(0),
        lowPower(1),
        performance(2),
        highPower(3),
        maxPower(4),
        acoustic(5)
    }

CucsComputeNetworkFeatureMask ::= TEXTUAL-CONVENTION
    STATUS        current
    DESCRIPTION
        ""
    SYNTAX        BITS
    {
        netflowFeatureMask(0),
        vlanRangeFeatureMask(1),
        vlanRangeExtendedFeatureMask(2),
        usnicVmqFeatureMask(3),
        pvlanFeatureMask(4),
        vnicPairingFeatureMask(5)
    }

CucsComputeOpStatus ::= TEXTUAL-CONVENTION
    STATUS        current
    DESCRIPTION
        ""
    SYNTAX        INTEGER
    {
        nop(0),
        success(1),
        fail(2)
    }

CucsComputeOpType ::= TEXTUAL-CONVENTION
    STATUS        current
    DESCRIPTION
        ""
    SYNTAX        INTEGER
    {
        unknown(0),
        backup(1)
    }

CucsComputeOperAdminLinkAggregation ::= TEXTUAL-CONVENTION
    STATUS        current
    DESCRIPTION
        ""
    SYNTAX        INTEGER
    {
        none(0),
        portChannel(1),
        global(2),
        unspecified(255)
    }

CucsComputeOperBackplaneSpeedChassisPref ::= TEXTUAL-CONVENTION
    STATUS        current
    DESCRIPTION
        ""
    SYNTAX        INTEGER
    {
        n40G(0),
        n4x10G(1),
        global(2),
        unspecified(255)
    }

CucsComputeOwner ::= TEXTUAL-CONVENTION
    STATUS        current
    DESCRIPTION
        ""
    SYNTAX        INTEGER
    {
        policy(1),
        management(2)
    }

CucsComputePCIeFatalCompletionStatsThresholded ::= TEXTUAL-CONVENTION
    STATUS        current
    DESCRIPTION
        ""
    SYNTAX        BITS
    {
        abortErrors(0),
        timeoutErrors(1),
        unexpectedErrors(2),
        abortErrorsMin(3),
        abortErrorsRunning(4),
        timeoutErrorsAvg(6),
        timeoutErrorsMax(7),
        timeoutErrorsMin(8),
        timeoutErrorsRunning(9),
        unexpectedErrorsAvg(11),
        unexpectedErrorsMax(12),
        unexpectedErrorsMin(13),
        unexpectedErrorsRunning(14)
    }

CucsComputePCIeFatalCompletionStatsHistThresholded ::= TEXTUAL-CONVENTION
    STATUS        current
    DESCRIPTION
        ""
    SYNTAX        BITS
    {
        abortErrors(0),
        abortErrorsAvg(1),
        abortErrorsMax(2),
        abortErrorsMin(3),
        abortErrorsRunning(4),
        timeoutErrors(5),
        timeoutErrorsAvg(6),
        timeoutErrorsMax(7),
        timeoutErrorsMin(8),
        timeoutErrorsRunning(9),
        unexpectedErrors(10),
        unexpectedErrorsAvg(11),
        unexpectedErrorsMax(12),
        unexpectedErrorsMin(13),
        unexpectedErrorsRunning(14)
    }

CucsComputePCIeFatalProtocolStatsThresholded ::= TEXTUAL-CONVENTION
    STATUS        current
    DESCRIPTION
        ""
    SYNTAX        BITS
    {
        dllpErrors(0),
        flowControlErrors(1),
        dllpErrorsMax(2),
        dllpErrorsMin(3),
        dllpErrorsRunning(4),
        flowControlErrorsAvg(6),
        flowControlErrorsMax(7),
        flowControlErrorsMin(8),
        flowControlErrorsRunning(9)
    }

CucsComputePCIeFatalProtocolStatsHistThresholded ::= TEXTUAL-CONVENTION
    STATUS        current
    DESCRIPTION
        ""
    SYNTAX        BITS
    {
        dllpErrors(0),
        dllpErrorsAvg(1),
        dllpErrorsMax(2),
        dllpErrorsMin(3),
        dllpErrorsRunning(4),
        flowControlErrors(5),
        flowControlErrorsAvg(6),
        flowControlErrorsMax(7),
        flowControlErrorsMin(8),
        flowControlErrorsRunning(9)
    }

CucsComputePCIeFatalReceiveStatsThresholded ::= TEXTUAL-CONVENTION
    STATUS        current
    DESCRIPTION
        ""
    SYNTAX        BITS
    {
        bufferOverflowErrors(0),
        errFatalErrors(1),
        errNonFatalErrors(2),
        unsupportedRequestErrors(3),
        bufferOverflowErrorsRunning(4),
        errFatalErrorsAvg(6),
        errFatalErrorsMax(7),
        errFatalErrorsMin(8),
        errFatalErrorsRunning(9),
        errNonFatalErrorsAvg(11),
        errNonFatalErrorsMax(12),
        errNonFatalErrorsMin(13),
        errNonFatalErrorsRunning(14),
        unsupportedRequestErrorsAvg(16),
        unsupportedRequestErrorsMax(17),
        unsupportedRequestErrorsMin(18),
        unsupportedRequestErrorsRunning(19)
    }

CucsComputePCIeFatalReceiveStatsHistThresholded ::= TEXTUAL-CONVENTION
    STATUS        current
    DESCRIPTION
        ""
    SYNTAX        BITS
    {
        bufferOverflowErrors(0),
        bufferOverflowErrorsAvg(1),
        bufferOverflowErrorsMax(2),
        bufferOverflowErrorsMin(3),
        bufferOverflowErrorsRunning(4),
        errFatalErrors(5),
        errFatalErrorsAvg(6),
        errFatalErrorsMax(7),
        errFatalErrorsMin(8),
        errFatalErrorsRunning(9),
        errNonFatalErrors(10),
        errNonFatalErrorsAvg(11),
        errNonFatalErrorsMax(12),
        errNonFatalErrorsMin(13),
        errNonFatalErrorsRunning(14),
        unsupportedRequestErrors(15),
        unsupportedRequestErrorsAvg(16),
        unsupportedRequestErrorsMax(17),
        unsupportedRequestErrorsMin(18),
        unsupportedRequestErrorsRunning(19)
    }

CucsComputePCIeFatalStatsThresholded ::= TEXTUAL-CONVENTION
    STATUS        current
    DESCRIPTION
        ""
    SYNTAX        BITS
    {
        acsViolationErrors(0),
        malformedTLPErrors(1),
        poisonedTLPErrors(2),
        surpriseLinkDownErrors(3),
        acsViolationErrorsRunning(4),
        malformedTLPErrorsAvg(6),
        malformedTLPErrorsMax(7),
        malformedTLPErrorsMin(8),
        malformedTLPErrorsRunning(9),
        poisonedTLPErrorsAvg(11),
        poisonedTLPErrorsMax(12),
        poisonedTLPErrorsMin(13),
        poisonedTLPErrorsRunning(14),
        surpriseLinkDownErrorsAvg(16),
        surpriseLinkDownErrorsMax(17),
        surpriseLinkDownErrorsMin(18),
        surpriseLinkDownErrorsRunning(19)
    }

CucsComputePCIeFatalStatsHistThresholded ::= TEXTUAL-CONVENTION
    STATUS        current
    DESCRIPTION
        ""
    SYNTAX        BITS
    {
        acsViolationErrors(0),
        acsViolationErrorsAvg(1),
        acsViolationErrorsMax(2),
        acsViolationErrorsMin(3),
        acsViolationErrorsRunning(4),
        malformedTLPErrors(5),
        malformedTLPErrorsAvg(6),
        malformedTLPErrorsMax(7),
        malformedTLPErrorsMin(8),
        malformedTLPErrorsRunning(9),
        poisonedTLPErrors(10),
        poisonedTLPErrorsAvg(11),
        poisonedTLPErrorsMax(12),
        poisonedTLPErrorsMin(13),
        poisonedTLPErrorsRunning(14),
        surpriseLinkDownErrors(15),
        surpriseLinkDownErrorsAvg(16),
        surpriseLinkDownErrorsMax(17),
        surpriseLinkDownErrorsMin(18),
        surpriseLinkDownErrorsRunning(19)
    }

CucsComputePciCapOrder ::= TEXTUAL-CONVENTION
    STATUS        current
    DESCRIPTION
        ""
    SYNTAX        INTEGER
    {
        ascending(0),
        descending(1),
        ascendingDual(2),
        ascendingSeq(3),
        ascendingExtended(4)
    }

CucsComputePhysicalLowVoltageMemory ::= TEXTUAL-CONVENTION
    STATUS        current
    DESCRIPTION
        ""
    SYNTAX        INTEGER
    {
        unknown(0),
        yes(1),
        regularVoltage(2)
    }

CucsComputePhysicalFsmCurrentFsm ::= TEXTUAL-CONVENTION
    STATUS        current
    DESCRIPTION
        ""
    SYNTAX        INTEGER
    {
        nop(0),
        associate(665),
        disassociate(727),
        powerCap(767),
        decommission(769),
        softShutdown(771),
        hardShutdown(773),
        turnup(775),
        powercycle(777),
        hardreset(781),
        softreset(785),
        swConnUpd(789),
        biosRecovery(792),
        cmosReset(806),
        resetBmc(815),
        updateExtUsers(879),
        updateAdaptor(891),
        activateAdaptor(898),
        configSoL(932),
        unconfigSoL(934),
        diagnosticInterrupt(1036),
        resetKvm(1055),
        updateBIOS(1152),
        activateBIOS(1157),
        resetIpmi(1254),
        fwUpgrade(1256),
        cimcSessionDelete(1478),
        serviceInfraDeploy(1513),
        serviceInfraWithdraw(1518),
        updateBoardController(1525),
        configBoard(1531),
        resetMemoryErrors(1533),
        flashController(1592),
        enableCimcSecureBoot(1611),
        oobStorageAdminConfig(1722),
        clearTPM(1945),
        diskZoningInventory(2045),
        diag(2209),
        cimcSecurityConfig(2242),
        executeActions(2337),
        nvmeSwitchRecovery(2345),
        reinitializeVirtualDrive(2375),
        configureServerPersonality(2401),
        biosPasswordReset(2407),
        cimcSecurityUnconfig(2416),
        dataSanitization(2454)
    }

CucsComputePhysicalFsmStageName ::= TEXTUAL-CONVENTION
    STATUS        current
    DESCRIPTION
        ""
    SYNTAX        INTEGER
    {
        nop(0),
        associateBegin(665),
        associateUpdateIBMCFw(668),
        associateWaitForIBMCFwUpdate(669),
        associateActivateIBMCFw(670),
        associateResetIBMC(671),
        associatePreSanitize(672),
        associateSanitize(673),
        associateConfigUserAccess(674),
        associateBladePowerOff(675),
        associateUpdateBoardCtrlRequest(676),
        associatePollBoardCtrlUpdateStatus(677),
        associatePowerOn(678),
        associateBmcPreconfigPnuOSLocal(679),
        associateBmcPreconfigPnuOSPeer(680),
        associateBmcConfigPnuOS(681),
        associateSwConfigPnuOSLocal(682),
        associateSwConfigPnuOSPeer(683),
        associateUpdateAdaptorNwFwLocal(684),
        associateUpdateAdaptorNwFwPeer(685),
        associateWaitForAdaptorNwFwUpdateLocal(686),
        associateWaitForAdaptorNwFwUpdatePeer(687),
        associateActivateAdaptorNwFwLocal(688),
        associateActivateAdaptorNwFwPeer(689),
        associateNicConfigPnuOSLocal(690),
        associateNicConfigPnuOSPeer(691),
        associateBootPnuos(692),
        associateBootWait(693),
        associateBiosPostCompletion(694),
        associateHagPnuOSConnect(695),
        associatePnuOSIdent(696),
        associatePnuOSPolicy(697),
        associatePnuOSValidate(698),
        associatePnuOSSelfTest(699),
        associateBiosImgUpdate(700),
        associateStorageCtlrImgUpdate(701),
        associateHbaImgUpdate(702),
        associateNicImgUpdate(703),
        associatePnuOSInventory(704),
        associatePnuOSConfig(705),
        associatePnuOSLocalDiskConfig(706),
        associatePnuOSUnloadDrivers(707),
        associateBmcUnconfigPnuOS(708),
        associateNicUnconfigPnuOSLocal(709),
        associateNicUnconfigPnuOSPeer(710),
        associateSwUnconfigPnuOSLocal(711),
        associateSwUnconfigPnuOSPeer(712),
        associateSwConfigHostOSLocal(713),
        associateSwConfigHostOSPeer(714),
        associateNicConfigHostOSLocal(715),
        associateNicConfigHostOSPeer(716),
        associateHagPnuOSDisconnect(717),
        associateConfigSoL(718),
        associatePrepareForBoot(719),
        associateConfigUuid(720),
        associateBootHost(721),
        associateHagHostOSConnect(722),
        associateHostOSIdent(723),
        associateHostOSPolicy(724),
        associateHostOSValidate(725),
        associateHostOSConfig(726),
        disassociateBegin(727),
        disassociateConfigUserAccess(730),
        disassociatePowerOn(731),
        disassociatePreSanitize(732),
        disassociateSanitize(733),
        disassociateNicUnconfigHostOSLocal(734),
        disassociateNicUnconfigHostOSPeer(735),
        disassociateSwUnconfigHostOSLocal(736),
        disassociateSwUnconfigHostOSPeer(737),
        disassociateBmcPreconfigPnuOSLocal(738),
        disassociateBmcPreconfigPnuOSPeer(739),
        disassociateBmcConfigPnuOS(740),
        disassociateSwConfigPnuOSLocal(741),
        disassociateSwConfigPnuOSPeer(742),
        disassociateNicConfigPnuOSLocal(743),
        disassociateNicConfigPnuOSPeer(744),
        disassociateConfigBios(745),
        disassociateBootPnuos(746),
        disassociateBootWait(747),
        disassociateBiosPostCompletion(748),
        disassociateHagPnuOSConnect(749),
        disassociatePnuOSIdent(750),
        disassociatePnuOSPolicy(751),
        disassociatePnuOSValidate(752),
        disassociatePnuOSUnconfig(753),
        disassociatePnuOSScrub(754),
        disassociatePnuOSSelfTest(755),
        disassociateBmcUnconfigPnuOS(756),
        disassociateNicUnconfigPnuOSLocal(757),
        disassociateNicUnconfigPnuOSPeer(758),
        disassociateHagPnuOSDisconnect(759),
        disassociateUnconfigUuid(760),
        disassociateShutdown(761),
        disassociateUnconfigBios(762),
        disassociateSwUnconfigPnuOSLocal(763),
        disassociateSwUnconfigPnuOSPeer(764),
        disassociateUnconfigSoL(765),
        disassociateHandlePooling(766),
        powerCapBegin(767),
        powerCapConfig(768),
        decommissionBegin(769),
        decommissionExecute(770),
        softShutdownBegin(771),
        softShutdownExecute(772),
        hardShutdownBegin(773),
        hardShutdownExecute(774),
        turnupBegin(775),
        turnupExecute(776),
        powercycleBegin(777),
        powercyclePreSanitize(778),
        powercycleSanitize(779),
        powercycleExecute(780),
        hardresetBegin(781),
        hardresetPreSanitize(782),
        hardresetSanitize(783),
        hardresetExecute(784),
        softresetBegin(785),
        softresetPreSanitize(786),
        softresetSanitize(787),
        softresetExecute(788),
        swConnUpdBegin(789),
        swConnUpdA(790),
        swConnUpdB(791),
        biosRecoveryBegin(792),
        biosRecoveryShutdown(793),
        biosRecoveryPreSanitize(794),
        biosRecoverySanitize(795),
        biosRecoverySetupVmediaLocal(796),
        biosRecoverySetupVmediaPeer(797),
        biosRecoveryStart(798),
        biosRecoveryWait(799),
        biosRecoveryCleanup(800),
        biosRecoveryReset(801),
        biosRecoveryTeardownVmediaLocal(802),
        biosRecoveryTeardownVmediaPeer(803),
        cmosResetBegin(806),
        cmosResetPreSanitize(807),
        cmosResetSanitize(808),
        cmosResetExecute(809),
        cmosResetReconfigBios(810),
        cmosResetReconfigUuid(811),
        cmosResetBladePowerOn(812),
        resetBmcBegin(815),
        resetBmcExecute(816),
        updateExtUsersBegin(879),
        updateExtUsersDeploy(880),
        updateAdaptorBegin(891),
        updateAdaptorPowerOn(892),
        updateAdaptorUpdateRequestLocal(893),
        updateAdaptorUpdateRequestPeer(894),
        updateAdaptorPollUpdateStatusLocal(895),
        updateAdaptorPollUpdateStatusPeer(896),
        updateAdaptorPowerOff(897),
        activateAdaptorBegin(898),
        activateAdaptorPowerOn(899),
        activateAdaptorActivateLocal(900),
        activateAdaptorActivatePeer(901),
        activateAdaptorReset(902),
        configSoLBegin(932),
        configSoLExecute(933),
        unconfigSoLBegin(934),
        unconfigSoLExecute(935),
        activateAdaptorFail(940),
        activateAdaptorSuccess(941),
        associateFail(942),
        associateSuccess(943),
        biosRecoveryFail(946),
        biosRecoverySuccess(947),
        cmosResetFail(948),
        cmosResetSuccess(949),
        configSoLFail(950),
        configSoLSuccess(951),
        decommissionFail(952),
        decommissionSuccess(953),
        disassociateFail(954),
        disassociateSuccess(955),
        hardShutdownFail(956),
        hardShutdownSuccess(957),
        hardresetFail(958),
        hardresetSuccess(959),
        powerCapFail(960),
        powerCapSuccess(961),
        powercycleFail(962),
        powercycleSuccess(963),
        resetBmcFail(964),
        resetBmcSuccess(965),
        softShutdownFail(966),
        softShutdownSuccess(967),
        softresetFail(968),
        softresetSuccess(969),
        swConnUpdFail(970),
        swConnUpdSuccess(971),
        turnupFail(972),
        turnupSuccess(973),
        unconfigSoLFail(974),
        unconfigSoLSuccess(975),
        updateAdaptorFail(976),
        updateAdaptorSuccess(977),
        updateExtUsersFail(978),
        updateExtUsersSuccess(979),
        decommissionStopVMediaLocal(1019),
        decommissionStopVMediaPeer(1020),
        biosRecoveryStopVMediaLocal(1021),
        biosRecoveryStopVMediaPeer(1022),
        diagnosticInterruptBegin(1036),
        diagnosticInterruptExecute(1037),
        diagnosticInterruptFail(1038),
        diagnosticInterruptSuccess(1039),
        associateLocalDiskFwUpdate(1040),
        resetKvmBegin(1055),
        resetKvmExecute(1056),
        resetKvmFail(1057),
        resetKvmSuccess(1058),
        associateSwConfigPortNivLocal(1069),
        associateSwConfigPortNivPeer(1070),
        disassociateSwConfigPortNivLocal(1071),
        disassociateSwConfigPortNivPeer(1072),
        associateSolRedirectEnable(1104),
        associateSerialDebugPnuOSConnect(1105),
        associateSerialDebugPnuOSDisconnect(1106),
        associateSolRedirectDisable(1107),
        disassociateSolRedirectEnable(1108),
        disassociateSerialDebugPnuOSConnect(1109),
        disassociateSerialDebugPnuOSDisconnect(1110),
        disassociateSolRedirectDisable(1111),
        decommissionCleanupCIMC(1112),
        updateBIOSBegin(1152),
        updateBIOSClear(1153),
        updateBIOSPollClearStatus(1154),
        updateBIOSUpdateRequest(1155),
        updateBIOSPollUpdateStatus(1156),
        activateBIOSBegin(1157),
        activateBIOSPowerOff(1158),
        activateBIOSClear(1159),
        activateBIOSPollClearStatus(1160),
        activateBIOSActivate(1161),
        activateBIOSPollActivateStatus(1162),
        activateBIOSUpdateTokens(1163),
        activateBIOSPowerOn(1164),
        associateClearBiosUpdate(1169),
        associatePollClearBiosUpdateStatus(1170),
        associateUpdateBiosRequest(1171),
        associatePollBiosUpdateStatus(1172),
        associateActivateBios(1173),
        associatePollBiosActivateStatus(1174),
        associatePnuOSCatalog(1175),
        disassociatePnuOSCatalog(1176),
        activateBIOSFail(1178),
        activateBIOSSuccess(1179),
        updateBIOSFail(1180),
        updateBIOSSuccess(1181),
        associateMarkAdapterForReboot(1247),
        associateDeassertResetBypass(1248),
        associateVerifyFcZoneConfig(1249),
        disassociateDeassertResetBypass(1250),
        disassociateVerifyFcZoneConfig(1251),
        decommissionCleanupPortConfigLocal(1252),
        decommissionCleanupPortConfigPeer(1253),
        resetIpmiBegin(1254),
        resetIpmiExecute(1255),
        fwUpgradeBegin(1256),
        fwUpgradeUpdateIBMCFw(1257),
        fwUpgradeWaitForIBMCFwUpdate(1258),
        fwUpgradeActivateIBMCFw(1259),
        fwUpgradeResetIBMC(1260),
        fwUpgradePreSanitize(1261),
        fwUpgradeSanitize(1262),
        fwUpgradeBladePowerOff(1263),
        fwUpgradeUpdateBoardCtrlRequest(1264),
        fwUpgradePollBoardCtrlUpdateStatus(1265),
        fwUpgradeClearBiosUpdate(1266),
        fwUpgradePollClearBiosUpdateStatus(1267),
        fwUpgradeUpdateBiosRequest(1268),
        fwUpgradePollBiosUpdateStatus(1269),
        fwUpgradeActivateBios(1270),
        fwUpgradePollBiosActivateStatus(1271),
        fwUpgradePowerOn(1272),
        fwUpgradeBmcPreconfigPnuOSLocal(1273),
        fwUpgradeBmcPreconfigPnuOSPeer(1274),
        fwUpgradeSwConfigPortNivLocal(1275),
        fwUpgradeSwConfigPortNivPeer(1276),
        fwUpgradeSwConfigPnuOSLocal(1277),
        fwUpgradeSwConfigPnuOSPeer(1278),
        fwUpgradeUpdateAdaptorNwFwLocal(1279),
        fwUpgradeUpdateAdaptorNwFwPeer(1280),
        fwUpgradeWaitForAdaptorNwFwUpdateLocal(1281),
        fwUpgradeWaitForAdaptorNwFwUpdatePeer(1282),
        fwUpgradeActivateAdaptorNwFwLocal(1283),
        fwUpgradeActivateAdaptorNwFwPeer(1284),
        fwUpgradeNicConfigPnuOSLocal(1285),
        fwUpgradeNicConfigPnuOSPeer(1286),
        fwUpgradeBmcConfigPnuOS(1287),
        fwUpgradeSolRedirectEnable(1288),
        fwUpgradeSerialDebugPnuOSConnect(1289),
        fwUpgradeBootPnuos(1290),
        fwUpgradeBootWait(1291),
        fwUpgradeBiosPostCompletion(1292),
        fwUpgradeHagPnuOSConnect(1293),
        fwUpgradePnuOSIdent(1294),
        fwUpgradePnuOSPolicy(1295),
        fwUpgradePnuOSCatalog(1296),
        fwUpgradePnuOSValidate(1297),
        fwUpgradePnuOSSelfTest(1298),
        fwUpgradeStorageCtlrImgUpdate(1299),
        fwUpgradeHbaImgUpdate(1300),
        fwUpgradeNicImgUpdate(1301),
        fwUpgradeLocalDiskFwUpdate(1302),
        fwUpgradePnuOSConfig(1303),
        fwUpgradePnuOSInventory(1304),
        fwUpgradeBiosImgUpdate(1305),
        fwUpgradePnuOSUnloadDrivers(1306),
        fwUpgradeBmcUnconfigPnuOS(1307),
        fwUpgradeNicUnconfigPnuOSLocal(1308),
        fwUpgradeNicUnconfigPnuOSPeer(1309),
        fwUpgradeSwUnconfigPnuOSLocal(1310),
        fwUpgradeSwUnconfigPnuOSPeer(1311),
        fwUpgradeHagPnuOSDisconnect(1312),
        fwUpgradeSerialDebugPnuOSDisconnect(1313),
        fwUpgradeSolRedirectDisable(1314),
        fwUpgradeShutdown(1315),
        activateAdaptorDeassertResetBypass(1361),
        fwUpgradeDeassertResetBypass(1363),
        fwUpgradeFail(1385),
        fwUpgradeSuccess(1386),
        resetIpmiFail(1387),
        resetIpmiSuccess(1388),
        associateConfigFlexFlash(1471),
        associateSyncPowerState(1472),
        disassociateUnconfigFlexFlash(1473),
        cimcSessionDeleteBegin(1478),
        cimcSessionDeleteExecute(1479),
        cimcSessionDeleteFail(1480),
        cimcSessionDeleteSuccess(1481),
        associatePowerOnPreConfig(1501),
        associateOobStorageInventory(1502),
        associateSwConfigServiceInfraLocal(1503),
        associateSwConfigServiceInfraPeer(1504),
        associateNicConfigServiceInfraLocal(1505),
        associateNicConfigServiceInfraPeer(1506),
        disassociateNicUnconfigServiceInfraLocal(1507),
        disassociateNicUnconfigServiceInfraPeer(1508),
        disassociateConfigFlexFlashScrub(1509),
        serviceInfraDeployBegin(1513),
        serviceInfraDeploySwConfigLocal(1514),
        serviceInfraDeploySwConfigPeer(1515),
        serviceInfraDeployNicConfigLocal(1516),
        serviceInfraDeployNicConfigPeer(1517),
        serviceInfraWithdrawBegin(1518),
        serviceInfraWithdrawSwUnConfigLocal(1519),
        serviceInfraWithdrawSwUnConfigPeer(1520),
        serviceInfraWithdrawNicUnConfigLocal(1521),
        serviceInfraWithdrawNicUnConfigPeer(1522),
        updateBoardControllerBegin(1525),
        updateBoardControllerPrepareForUpdate(1526),
        updateBoardControllerServerPowerOff(1527),
        updateBoardControllerUpdateRequest(1528),
        updateBoardControllerPollUpdateStatus(1529),
        updateBoardControllerServerPowerOn(1530),
        configBoardBegin(1531),
        configBoardConfigMemoryPolicy(1532),
        resetMemoryErrorsBegin(1533),
        resetMemoryErrorsExecute(1534),
        configBoardFail(1542),
        configBoardSuccess(1543),
        resetMemoryErrorsFail(1544),
        resetMemoryErrorsSuccess(1545),
        serviceInfraDeployFail(1546),
        serviceInfraDeploySuccess(1547),
        serviceInfraWithdrawFail(1548),
        serviceInfraWithdrawSuccess(1549),
        updateBoardControllerFail(1550),
        updateBoardControllerSuccess(1551),
        disassociateResetSecureBootConfig(1561),
        associateUnconfigExtMgmtRules(1569),
        associateUnconfigExtMgmtGw(1570),
        associateUnconfigCimcVMedia(1571),
        associateConfigExtMgmtRules(1572),
        associateConfigExtMgmtGw(1573),
        associateConfigCimcVMedia(1574),
        associateGraphicsImageUpdate(1575),
        disassociateConfigKvmMgmtDefaultSetting(1576),
        disassociateUnconfigExtMgmtRules(1577),
        disassociateUnconfigExtMgmtGw(1578),
        disassociateUnconfigCimcVMedia(1579),
        decommissionUnconfigExtMgmtRules(1580),
        decommissionUnconfigExtMgmtGw(1581),
        fwUpgradeUnconfigExtMgmtRules(1582),
        fwUpgradeUnconfigExtMgmtGw(1583),
        fwUpgradeUnconfigCimcVMedia(1584),
        fwUpgradeGraphicsImageUpdate(1585),
        associateDownloadImages(1588),
        associateCopyRemote(1589),
        fwUpgradeDownloadImages(1590),
        fwUpgradeCopyRemote(1591),
        flashControllerBegin(1592),
        flashControllerUpdateFlashLife(1593),
        flashControllerFail(1595),
        flashControllerSuccess(1596),
        associateDeleteCurlDownloadedImages(1598),
        fwUpgradeDeleteCurlDownloadedImages(1599),
        enableCimcSecureBootBegin(1611),
        enableCimcSecureBootUpdateRequest(1612),
        enableCimcSecureBootPollUpdateStatus(1613),
        enableCimcSecureBootActivate(1614),
        enableCimcSecureBootReset(1615),
        enableCimcSecureBootFail(1620),
        enableCimcSecureBootSuccess(1621),
        associateCheckPowerAvailability(1698),
        associatePowerDeployWait(1699),
        associateOobStorageConfig(1700),
        associateVerifyRemoteStorageConfig(1701),
        associateNicConfigParamsHostOSLocal(1702),
        associateNicConfigParamsHostOSPeer(1703),
        associateBmcUpdateHostPreBoot(1704),
        disassociateWaitForUnConfigAppliances(1705),
        disassociateCheckPowerAvailability(1706),
        disassociatePowerDeployWait(1707),
        turnupCheckPowerAvailability(1708),
        turnupPowerDeployWait(1709),
        powercycleCheckPowerAvailability(1710),
        powercyclePowerDeployWait(1711),
        hardresetCheckPowerAvailability(1712),
        hardresetPowerDeployWait(1713),
        softresetCheckPowerAvailability(1714),
        softresetPowerDeployWait(1715),
        biosRecoveryCheckPowerAvailability(1716),
        biosRecoveryPowerDeployWait(1717),
        cmosResetCheckPowerAvailability(1718),
        cmosResetPowerDeployWait(1719),
        fwUpgradeCheckPowerAvailability(1720),
        fwUpgradePowerDeployWait(1721),
        oobStorageAdminConfigBegin(1722),
        oobStorageAdminConfigPreSanitize(1723),
        oobStorageAdminConfigSanitize(1724),
        oobStorageAdminConfigTearDownVMediaLocal(1725),
        oobStorageAdminConfigTearDownVMediaPeer(1726),
        oobStorageAdminConfigBootHost(1727),
        oobStorageAdminConfigBootWait(1728),
        oobStorageAdminConfigOobStorageConfig(1729),
        oobStorageAdminConfigOobStorageInventory(1730),
        oobStorageAdminConfigShutdown(1731),
        activateBIOSCheckPowerAvailability(1800),
        activateBIOSPowerDeployWait(1801),
        updateAdaptorCheckPowerAvailability(1802),
        updateAdaptorPowerDeployWait(1803),
        activateAdaptorCheckPowerAvailability(1804),
        activateAdaptorPowerDeployWait(1805),
        updateBoardControllerCheckPowerAvailability(1806),
        updateBoardControllerPowerDeployWait(1807),
        oobStorageAdminConfigFail(1813),
        oobStorageAdminConfigSuccess(1814),
        associateDeleteImagesRemote(1880),
        disassociateOobDiskScrub(1881),
        fwUpgradeDeleteImagesRemote(1882),
        associateUnlockFirmwareImage(1943),
        decommissionPrecleanupPortConfig(1944),
        clearTPMBegin(1945),
        clearTPMPreSanitize(1946),
        clearTPMSanitize(1947),
        clearTPMClear(1948),
        clearTPMBootHost(1949),
        clearTPMBiosPostCompletion(1950),
        clearTPMReadSmBios(1951),
        clearTPMBladePowerOff(1952),
        clearTPMReconfigBios(1953),
        clearTPMBladePowerOn(1954),
        fwUpgradeUnlockFirmwareImage(1955),
        clearTPMFail(1957),
        clearTPMSuccess(1958),
        clearTPMStopVMediaLocal(1964),
        clearTPMStopVMediaPeer(1965),
        clearTPMSetupVmedia(1966),
        clearTPMUnconfigVmedia(1967),
        updateBoardControllerPowerCycleBoard(1968),
        updateBoardControllerPollBoardCtrlPowerCycle(1969),
        associatePowerCycleBoard(1970),
        associatePollBoardCtrlPowerCycle(1971),
        fwUpgradePowerCycleBoard(1972),
        fwUpgradePollBoardCtrlPowerCycle(1973),
        associateCalculateVlanGroupForHostOSLocal(1978),
        associateCalculateVlanGroupForHostOSPeer(1979),
        associateConfigFanSpeed(1998),
        associateSasExpanderImgUpdate(1999),
        fwUpgradeSasExpanderImgUpdate(2000),
        fwUpgradeOobStorageInventory(2001),
        associateOobSasExpanderImgUpdate(2030),
        associateOobPollSasExpanderUpdateStatus(2031),
        associateOobSasExpanderImgActivate(2032),
        associateOobPollSasExpanderActivateStatus(2033),
        associateCiscoOSOpenGate(2034),
        fwUpgradeOobSasExpanderImgUpdate(2037),
        fwUpgradeOobPollSasExpanderUpdateStatus(2038),
        fwUpgradeOobSasExpanderImgActivate(2039),
        fwUpgradeOobPollSasExpanderActivateStatus(2040),
        fwUpgradeCiscoOSOpenGate(2041),
        oobStorageAdminConfigCheckPowerAvailability(2043),
        oobStorageAdminConfigPowerDeployWait(2044),
        diskZoningInventoryBegin(2045),
        diskZoningInventoryPreSanitize(2046),
        diskZoningInventorySanitize(2047),
        diskZoningInventoryBootHost(2048),
        diskZoningInventoryBootWait(2049),
        diskZoningInventoryStorageInventory(2050),
        diskZoningInventoryShutdown(2051),
        diskZoningInventoryFail(2161),
        diskZoningInventorySuccess(2162),
        activateAdaptorAssertBypassWait(2200),
        diagBegin(2209),
        diagPreSanitize(2210),
        diagSanitize(2211),
        diagCheckPowerAvailability(2212),
        diagDisableScriptableVMedia(2213),
        diagPreconfigVmediaLocal(2214),
        diagPreconfigVmediaPeer(2215),
        diagSetupVmediaLocal(2216),
        diagSetupVmediaPeer(2217),
        diagSetupBootEnvironment(2218),
        diagSerialDebugConnect(2219),
        diagPowerOn(2220),
        diagPowerOnWait(2221),
        diagBiosPostCompletion(2222),
        diagHagConnect(2223),
        diagPnuOSIdent(2224),
        diagRunTests(2225),
        diagLogTransfer(2226),
        diagWaitForDebug(2227),
        diagTeardownVmediaLocal(2228),
        diagTeardownVmediaPeer(2229),
        diagHagDisconnect(2230),
        diagSerialDebugDisconnect(2231),
        diagTearDownBootEnvironment(2232),
        diagShutdown(2233),
        associatePnuOSPeripheralComponentConfig(2234),
        associateConfigMgmtIpRules(2235),
        associateAssertBypassWait(2236),
        associateHostOSConnect(2237),
        associateConfigHostOsAnnotations(2238),
        associateConfigServerIdentity(2239),
        disassociateUnconfigServerIdentity(2240),
        fwUpgradeAssertBypassWait(2241),
        cimcSecurityConfigBegin(2242),
        cimcSecurityConfigKmipCertConfig(2243),
        cimcSecurityConfigKmipSaveCert(2244),
        cimcSecurityConfigFail(2257),
        cimcSecurityConfigSuccess(2258),
        diagFail(2259),
        diagSuccess(2260),
        associateRestoreVdStatus(2271),
        associateOobSasExpanderBootImgActivate(2301),
        associateOobPollSasExpanderBootImgActivateStatus(2302),
        associateMswitchImgUpdate(2303),
        fwUpgradeOobSasExpanderBootImgActivate(2304),
        fwUpgradeOobPollSasExpanderBootImgActivateStatus(2305),
        fwUpgradeMswitchImgUpdate(2306),
        associatePciSwitchImageUpdate(2325),
        associateSharedComponentsOobInventory(2326),
        associateSharedComponentsOobInventoryPeer(2327),
        fwUpgradePciSwitchImageUpdate(2328),
        associatePersistentMemoryDimmFwUpdate(2334),
        associateWaitForBorderConfigCompletionLocal(2335),
        associateWaitForBorderConfigCompletionPeer(2336),
        executeActionsBegin(2337),
        executeActionsSoftShutdown(2338),
        executeActionsExecutePMAction(2339),
        executeActionsPowerOn(2340),
        executeActionsBiosPostCompletion(2341),
        fwUpgradePersistentMemoryDimmFwUpdate(2344),
        nvmeSwitchRecoveryBegin(2345),
        nvmeSwitchRecoveryWaitForAck(2346),
        nvmeSwitchRecoveryExecute(2347),
        nvmeSwitchRecoveryCheckStatus(2348),
        executeActionsFail(2363),
        executeActionsSuccess(2364),
        nvmeSwitchRecoveryFail(2365),
        nvmeSwitchRecoverySuccess(2366),
        reinitializeVirtualDriveBegin(2375),
        reinitializeVirtualDriveExecuteVDAction(2376),
        reinitializeVirtualDriveFail(2377),
        reinitializeVirtualDriveSuccess(2378),
        configureServerPersonalityBegin(2401),
        configureServerPersonalityExecute(2402),
        configureServerPersonalityFail(2403),
        configureServerPersonalitySuccess(2404),
        biosPasswordResetBegin(2407),
        biosPasswordResetPreSanitize(2408),
        biosPasswordResetSanitize(2409),
        biosPasswordResetExecute(2410),
        biosPasswordResetReconfigBios(2411),
        biosPasswordResetReconfigUuid(2412),
        biosPasswordResetCheckPowerAvailability(2413),
        biosPasswordResetPowerDeployWait(2414),
        biosPasswordResetBladePowerOn(2415),
        cimcSecurityUnconfigBegin(2416),
        cimcSecurityUnconfigKmipDelCert(2417),
        biosPasswordResetFail(2418),
        biosPasswordResetSuccess(2419),
        cimcSecurityUnconfigFail(2420),
        cimcSecurityUnconfigSuccess(2421),
        diagPowerDeployWait(2422),
        associateUpdateFruComponents(2424),
        associateWaitForUpdateFruComponents(2425),
        associateWaitForBiosPostCompletion(2426),
        associateUpdateNwSbAdaptorFw(2427),
        associateWaitForNwSbAdaptorFwUpdate(2428),
        associateActivateNwSbAdaptorFw(2429),
        associateWaitForNwSbAdaptorFwActivate(2430),
        fwUpgradeUpdateFruComponents(2433),
        fwUpgradeWaitForUpdateFruComponents(2434),
        fwUpgradeWaitForBiosPostCompletion(2435),
        fwUpgradeUpdateNwSbAdaptorFw(2436),
        fwUpgradeWaitForNwSbAdaptorFwUpdate(2437),
        fwUpgradeActivateNwSbAdaptorFw(2438),
        fwUpgradeWaitForNwSbAdaptorFwActivate(2439),
        associateHybridDriveSlotConfig(2446),
        associateUpdateFruComponentsAfterPoweredOn(2447),
        associateWaitForUpdateFruComponentsAfterPoweredOn(2448),
        associatePowerOffForSbAdaptorActivation(2449),
        associateNVMEVDConfig(2450),
        fwUpgradeUpdateFruComponentsAfterPoweredOn(2451),
        fwUpgradeWaitForUpdateFruComponentsAfterPoweredOn(2452),
        fwUpgradePowerOffForSbAdaptorActivation(2453),
        dataSanitizationBegin(2454),
        dataSanitizationPreSanitize(2455),
        dataSanitizationSanitize(2456),
        dataSanitizationCheckPowerAvailability(2457),
        dataSanitizationPowerDeployWait(2458),
        dataSanitizationDisableScriptableVMedia(2459),
        dataSanitizationPreconfigVmediaLocal(2460),
        dataSanitizationPreconfigVmediaPeer(2461),
        dataSanitizationSetupVmediaLocal(2462),
        dataSanitizationSetupVmediaPeer(2463),
        dataSanitizationSetupBootEnvironment(2464),
        dataSanitizationSerialDebugConnect(2465),
        dataSanitizationPowerOn(2466),
        dataSanitizationPowerOnWait(2467),
        dataSanitizationBiosPostCompletion(2468),
        dataSanitizationHagConnect(2469),
        dataSanitizationPnuOSIdent(2470),
        dataSanitizationStorageComponents(2471),
        dataSanitizationWaitForStorageComponent(2472),
        dataSanitizationTeardownVmediaLocal(2473),
        dataSanitizationTeardownVmediaPeer(2474),
        dataSanitizationHagDisconnect(2475),
        dataSanitizationSerialDebugDisconnect(2476),
        dataSanitizationTearDownBootEnvironment(2477),
        dataSanitizationNetworkAdapter(2478),
        dataSanitizationWaitForNetworkAdapter(2479),
        dataSanitizationHostComponents(2480),
        dataSanitizationWaitForHostComponents(2481),
        dataSanitizationBoardComponents(2482),
        dataSanitizationWaitForBoardComponents(2483),
        dataSanitizationShutdown(2484),
        dataSanitizationFail(2488),
        dataSanitizationSuccess(2489),
        associatePowerOnForStorageInit(2492),
        associateWaitForStorageInit(2493),
        associateConfigStorageRemoteSecurity(2494),
        associatePowerOff(2495),
        associateFetchBiosHealthReport(2496),
        disassociateOobStorageInventory(2497),
        associateSyncPowerStateForStorageInit(2507),
        associatePowerOnPreConfigForStorageInit(2508),
        associateCheckPowerAvailabilityForStorageInit(2509),
        associatePowerDeployWaitForStorageInit(2510)
    }

CucsComputePhysicalFsmTaskFlags ::= TEXTUAL-CONVENTION
    STATUS        current
    DESCRIPTION
        ""
    SYNTAX        BITS
    {
        samDmeComputePhysicalFwUpgradeConfigPnuos(0),
        samDmeComputePhysicalFwUpgradeConfigAdaptorNwFw(1),
        samDmeComputePhysicalFwUpgradeConfigMgmtFw(2),
        samDmeComputePhysicalFwUpgradeConfigBoardCtrlFw(3),
        samDmeComputePhysicalFwUpgradeConfigBmcBiosUpdate(4),
        samDmeComputePhysicalAssociateFlexflashConfig(9),
        samDmeComputePhysicalAssociatePowerForceConfig(10),
        samDmeComputePhysicalFwUpgradePrepareForUpdate(11),
        samDmeComputePhysicalAssociateConfigAssetTag(12),
        samDmeComputePhysicalAssociateVmediaConfig(13),
        samDmeComputePhysicalAssociateGraphicsCardConfig(14),
        samDmeComputePhysicalAssociateHostAgentConfig(15),
        samDmeComputePhysicalAssociateStorageSecurity(16),
        samDmeComputePhysicalCimcSecurityConfigCertPolicy(17),
        samDmeComputePhysicalCimcSecurityConfigSaveCert(18),
        samDmeComputePhysicalFwUpgradeSasExpBootFw(20),
        samDmeComputePhysicalOobStorageAdminConfigOobStorageConfig(22),
        samDmeComputePhysicalDiagDiagCancel(23),
        samDmeComputePhysicalAssociateRemoteStorageConfig(24),
        samDmeComputePhysicalAssociateNicParamConfig(25),
        samDmeComputePhysicalExecuteActionsSkipReboot(26),
        samDmeComputePhysicalAssociateSwitchConfig(27),
        samDmeComputePhysicalAssociateHostConfig(28),
        samDmeComputePhysicalAssociateHostReboot(29),
        samDmeComputePhysicalAssociateIfConfig(30),
        samDmeComputePhysicalAssociateNicConfig(31),
        samDmeComputePhysicalAssociateAdaptorNwFwConfig(32),
        samDmeComputePhysicalAssociateMgmtFwConfig(33),
        samDmeComputePhysicalAssociateSnicConfig(34),
        samDmeComputePhysicalSoftShutdownNoHardshutdown(35),
        samDmeComputePhysicalAssociateSolConfig(36),
        samDmeComputePhysicalAssociateEpAuthConfig(37),
        samDmeComputePhysicalDisassociateSolConfig(38),
        samDmeComputePhysicalDisassociateSwitchUnconfig(39),
        samDmeComputePhysicalActivateAdaptorActivate(40),
        samDmeComputePhysicalActivateAdaptorReset(41),
        samDmeComputePhysicalCmosResetAlways(42),
        samDmeComputePhysicalCmosResetSetUuidBiosBoot(43),
        samDmeComputePhysicalFwUpgradeSasExpRegFw(44),
        samDmeComputePhysicalDiskZoningInventoryDiskZoningConfig(45),
        samDmeComputePhysicalAssociateAdaptorNwFwPnuosConfig(46),
        samDmeComputePhysicalFwUpgradeConfigPnuosAdaptorNwFw(47),
        samDmeComputePhysicalAssociateBmcFrucompUpdate(48),
        samDmeComputePhysicalFwUpgradeConfigBmcFrucompUpdate(49),
        samDmeComputePhysicalAssociateHybridSlotConfig(50),
        samDmeComputePhysicalAssociateNvmeVdConfig(51),
        samDmeComputePhysicalFwUpgradeActivateSbAdaptorNwFw(52),
        samDmeComputePhysicalFwUpgradeActivateBmcFrucomp(53),
        samDmeComputePhysicalDataSanitizationHostDomain(54),
        samDmeComputePhysicalDataSanitizationBoardDomain(55),
        samDmeComputePhysicalAssociateBmcBiosUpdate(58),
        samDmeComputePhysicalAssociateLsRename(62)
    }

CucsComputePhysicalFsmTaskItem ::= TEXTUAL-CONVENTION
    STATUS        current
    DESCRIPTION
        ""
    SYNTAX        INTEGER
    {
        nop(0),
        associate(634),
        disassociate(680),
        decommission(711),
        softShutdown(713),
        hardShutdown(715),
        turnup(717),
        powercycle(719),
        hardreset(723),
        softreset(727),
        swConnUpd(731),
        biosRecovery(734),
        cmosReset(748),
        resetBmc(752),
        updateExtUsers(754),
        updateAdaptor(756),
        activateAdaptor(761),
        configSoL(765),
        unconfigSoL(767),
        diagnosticInterrupt(1036),
        resetKvm(1055),
        updateBIOS(1152),
        activateBIOS(1157),
        resetIpmi(1254),
        fwUpgrade(1256),
        cimcSessionDelete(1478),
        serviceInfraDeploy(1513),
        serviceInfraWithdraw(1518),
        updateBoardController(1525),
        configBoard(1531),
        resetMemoryErrors(1533),
        flashController(1592),
        enableCimcSecureBoot(1611),
        oobStorageAdminConfig(1722),
        clearTPM(1945),
        diskZoningInventory(2045),
        diag(2209),
        cimcSecurityConfig(2242),
        executeActions(2337),
        nvmeSwitchRecovery(2345),
        reinitializeVirtualDrive(2375),
        configureServerPersonality(2401),
        biosPasswordReset(2407),
        cimcSecurityUnconfig(2416),
        dataSanitization(2454)
    }

CucsComputePollReadinessState ::= TEXTUAL-CONVENTION
    STATUS        current
    DESCRIPTION
        ""
    SYNTAX        INTEGER
    {
        initializing(1),
        timedout(2),
        ready(3)
    }

CucsComputePollingInterval ::= TEXTUAL-CONVENTION
    STATUS        current
    DESCRIPTION
        ""
    SYNTAX        INTEGER
    {
        n5Min(5),
        n10Min(10),
        n15Min(15),
        n20Min(20),
        n30Min(30),
        n45Min(45),
        n60Min(60)
    }

CucsComputePollingState ::= TEXTUAL-CONVENTION
    STATUS        current
    DESCRIPTION
        ""
    SYNTAX        INTEGER
    {
        started(1),
        complete(2),
        pendingRebalance(3),
        rebalancing(4),
        systemInit(5),
        initDone(6)
    }

CucsComputePooledEnclosureComputeSlotServerInstanceId ::= TEXTUAL-CONVENTION
    STATUS        current
    DESCRIPTION
        ""
    SYNTAX        Gauge32 (1..8)

CucsComputePooledEnclosureComputeSlotSlotId ::= TEXTUAL-CONVENTION
    STATUS        current
    DESCRIPTION
        ""
    SYNTAX        Gauge32 (1..8)

CucsComputePooledRackUnitId ::= TEXTUAL-CONVENTION
    STATUS        current
    DESCRIPTION
        ""
    SYNTAX        Gauge32 (1..255)

CucsComputePooledSlotSlotId ::= TEXTUAL-CONVENTION
    STATUS        current
    DESCRIPTION
        ""
    SYNTAX        Gauge32 (1..8)

CucsComputePortDiscPolicyEthBreakoutAutoDiscovery ::= TEXTUAL-CONVENTION
    STATUS        current
    DESCRIPTION
        ""
    SYNTAX        INTEGER
    {
        disabled(0),
        enabled(1)
    }

CucsComputePortDiscPolicyEthSvrAutoDiscovery ::= TEXTUAL-CONVENTION
    STATUS        current
    DESCRIPTION
        ""
    SYNTAX        INTEGER
    {
        disabled(0),
        enabled(1)
    }

CucsComputePowerExtendedMode ::= TEXTUAL-CONVENTION
    STATUS        current
    DESCRIPTION
        ""
    SYNTAX        INTEGER
    {
        disable(0),
        enable(1)
    }

CucsComputePowerSaveMode ::= TEXTUAL-CONVENTION
    STATUS        current
    DESCRIPTION
        ""
    SYNTAX        INTEGER
    {
        disable(0),
        enable(1)
    }

CucsComputePowerSyncOption ::= TEXTUAL-CONVENTION
    STATUS        current
    DESCRIPTION
        ""
    SYNTAX        INTEGER
    {
        default(0),
        alwaysSync(1),
        neverSync(2)
    }

CucsComputePowerTransitionSrc ::= TEXTUAL-CONVENTION
    STATUS        current
    DESCRIPTION
        ""
    SYNTAX        INTEGER
    {
        unknown(0),
        userUnknown(1),
        userFp(2),
        software(3),
        softwareMcserver(4)
    }

CucsComputePsuClusterState ::= TEXTUAL-CONVENTION
    STATUS        current
    DESCRIPTION
        ""
    SYNTAX        INTEGER
    {
        unknown(0),
        slot1Master(1),
        slot2Master(2),
        notClustered(3),
        nA(4)
    }

CucsComputePsuControlExtendedMode ::= TEXTUAL-CONVENTION
    STATUS        current
    DESCRIPTION
        ""
    SYNTAX        INTEGER
    {
        disable(0),
        enable(1)
    }

CucsComputePsuControlMode ::= TEXTUAL-CONVENTION
    STATUS        current
    DESCRIPTION
        ""
    SYNTAX        INTEGER
    {
        disable(0),
        enable(1)
    }

CucsComputePsuControlRedundancy ::= TEXTUAL-CONVENTION
    STATUS        current
    DESCRIPTION
        ""
    SYNTAX        INTEGER
    {
        unknown(0),
        nonRedundant(1),
        nPlus1(2),
        grid(3),
        nPlus2(4)
    }

CucsComputePsuRedundancy ::= TEXTUAL-CONVENTION
    STATUS        current
    DESCRIPTION
        ""
    SYNTAX        INTEGER
    {
        nonRedundant(1),
        nPlus1(2),
        grid(3),
        nPlus2(4)
    }

CucsComputePsuRedundancyOperQualifier ::= TEXTUAL-CONVENTION
    STATUS        current
    DESCRIPTION
        ""
    SYNTAX        BITS
    {
        redundancyLost(0),
        redundancyDegraded(1),
        nonRedundantSufficientResources(2),
        nonRedundantInsufficientResources(3)
    }

CucsComputePsuRedundancyOperState ::= TEXTUAL-CONVENTION
    STATUS        current
    DESCRIPTION
        ""
    SYNTAX        INTEGER
    {
        unknown(0),
        ok(1),
        failed(2),
        degraded(3)
    }

CucsComputePwrChangeSource ::= TEXTUAL-CONVENTION
    STATUS        current
    DESCRIPTION
        ""
    SYNTAX        INTEGER
    {
        none(0),
        unknown(1),
        hostPwrTransition(2),
        software(3),
        userFrontPanel(4),
        ucsTurnup(5),
        ucsHardShutdown(6),
        ucsSoftShutdown(7),
        ucsPowercycle(8),
        ucsHardreset(9),
        ucsSoftreset(10),
        ucsBladeShutdown(11),
        ucsServerDiscover(12),
        ucsAssociate(13),
        ucsDisassociate(14),
        ucsFwUpgrade(15),
        ucsOobAdminConfig(16),
        ucsDiskZoningInventory(17),
        ucsUpdateBoardctrlFw(18),
        ucsUpdateAdaptorFw(19),
        ucsActivateAdaptorFw(20),
        ucsActivateBiosFw(21),
        ucsBiosRecovery(22),
        ucsCmosReset(23),
        ucsRackunitDiscover(24),
        ucsRackUnitAdapterReset(25),
        ucsClearTpm(26),
        ucsDiagnosticInterrupt(27),
        ucsServerunitDiscover(28),
        ucsDiag(29),
        ucsBiosPasswordReset(30)
    }

CucsComputeRackConnLinkPolicyRackId ::= TEXTUAL-CONVENTION
    STATUS        current
    DESCRIPTION
        ""
    SYNTAX        Gauge32 (1..255)

CucsComputeRackQualMaxId ::= TEXTUAL-CONVENTION
    STATUS        current
    DESCRIPTION
        ""
    SYNTAX        Gauge32 (1..255)

CucsComputeRackQualMinId ::= TEXTUAL-CONVENTION
    STATUS        current
    DESCRIPTION
        ""
    SYNTAX        Gauge32 (1..255)

CucsComputeRackUnitId ::= TEXTUAL-CONVENTION
    STATUS        current
    DESCRIPTION
        ""
    SYNTAX        Gauge32 (1..255)

CucsComputeRackUnitFsmCurrentFsm ::= TEXTUAL-CONVENTION
    STATUS        current
    DESCRIPTION
        ""
    SYNTAX        INTEGER
    {
        nop(0),
        associate(665),
        disassociate(727),
        powerCap(767),
        decommission(769),
        softShutdown(771),
        hardShutdown(773),
        turnup(775),
        powercycle(777),
        hardreset(781),
        softreset(785),
        swConnUpd(789),
        biosRecovery(792),
        cmosReset(806),
        resetBmc(815),
        discover(819),
        updateExtUsers(879),
        updateAdaptor(891),
        activateAdaptor(898),
        configSoL(932),
        unconfigSoL(934),
        diagnosticInterrupt(1036),
        resetKvm(1055),
        offline(1064),
        updateBIOS(1152),
        activateBIOS(1157),
        resetIpmi(1254),
        fwUpgrade(1256),
        adapterReset(1316),
        cimcSessionDelete(1478),
        createDhcpEntry(1510),
        serviceInfraDeploy(1513),
        serviceInfraWithdraw(1518),
        updateBoardController(1525),
        configBoard(1531),
        resetMemoryErrors(1533),
        flashController(1592),
        enableCimcSecureBoot(1611),
        oobStorageAdminConfig(1722),
        clearTPM(1945),
        diskZoningInventory(2045),
        diag(2209),
        cimcSecurityConfig(2242),
        executeActions(2337),
        nvmeSwitchRecovery(2345),
        reinitializeVirtualDrive(2375),
        configureServerPersonality(2401),
        biosPasswordReset(2407),
        cimcSecurityUnconfig(2416),
        dataSanitization(2454)
    }

CucsComputeRackUnitFsmStageName ::= TEXTUAL-CONVENTION
    STATUS        current
    DESCRIPTION
        ""
    SYNTAX        INTEGER
    {
        nop(0),
        associateBegin(665),
        associateUpdateIBMCFw(668),
        associateWaitForIBMCFwUpdate(669),
        associateActivateIBMCFw(670),
        associateResetIBMC(671),
        associatePreSanitize(672),
        associateSanitize(673),
        associateConfigUserAccess(674),
        associateBladePowerOff(675),
        associateUpdateBoardCtrlRequest(676),
        associatePollBoardCtrlUpdateStatus(677),
        associatePowerOn(678),
        associateBmcPreconfigPnuOSLocal(679),
        associateBmcPreconfigPnuOSPeer(680),
        associateBmcConfigPnuOS(681),
        associateSwConfigPnuOSLocal(682),
        associateSwConfigPnuOSPeer(683),
        associateUpdateAdaptorNwFwLocal(684),
        associateUpdateAdaptorNwFwPeer(685),
        associateWaitForAdaptorNwFwUpdateLocal(686),
        associateWaitForAdaptorNwFwUpdatePeer(687),
        associateActivateAdaptorNwFwLocal(688),
        associateActivateAdaptorNwFwPeer(689),
        associateNicConfigPnuOSLocal(690),
        associateNicConfigPnuOSPeer(691),
        associateBootPnuos(692),
        associateBootWait(693),
        associateBiosPostCompletion(694),
        associateHagPnuOSConnect(695),
        associatePnuOSIdent(696),
        associatePnuOSPolicy(697),
        associatePnuOSValidate(698),
        associatePnuOSSelfTest(699),
        associateBiosImgUpdate(700),
        associateStorageCtlrImgUpdate(701),
        associateHbaImgUpdate(702),
        associateNicImgUpdate(703),
        associatePnuOSInventory(704),
        associatePnuOSConfig(705),
        associatePnuOSLocalDiskConfig(706),
        associatePnuOSUnloadDrivers(707),
        associateBmcUnconfigPnuOS(708),
        associateNicUnconfigPnuOSLocal(709),
        associateNicUnconfigPnuOSPeer(710),
        associateSwUnconfigPnuOSLocal(711),
        associateSwUnconfigPnuOSPeer(712),
        associateSwConfigHostOSLocal(713),
        associateSwConfigHostOSPeer(714),
        associateNicConfigHostOSLocal(715),
        associateNicConfigHostOSPeer(716),
        associateHagPnuOSDisconnect(717),
        associateConfigSoL(718),
        associatePrepareForBoot(719),
        associateConfigUuid(720),
        associateBootHost(721),
        associateHagHostOSConnect(722),
        associateHostOSIdent(723),
        associateHostOSPolicy(724),
        associateHostOSValidate(725),
        associateHostOSConfig(726),
        disassociateBegin(727),
        disassociateConfigUserAccess(730),
        disassociatePowerOn(731),
        disassociatePreSanitize(732),
        disassociateSanitize(733),
        disassociateNicUnconfigHostOSLocal(734),
        disassociateNicUnconfigHostOSPeer(735),
        disassociateSwUnconfigHostOSLocal(736),
        disassociateSwUnconfigHostOSPeer(737),
        disassociateBmcPreconfigPnuOSLocal(738),
        disassociateBmcPreconfigPnuOSPeer(739),
        disassociateBmcConfigPnuOS(740),
        disassociateSwConfigPnuOSLocal(741),
        disassociateSwConfigPnuOSPeer(742),
        disassociateNicConfigPnuOSLocal(743),
        disassociateNicConfigPnuOSPeer(744),
        disassociateConfigBios(745),
        disassociateBootPnuos(746),
        disassociateBootWait(747),
        disassociateBiosPostCompletion(748),
        disassociateHagPnuOSConnect(749),
        disassociatePnuOSIdent(750),
        disassociatePnuOSPolicy(751),
        disassociatePnuOSValidate(752),
        disassociatePnuOSUnconfig(753),
        disassociatePnuOSScrub(754),
        disassociatePnuOSSelfTest(755),
        disassociateBmcUnconfigPnuOS(756),
        disassociateNicUnconfigPnuOSLocal(757),
        disassociateNicUnconfigPnuOSPeer(758),
        disassociateHagPnuOSDisconnect(759),
        disassociateUnconfigUuid(760),
        disassociateShutdown(761),
        disassociateUnconfigBios(762),
        disassociateSwUnconfigPnuOSLocal(763),
        disassociateSwUnconfigPnuOSPeer(764),
        disassociateUnconfigSoL(765),
        disassociateHandlePooling(766),
        powerCapBegin(767),
        powerCapConfig(768),
        decommissionBegin(769),
        decommissionExecute(770),
        softShutdownBegin(771),
        softShutdownExecute(772),
        hardShutdownBegin(773),
        hardShutdownExecute(774),
        turnupBegin(775),
        turnupExecute(776),
        powercycleBegin(777),
        powercyclePreSanitize(778),
        powercycleSanitize(779),
        powercycleExecute(780),
        hardresetBegin(781),
        hardresetPreSanitize(782),
        hardresetSanitize(783),
        hardresetExecute(784),
        softresetBegin(785),
        softresetPreSanitize(786),
        softresetSanitize(787),
        softresetExecute(788),
        swConnUpdBegin(789),
        swConnUpdA(790),
        swConnUpdB(791),
        biosRecoveryBegin(792),
        biosRecoveryShutdown(793),
        biosRecoveryPreSanitize(794),
        biosRecoverySanitize(795),
        biosRecoverySetupVmediaLocal(796),
        biosRecoverySetupVmediaPeer(797),
        biosRecoveryStart(798),
        biosRecoveryWait(799),
        biosRecoveryCleanup(800),
        biosRecoveryReset(801),
        biosRecoveryTeardownVmediaLocal(802),
        biosRecoveryTeardownVmediaPeer(803),
        cmosResetBegin(806),
        cmosResetPreSanitize(807),
        cmosResetSanitize(808),
        cmosResetExecute(809),
        cmosResetReconfigBios(810),
        cmosResetReconfigUuid(811),
        cmosResetBladePowerOn(812),
        resetBmcBegin(815),
        resetBmcExecute(816),
        discoverBegin(819),
        discoverBmcConfigureConnLocal(820),
        discoverSwConfigureConnLocal(821),
        discoverBmcConfigureConnPeer(822),
        discoverSwConfigureConnPeer(823),
        discoverBmcPresence(826),
        discoverBmcInventory(827),
        discoverPreSanitize(828),
        discoverSanitize(829),
        discoverConfigUserAccess(830),
        discoverSwConfigPnuOSLocal(831),
        discoverSwConfigPnuOSPeer(832),
        discoverBmcPreconfigPnuOSLocal(833),
        discoverBmcPreconfigPnuOSPeer(834),
        discoverBmcConfigPnuOS(835),
        discoverBootPnuos(836),
        discoverBootWait(837),
        discoverBiosPostCompletion(838),
        discoverReadSmbios(839),
        discoverHagConnect(841),
        discoverPnuOSIdent(842),
        discoverPnuOSPolicy(843),
        discoverPnuOSInventory(844),
        discoverPnuOSScrub(845),
        discoverPnuOSConnectivity(846),
        discoverPnuOSConnStatus(847),
        discoverSwPnuOSConnectivityLocal(848),
        discoverSwPnuOSConnectivityPeer(849),
        discoverPnuOSSelfTest(850),
        discoverBmcUnconfigPnuOS(851),
        discoverHagDisconnect(852),
        discoverBmcShutdownDiscovered(853),
        discoverHandlePooling(854),
        discoverSuccess(855),
        discoverFail(856),
        updateExtUsersBegin(879),
        updateExtUsersDeploy(880),
        updateAdaptorBegin(891),
        updateAdaptorPowerOn(892),
        updateAdaptorUpdateRequestLocal(893),
        updateAdaptorUpdateRequestPeer(894),
        updateAdaptorPollUpdateStatusLocal(895),
        updateAdaptorPollUpdateStatusPeer(896),
        updateAdaptorPowerOff(897),
        activateAdaptorBegin(898),
        activateAdaptorPowerOn(899),
        activateAdaptorActivateLocal(900),
        activateAdaptorActivatePeer(901),
        activateAdaptorReset(902),
        configSoLBegin(932),
        configSoLExecute(933),
        unconfigSoLBegin(934),
        unconfigSoLExecute(935),
        activateAdaptorFail(940),
        activateAdaptorSuccess(941),
        associateFail(942),
        associateSuccess(943),
        biosRecoveryFail(946),
        biosRecoverySuccess(947),
        cmosResetFail(948),
        cmosResetSuccess(949),
        configSoLFail(950),
        configSoLSuccess(951),
        decommissionFail(952),
        decommissionSuccess(953),
        disassociateFail(954),
        disassociateSuccess(955),
        hardShutdownFail(956),
        hardShutdownSuccess(957),
        hardresetFail(958),
        hardresetSuccess(959),
        powerCapFail(960),
        powerCapSuccess(961),
        powercycleFail(962),
        powercycleSuccess(963),
        resetBmcFail(964),
        resetBmcSuccess(965),
        softShutdownFail(966),
        softShutdownSuccess(967),
        softresetFail(968),
        softresetSuccess(969),
        swConnUpdFail(970),
        swConnUpdSuccess(971),
        turnupFail(972),
        turnupSuccess(973),
        unconfigSoLFail(974),
        unconfigSoLSuccess(975),
        updateAdaptorFail(976),
        updateAdaptorSuccess(977),
        updateExtUsersFail(978),
        updateExtUsersSuccess(979),
        decommissionStopVMediaLocal(1019),
        decommissionStopVMediaPeer(1020),
        biosRecoveryStopVMediaLocal(1021),
        biosRecoveryStopVMediaPeer(1022),
        discoverConfigDiscoveryMode(1023),
        discoverSwUnconfigPortNivLocal(1024),
        discoverSwUnconfigPortNivPeer(1025),
        discoverSwConfigPortNivLocal(1027),
        discoverSwConfigPortNivPeer(1028),
        discoverNicInventoryLocal(1029),
        discoverNicInventoryPeer(1030),
        discoverConfigNivMode(1031),
        diagnosticInterruptBegin(1036),
        diagnosticInterruptExecute(1037),
        diagnosticInterruptFail(1038),
        diagnosticInterruptSuccess(1039),
        associateLocalDiskFwUpdate(1040),
        discoverWaitForConnReady(1050),
        resetKvmBegin(1055),
        resetKvmExecute(1056),
        resetKvmFail(1057),
        resetKvmSuccess(1058),
        offlineBegin(1064),
        offlineCleanupLocal(1065),
        offlineCleanupPeer(1066),
        offlineSwUnconfigureLocal(1067),
        offlineSwUnconfigurePeer(1068),
        associateSwConfigPortNivLocal(1069),
        associateSwConfigPortNivPeer(1070),
        disassociateSwConfigPortNivLocal(1071),
        disassociateSwConfigPortNivPeer(1072),
        offlineFail(1073),
        offlineSuccess(1074),
        discoverSolRedirectEnable(1092),
        discoverSerialDebugConnect(1093),
        discoverSerialDebugDisconnect(1094),
        discoverSolRedirectDisable(1095),
        associateSolRedirectEnable(1104),
        associateSerialDebugPnuOSConnect(1105),
        associateSerialDebugPnuOSDisconnect(1106),
        associateSolRedirectDisable(1107),
        disassociateSolRedirectEnable(1108),
        disassociateSerialDebugPnuOSConnect(1109),
        disassociateSerialDebugPnuOSDisconnect(1110),
        disassociateSolRedirectDisable(1111),
        decommissionCleanupCIMC(1112),
        updateBIOSBegin(1152),
        updateBIOSClear(1153),
        updateBIOSPollClearStatus(1154),
        updateBIOSUpdateRequest(1155),
        updateBIOSPollUpdateStatus(1156),
        activateBIOSBegin(1157),
        activateBIOSPowerOff(1158),
        activateBIOSClear(1159),
        activateBIOSPollClearStatus(1160),
        activateBIOSActivate(1161),
        activateBIOSPollActivateStatus(1162),
        activateBIOSUpdateTokens(1163),
        activateBIOSPowerOn(1164),
        associateClearBiosUpdate(1169),
        associatePollClearBiosUpdateStatus(1170),
        associateUpdateBiosRequest(1171),
        associatePollBiosUpdateStatus(1172),
        associateActivateBios(1173),
        associatePollBiosActivateStatus(1174),
        associatePnuOSCatalog(1175),
        disassociatePnuOSCatalog(1176),
        discoverPnuOSCatalog(1177),
        activateBIOSFail(1178),
        activateBIOSSuccess(1179),
        updateBIOSFail(1180),
        updateBIOSSuccess(1181),
        discoverBladePowerOff(1243),
        discoverNicConfigPnuOSLocal(1244),
        discoverNicConfigPnuOSPeer(1245),
        associateMarkAdapterForReboot(1247),
        associateDeassertResetBypass(1248),
        associateVerifyFcZoneConfig(1249),
        disassociateDeassertResetBypass(1250),
        disassociateVerifyFcZoneConfig(1251),
        decommissionCleanupPortConfigLocal(1252),
        decommissionCleanupPortConfigPeer(1253),
        resetIpmiBegin(1254),
        resetIpmiExecute(1255),
        fwUpgradeBegin(1256),
        fwUpgradeUpdateIBMCFw(1257),
        fwUpgradeWaitForIBMCFwUpdate(1258),
        fwUpgradeActivateIBMCFw(1259),
        fwUpgradeResetIBMC(1260),
        fwUpgradePreSanitize(1261),
        fwUpgradeSanitize(1262),
        fwUpgradeBladePowerOff(1263),
        fwUpgradeUpdateBoardCtrlRequest(1264),
        fwUpgradePollBoardCtrlUpdateStatus(1265),
        fwUpgradeClearBiosUpdate(1266),
        fwUpgradePollClearBiosUpdateStatus(1267),
        fwUpgradeUpdateBiosRequest(1268),
        fwUpgradePollBiosUpdateStatus(1269),
        fwUpgradeActivateBios(1270),
        fwUpgradePollBiosActivateStatus(1271),
        fwUpgradePowerOn(1272),
        fwUpgradeBmcPreconfigPnuOSLocal(1273),
        fwUpgradeBmcPreconfigPnuOSPeer(1274),
        fwUpgradeSwConfigPortNivLocal(1275),
        fwUpgradeSwConfigPortNivPeer(1276),
        fwUpgradeSwConfigPnuOSLocal(1277),
        fwUpgradeSwConfigPnuOSPeer(1278),
        fwUpgradeUpdateAdaptorNwFwLocal(1279),
        fwUpgradeUpdateAdaptorNwFwPeer(1280),
        fwUpgradeWaitForAdaptorNwFwUpdateLocal(1281),
        fwUpgradeWaitForAdaptorNwFwUpdatePeer(1282),
        fwUpgradeActivateAdaptorNwFwLocal(1283),
        fwUpgradeActivateAdaptorNwFwPeer(1284),
        fwUpgradeNicConfigPnuOSLocal(1285),
        fwUpgradeNicConfigPnuOSPeer(1286),
        fwUpgradeBmcConfigPnuOS(1287),
        fwUpgradeSolRedirectEnable(1288),
        fwUpgradeSerialDebugPnuOSConnect(1289),
        fwUpgradeBootPnuos(1290),
        fwUpgradeBootWait(1291),
        fwUpgradeBiosPostCompletion(1292),
        fwUpgradeHagPnuOSConnect(1293),
        fwUpgradePnuOSIdent(1294),
        fwUpgradePnuOSPolicy(1295),
        fwUpgradePnuOSCatalog(1296),
        fwUpgradePnuOSValidate(1297),
        fwUpgradePnuOSSelfTest(1298),
        fwUpgradeStorageCtlrImgUpdate(1299),
        fwUpgradeHbaImgUpdate(1300),
        fwUpgradeNicImgUpdate(1301),
        fwUpgradeLocalDiskFwUpdate(1302),
        fwUpgradePnuOSConfig(1303),
        fwUpgradePnuOSInventory(1304),
        fwUpgradeBiosImgUpdate(1305),
        fwUpgradePnuOSUnloadDrivers(1306),
        fwUpgradeBmcUnconfigPnuOS(1307),
        fwUpgradeNicUnconfigPnuOSLocal(1308),
        fwUpgradeNicUnconfigPnuOSPeer(1309),
        fwUpgradeSwUnconfigPnuOSLocal(1310),
        fwUpgradeSwUnconfigPnuOSPeer(1311),
        fwUpgradeHagPnuOSDisconnect(1312),
        fwUpgradeSerialDebugPnuOSDisconnect(1313),
        fwUpgradeSolRedirectDisable(1314),
        fwUpgradeShutdown(1315),
        adapterResetBegin(1316),
        adapterResetPreSanitize(1317),
        adapterResetSanitize(1318),
        adapterResetDeassertResetBypass(1319),
        adapterResetPowerCycle(1320),
        activateAdaptorDeassertResetBypass(1361),
        fwUpgradeDeassertResetBypass(1363),
        fwUpgradeFail(1385),
        fwUpgradeSuccess(1386),
        resetIpmiFail(1387),
        resetIpmiSuccess(1388),
        adapterResetFail(1389),
        adapterResetSuccess(1390),
        associateConfigFlexFlash(1471),
        associateSyncPowerState(1472),
        disassociateUnconfigFlexFlash(1473),
        cimcSessionDeleteBegin(1478),
        cimcSessionDeleteExecute(1479),
        cimcSessionDeleteFail(1480),
        cimcSessionDeleteSuccess(1481),
        associatePowerOnPreConfig(1501),
        associateOobStorageInventory(1502),
        associateSwConfigServiceInfraLocal(1503),
        associateSwConfigServiceInfraPeer(1504),
        associateNicConfigServiceInfraLocal(1505),
        associateNicConfigServiceInfraPeer(1506),
        disassociateNicUnconfigServiceInfraLocal(1507),
        disassociateNicUnconfigServiceInfraPeer(1508),
        disassociateConfigFlexFlashScrub(1509),
        createDhcpEntryBegin(1510),
        createDhcpEntryExecuteLocal(1511),
        createDhcpEntryExecutePeer(1512),
        serviceInfraDeployBegin(1513),
        serviceInfraDeploySwConfigLocal(1514),
        serviceInfraDeploySwConfigPeer(1515),
        serviceInfraDeployNicConfigLocal(1516),
        serviceInfraDeployNicConfigPeer(1517),
        serviceInfraWithdrawBegin(1518),
        serviceInfraWithdrawSwUnConfigLocal(1519),
        serviceInfraWithdrawSwUnConfigPeer(1520),
        serviceInfraWithdrawNicUnConfigLocal(1521),
        serviceInfraWithdrawNicUnConfigPeer(1522),
        discoverOobStorageInventory(1523),
        discoverConfigFlexFlashScrub(1524),
        updateBoardControllerBegin(1525),
        updateBoardControllerPrepareForUpdate(1526),
        updateBoardControllerServerPowerOff(1527),
        updateBoardControllerUpdateRequest(1528),
        updateBoardControllerPollUpdateStatus(1529),
        updateBoardControllerServerPowerOn(1530),
        configBoardBegin(1531),
        configBoardConfigMemoryPolicy(1532),
        resetMemoryErrorsBegin(1533),
        resetMemoryErrorsExecute(1534),
        configBoardFail(1542),
        configBoardSuccess(1543),
        resetMemoryErrorsFail(1544),
        resetMemoryErrorsSuccess(1545),
        serviceInfraDeployFail(1546),
        serviceInfraDeploySuccess(1547),
        serviceInfraWithdrawFail(1548),
        serviceInfraWithdrawSuccess(1549),
        updateBoardControllerFail(1550),
        updateBoardControllerSuccess(1551),
        createDhcpEntryFail(1552),
        createDhcpEntrySuccess(1553),
        disassociateResetSecureBootConfig(1561),
        discoverUnconfigExtMgmtRules(1563),
        discoverUnconfigExtMgmtGw(1564),
        discoverUnconfigCimcVMedia(1565),
        associateUnconfigExtMgmtRules(1569),
        associateUnconfigExtMgmtGw(1570),
        associateUnconfigCimcVMedia(1571),
        associateConfigExtMgmtRules(1572),
        associateConfigExtMgmtGw(1573),
        associateConfigCimcVMedia(1574),
        associateGraphicsImageUpdate(1575),
        disassociateConfigKvmMgmtDefaultSetting(1576),
        disassociateUnconfigExtMgmtRules(1577),
        disassociateUnconfigExtMgmtGw(1578),
        disassociateUnconfigCimcVMedia(1579),
        decommissionUnconfigExtMgmtRules(1580),
        decommissionUnconfigExtMgmtGw(1581),
        fwUpgradeUnconfigExtMgmtRules(1582),
        fwUpgradeUnconfigExtMgmtGw(1583),
        fwUpgradeUnconfigCimcVMedia(1584),
        fwUpgradeGraphicsImageUpdate(1585),
        associateDownloadImages(1588),
        associateCopyRemote(1589),
        fwUpgradeDownloadImages(1590),
        fwUpgradeCopyRemote(1591),
        flashControllerBegin(1592),
        flashControllerUpdateFlashLife(1593),
        flashControllerFail(1595),
        flashControllerSuccess(1596),
        associateDeleteCurlDownloadedImages(1598),
        fwUpgradeDeleteCurlDownloadedImages(1599),
        enableCimcSecureBootBegin(1611),
        enableCimcSecureBootUpdateRequest(1612),
        enableCimcSecureBootPollUpdateStatus(1613),
        enableCimcSecureBootActivate(1614),
        enableCimcSecureBootReset(1615),
        enableCimcSecureBootFail(1620),
        enableCimcSecureBootSuccess(1621),
        associateCheckPowerAvailability(1698),
        associatePowerDeployWait(1699),
        associateOobStorageConfig(1700),
        associateVerifyRemoteStorageConfig(1701),
        associateNicConfigParamsHostOSLocal(1702),
        associateNicConfigParamsHostOSPeer(1703),
        associateBmcUpdateHostPreBoot(1704),
        disassociateWaitForUnConfigAppliances(1705),
        disassociateCheckPowerAvailability(1706),
        disassociatePowerDeployWait(1707),
        turnupCheckPowerAvailability(1708),
        turnupPowerDeployWait(1709),
        powercycleCheckPowerAvailability(1710),
        powercyclePowerDeployWait(1711),
        hardresetCheckPowerAvailability(1712),
        hardresetPowerDeployWait(1713),
        softresetCheckPowerAvailability(1714),
        softresetPowerDeployWait(1715),
        biosRecoveryCheckPowerAvailability(1716),
        biosRecoveryPowerDeployWait(1717),
        cmosResetCheckPowerAvailability(1718),
        cmosResetPowerDeployWait(1719),
        fwUpgradeCheckPowerAvailability(1720),
        fwUpgradePowerDeployWait(1721),
        oobStorageAdminConfigBegin(1722),
        oobStorageAdminConfigPreSanitize(1723),
        oobStorageAdminConfigSanitize(1724),
        oobStorageAdminConfigTearDownVMediaLocal(1725),
        oobStorageAdminConfigTearDownVMediaPeer(1726),
        oobStorageAdminConfigBootHost(1727),
        oobStorageAdminConfigBootWait(1728),
        oobStorageAdminConfigOobStorageConfig(1729),
        oobStorageAdminConfigOobStorageInventory(1730),
        oobStorageAdminConfigShutdown(1731),
        activateBIOSCheckPowerAvailability(1800),
        activateBIOSPowerDeployWait(1801),
        updateAdaptorCheckPowerAvailability(1802),
        updateAdaptorPowerDeployWait(1803),
        activateAdaptorCheckPowerAvailability(1804),
        activateAdaptorPowerDeployWait(1805),
        updateBoardControllerCheckPowerAvailability(1806),
        updateBoardControllerPowerDeployWait(1807),
        oobStorageAdminConfigFail(1813),
        oobStorageAdminConfigSuccess(1814),
        associateDeleteImagesRemote(1880),
        disassociateOobDiskScrub(1881),
        fwUpgradeDeleteImagesRemote(1882),
        associateUnlockFirmwareImage(1943),
        decommissionPrecleanupPortConfig(1944),
        clearTPMBegin(1945),
        clearTPMPreSanitize(1946),
        clearTPMSanitize(1947),
        clearTPMClear(1948),
        clearTPMBootHost(1949),
        clearTPMBiosPostCompletion(1950),
        clearTPMReadSmBios(1951),
        clearTPMBladePowerOff(1952),
        clearTPMReconfigBios(1953),
        clearTPMBladePowerOn(1954),
        fwUpgradeUnlockFirmwareImage(1955),
        clearTPMFail(1957),
        clearTPMSuccess(1958),
        clearTPMStopVMediaLocal(1964),
        clearTPMStopVMediaPeer(1965),
        clearTPMSetupVmedia(1966),
        clearTPMUnconfigVmedia(1967),
        updateBoardControllerPowerCycleBoard(1968),
        updateBoardControllerPollBoardCtrlPowerCycle(1969),
        associatePowerCycleBoard(1970),
        associatePollBoardCtrlPowerCycle(1971),
        fwUpgradePowerCycleBoard(1972),
        fwUpgradePollBoardCtrlPowerCycle(1973),
        associateCalculateVlanGroupForHostOSLocal(1978),
        associateCalculateVlanGroupForHostOSPeer(1979),
        associateConfigFanSpeed(1998),
        associateSasExpanderImgUpdate(1999),
        fwUpgradeSasExpanderImgUpdate(2000),
        fwUpgradeOobStorageInventory(2001),
        discoverBmcFactoryReset(2010),
        discoverCheckPowerAvailability(2026),
        discoverPowerDeployWait(2027),
        associateOobSasExpanderImgUpdate(2030),
        associateOobPollSasExpanderUpdateStatus(2031),
        associateOobSasExpanderImgActivate(2032),
        associateOobPollSasExpanderActivateStatus(2033),
        associateCiscoOSOpenGate(2034),
        fwUpgradeOobSasExpanderImgUpdate(2037),
        fwUpgradeOobPollSasExpanderUpdateStatus(2038),
        fwUpgradeOobSasExpanderImgActivate(2039),
        fwUpgradeOobPollSasExpanderActivateStatus(2040),
        fwUpgradeCiscoOSOpenGate(2041),
        oobStorageAdminConfigCheckPowerAvailability(2043),
        oobStorageAdminConfigPowerDeployWait(2044),
        diskZoningInventoryBegin(2045),
        diskZoningInventoryPreSanitize(2046),
        diskZoningInventorySanitize(2047),
        diskZoningInventoryBootHost(2048),
        diskZoningInventoryBootWait(2049),
        diskZoningInventoryStorageInventory(2050),
        diskZoningInventoryShutdown(2051),
        diskZoningInventoryFail(2161),
        diskZoningInventorySuccess(2162),
        activateAdaptorAssertBypassWait(2200),
        diagBegin(2209),
        diagPreSanitize(2210),
        diagSanitize(2211),
        diagCheckPowerAvailability(2212),
        diagDisableScriptableVMedia(2213),
        diagPreconfigVmediaLocal(2214),
        diagPreconfigVmediaPeer(2215),
        diagSetupVmediaLocal(2216),
        diagSetupVmediaPeer(2217),
        diagSetupBootEnvironment(2218),
        diagSerialDebugConnect(2219),
        diagPowerOn(2220),
        diagPowerOnWait(2221),
        diagBiosPostCompletion(2222),
        diagHagConnect(2223),
        diagPnuOSIdent(2224),
        diagRunTests(2225),
        diagLogTransfer(2226),
        diagWaitForDebug(2227),
        diagTeardownVmediaLocal(2228),
        diagTeardownVmediaPeer(2229),
        diagHagDisconnect(2230),
        diagSerialDebugDisconnect(2231),
        diagTearDownBootEnvironment(2232),
        diagShutdown(2233),
        associatePnuOSPeripheralComponentConfig(2234),
        associateConfigMgmtIpRules(2235),
        associateAssertBypassWait(2236),
        associateHostOSConnect(2237),
        associateConfigHostOsAnnotations(2238),
        associateConfigServerIdentity(2239),
        disassociateUnconfigServerIdentity(2240),
        fwUpgradeAssertBypassWait(2241),
        cimcSecurityConfigBegin(2242),
        cimcSecurityConfigKmipCertConfig(2243),
        cimcSecurityConfigKmipSaveCert(2244),
        cimcSecurityConfigFail(2257),
        cimcSecurityConfigSuccess(2258),
        diagFail(2259),
        diagSuccess(2260),
        discoverOobStorageConfig(2270),
        associateRestoreVdStatus(2271),
        discoverSwPortDetailsLocal(2292),
        discoverSwPortDetailsPeer(2293),
        discoverSwConfigurePortChannelLocal(2294),
        discoverSwConfigurePortChannelPeer(2295),
        discoverPnuosBootWait(2296),
        discoverSwHostOSMultiPortConnectivityLocal(2297),
        discoverSwHostOSMultiPortConnectivityPeer(2298),
        discoverSwHostOSConfigurePortChannelLocal(2299),
        discoverSwHostOSConfigurePortChannelPeer(2300),
        associateOobSasExpanderBootImgActivate(2301),
        associateOobPollSasExpanderBootImgActivateStatus(2302),
        associateMswitchImgUpdate(2303),
        fwUpgradeOobSasExpanderBootImgActivate(2304),
        fwUpgradeOobPollSasExpanderBootImgActivateStatus(2305),
        fwUpgradeMswitchImgUpdate(2306),
        associatePciSwitchImageUpdate(2325),
        associateSharedComponentsOobInventory(2326),
        associateSharedComponentsOobInventoryPeer(2327),
        fwUpgradePciSwitchImageUpdate(2328),
        associatePersistentMemoryDimmFwUpdate(2334),
        associateWaitForBorderConfigCompletionLocal(2335),
        associateWaitForBorderConfigCompletionPeer(2336),
        executeActionsBegin(2337),
        executeActionsSoftShutdown(2338),
        executeActionsExecutePMAction(2339),
        executeActionsPowerOn(2340),
        executeActionsBiosPostCompletion(2341),
        fwUpgradePersistentMemoryDimmFwUpdate(2344),
        nvmeSwitchRecoveryBegin(2345),
        nvmeSwitchRecoveryWaitForAck(2346),
        nvmeSwitchRecoveryExecute(2347),
        nvmeSwitchRecoveryCheckStatus(2348),
        executeActionsFail(2363),
        executeActionsSuccess(2364),
        nvmeSwitchRecoveryFail(2365),
        nvmeSwitchRecoverySuccess(2366),
        reinitializeVirtualDriveBegin(2375),
        reinitializeVirtualDriveExecuteVDAction(2376),
        reinitializeVirtualDriveFail(2377),
        reinitializeVirtualDriveSuccess(2378),
        configureServerPersonalityBegin(2401),
        configureServerPersonalityExecute(2402),
        configureServerPersonalityFail(2403),
        configureServerPersonalitySuccess(2404),
        biosPasswordResetBegin(2407),
        biosPasswordResetPreSanitize(2408),
        biosPasswordResetSanitize(2409),
        biosPasswordResetExecute(2410),
        biosPasswordResetReconfigBios(2411),
        biosPasswordResetReconfigUuid(2412),
        biosPasswordResetCheckPowerAvailability(2413),
        biosPasswordResetPowerDeployWait(2414),
        biosPasswordResetBladePowerOn(2415),
        cimcSecurityUnconfigBegin(2416),
        cimcSecurityUnconfigKmipDelCert(2417),
        biosPasswordResetFail(2418),
        biosPasswordResetSuccess(2419),
        cimcSecurityUnconfigFail(2420),
        cimcSecurityUnconfigSuccess(2421),
        diagPowerDeployWait(2422),
        associateUpdateFruComponents(2424),
        associateWaitForUpdateFruComponents(2425),
        associateWaitForBiosPostCompletion(2426),
        associateUpdateNwSbAdaptorFw(2427),
        associateWaitForNwSbAdaptorFwUpdate(2428),
        associateActivateNwSbAdaptorFw(2429),
        associateWaitForNwSbAdaptorFwActivate(2430),
        fwUpgradeUpdateFruComponents(2433),
        fwUpgradeWaitForUpdateFruComponents(2434),
        fwUpgradeWaitForBiosPostCompletion(2435),
        fwUpgradeUpdateNwSbAdaptorFw(2436),
        fwUpgradeWaitForNwSbAdaptorFwUpdate(2437),
        fwUpgradeActivateNwSbAdaptorFw(2438),
        fwUpgradeWaitForNwSbAdaptorFwActivate(2439),
        discoverFruComponentInventory(2440),
        associateHybridDriveSlotConfig(2446),
        associateUpdateFruComponentsAfterPoweredOn(2447),
        associateWaitForUpdateFruComponentsAfterPoweredOn(2448),
        associatePowerOffForSbAdaptorActivation(2449),
        associateNVMEVDConfig(2450),
        fwUpgradeUpdateFruComponentsAfterPoweredOn(2451),
        fwUpgradeWaitForUpdateFruComponentsAfterPoweredOn(2452),
        fwUpgradePowerOffForSbAdaptorActivation(2453),
        dataSanitizationBegin(2454),
        dataSanitizationPreSanitize(2455),
        dataSanitizationSanitize(2456),
        dataSanitizationCheckPowerAvailability(2457),
        dataSanitizationPowerDeployWait(2458),
        dataSanitizationDisableScriptableVMedia(2459),
        dataSanitizationPreconfigVmediaLocal(2460),
        dataSanitizationPreconfigVmediaPeer(2461),
        dataSanitizationSetupVmediaLocal(2462),
        dataSanitizationSetupVmediaPeer(2463),
        dataSanitizationSetupBootEnvironment(2464),
        dataSanitizationSerialDebugConnect(2465),
        dataSanitizationPowerOn(2466),
        dataSanitizationPowerOnWait(2467),
        dataSanitizationBiosPostCompletion(2468),
        dataSanitizationHagConnect(2469),
        dataSanitizationPnuOSIdent(2470),
        dataSanitizationStorageComponents(2471),
        dataSanitizationWaitForStorageComponent(2472),
        dataSanitizationTeardownVmediaLocal(2473),
        dataSanitizationTeardownVmediaPeer(2474),
        dataSanitizationHagDisconnect(2475),
        dataSanitizationSerialDebugDisconnect(2476),
        dataSanitizationTearDownBootEnvironment(2477),
        dataSanitizationNetworkAdapter(2478),
        dataSanitizationWaitForNetworkAdapter(2479),
        dataSanitizationHostComponents(2480),
        dataSanitizationWaitForHostComponents(2481),
        dataSanitizationBoardComponents(2482),
        dataSanitizationWaitForBoardComponents(2483),
        dataSanitizationShutdown(2484),
        dataSanitizationFail(2488),
        dataSanitizationSuccess(2489),
        associatePowerOnForStorageInit(2492),
        associateWaitForStorageInit(2493),
        associateConfigStorageRemoteSecurity(2494),
        associatePowerOff(2495),
        associateFetchBiosHealthReport(2496),
        disassociateOobStorageInventory(2497),
        discoverPostScrubOobStorageInventory(2498),
        associateSyncPowerStateForStorageInit(2507),
        associatePowerOnPreConfigForStorageInit(2508),
        associateCheckPowerAvailabilityForStorageInit(2509),
        associatePowerDeployWaitForStorageInit(2510)
    }

CucsComputeRackUnitFsmTaskFlags ::= TEXTUAL-CONVENTION
    STATUS        current
    DESCRIPTION
        ""
    SYNTAX        BITS
    {
        samDmeComputeRackUnitAdapterResetAlways(5),
        samDmeComputeRackUnitAdapterResetPowerOn(6),
        samDmeComputeRackUnitDiscoverCheckPoint(24)
    }

CucsComputeRackUnitFsmTaskItem ::= TEXTUAL-CONVENTION
    STATUS        current
    DESCRIPTION
        ""
    SYNTAX        INTEGER
    {
        nop(0),
        discover(599),
        offline(1064),
        adapterReset(1316),
        createDhcpEntry(1510)
    }

CucsComputeRackUnitMbTempStatsThresholded ::= TEXTUAL-CONVENTION
    STATUS        current
    DESCRIPTION
        ""
    SYNTAX        BITS
    {
        ambientTemp(0),
        ambientTempAvg(1),
        ambientTempMax(2),
        ambientTempMin(3),
        frontTemp(4),
        frontTempAvg(5),
        frontTempMax(6),
        frontTempMin(7),
        ioh1Temp(8),
        ioh1TempAvg(9),
        ioh1TempMax(10),
        ioh1TempMin(11),
        ioh2Temp(12),
        ioh2TempAvg(13),
        ioh2TempMax(14),
        ioh2TempMin(15),
        rearTemp(16),
        rearTempAvg(17),
        rearTempMax(18),
        rearTempMin(19)
    }

CucsComputeRackUnitMbTempStatsHistThresholded ::= TEXTUAL-CONVENTION
    STATUS        current
    DESCRIPTION
        ""
    SYNTAX        BITS
    {
        ambientTemp(0),
        ambientTempAvg(1),
        ambientTempMax(2),
        ambientTempMin(3),
        frontTemp(4),
        frontTempAvg(5),
        frontTempMax(6),
        frontTempMin(7),
        ioh1Temp(8),
        ioh1TempAvg(9),
        ioh1TempMax(10),
        ioh1TempMin(11),
        ioh2Temp(12),
        ioh2TempAvg(13),
        ioh2TempMax(14),
        ioh2TempMin(15),
        rearTemp(16),
        rearTempAvg(17),
        rearTempMax(18),
        rearTempMin(19)
    }

CucsComputeRemoteAdminTrigger ::= TEXTUAL-CONVENTION
    STATUS        current
    DESCRIPTION
        ""
    SYNTAX        INTEGER
    {
        remoteTrigger(0),
        rediscover(1),
        resetToFactory(2),
        discovered(3),
        remove(4),
        migrate(5),
        decommission(6)
    }

CucsComputeResourceSetState ::= TEXTUAL-CONVENTION
    STATUS        current
    DESCRIPTION
        ""
    SYNTAX        INTEGER
    {
        inventoryPending(1),
        inventoryInProgress(2),
        inventoryComplete(3)
    }

CucsComputeSanitizeCompType ::= TEXTUAL-CONVENTION
    STATUS        current
    DESCRIPTION
        ""
    SYNTAX        INTEGER
    {
        storage(1),
        networkAdapter(2),
        host(3),
        board(4)
    }

CucsComputeSanitizeStatus ::= TEXTUAL-CONVENTION
    STATUS        current
    DESCRIPTION
        ""
    SYNTAX        INTEGER
    {
        none(0),
        ready(1),
        inProgress(2),
        failed(3),
        completed(4)
    }

CucsComputeSanitizeType ::= TEXTUAL-CONVENTION
    STATUS        current
    DESCRIPTION
        ""
    SYNTAX        INTEGER
    {
        none(0),
        host(1),
        board(2),
        all(3)
    }

CucsComputeScrubAction ::= TEXTUAL-CONVENTION
    STATUS        current
    DESCRIPTION
        ""
    SYNTAX        INTEGER
    {
        no(0),
        yes(1)
    }

CucsComputeServerDiscPolicyFsmCurrentFsm ::= TEXTUAL-CONVENTION
    STATUS        current
    DESCRIPTION
        ""
    SYNTAX        INTEGER
    {
        nop(0),
        resolveScrubPolicy(1231)
    }

CucsComputeServerDiscPolicyFsmStageName ::= TEXTUAL-CONVENTION
    STATUS        current
    DESCRIPTION
        ""
    SYNTAX        INTEGER
    {
        nop(0),
        resolveScrubPolicyBegin(1231),
        resolveScrubPolicyResolve(1232),
        resolveScrubPolicyFail(1391),
        resolveScrubPolicySuccess(1392)
    }

CucsComputeServerDiscPolicyFsmTaskItem ::= TEXTUAL-CONVENTION
    STATUS        current
    DESCRIPTION
        ""
    SYNTAX        INTEGER
    {
        nop(0),
        resolveScrubPolicy(1231)
    }

CucsComputeServerFeatureMask ::= TEXTUAL-CONVENTION
    STATUS        current
    DESCRIPTION
        ""
    SYNTAX        BITS
    {
        policyMapFeatureMask(0),
        globalSpFeatureMask(1),
        inBandMgmtFeatureMask(2),
        healthPolicyFeatureMask(3),
        advancedBootOrderFeatureMask(4),
        maintenancePolicyFeatureMask(5),
        excludeFirmwareComponentFeatureMask(6),
        populateTemplateNameFeatureMask(7),
        lightWeightPatchingFeatureMask(8),
        selfEncryptingDrivesPolicyFeatureMask(9)
    }

CucsComputeServerMgmtDiscAction ::= TEXTUAL-CONVENTION
    STATUS        current
    DESCRIPTION
        ""
    SYNTAX        INTEGER
    {
        autoAcknowledged(0),
        userAcknowledged(1)
    }

CucsComputeServerTypeCapType ::= TEXTUAL-CONVENTION
    STATUS        current
    DESCRIPTION
        ""
    SYNTAX        INTEGER
    {
        generalPurpose(0),
        appliance(1),
        sharedIo(2),
        xSeries(3)
    }

CucsComputeServerUnitChassisId ::= TEXTUAL-CONVENTION
    STATUS        current
    DESCRIPTION
        ""
    SYNTAX        Gauge32 (1..255)

CucsComputeServerUnitServerInstanceId ::= TEXTUAL-CONVENTION
    STATUS        current
    DESCRIPTION
        ""
    SYNTAX        Gauge32 (1..2)

CucsComputeServerUnitSlotId ::= TEXTUAL-CONVENTION
    STATUS        current
    DESCRIPTION
        ""
    SYNTAX        Gauge32 (1..8)

CucsComputeServerUnitFsmCurrentFsm ::= TEXTUAL-CONVENTION
    STATUS        current
    DESCRIPTION
        ""
    SYNTAX        INTEGER
    {
        nop(0),
        associate(665),
        disassociate(727),
        powerCap(767),
        decommission(769),
        softShutdown(771),
        hardShutdown(773),
        turnup(775),
        powercycle(777),
        hardreset(781),
        softreset(785),
        swConnUpd(789),
        biosRecovery(792),
        cmosReset(806),
        resetBmc(815),
        updateExtUsers(879),
        updateAdaptor(891),
        activateAdaptor(898),
        configSoL(932),
        unconfigSoL(934),
        diagnosticInterrupt(1036),
        resetKvm(1055),
        updateBIOS(1152),
        activateBIOS(1157),
        resetIpmi(1200),
        fwUpgrade(1202),
        cimcSessionDelete(1477),
        updateBoardController(1497),
        configBoard(1506),
        resetMemoryErrors(1508),
        serviceInfraDeploy(1531),
        serviceInfraWithdraw(1536),
        flashController(1599),
        enableCimcSecureBoot(1613),
        oobStorageAdminConfig(1722),
        discover(1885),
        clearTPM(1945),
        diskZoningInventory(2045),
        diag(2209),
        cimcSecurityConfig(2242),
        executeActions(2337),
        nvmeSwitchRecovery(2345),
        reinitializeVirtualDrive(2375),
        configureServerPersonality(2401),
        biosPasswordReset(2407),
        cimcSecurityUnconfig(2416),
        dataSanitization(2454)
    }

CucsComputeServerUnitFsmStageName ::= TEXTUAL-CONVENTION
    STATUS        current
    DESCRIPTION
        ""
    SYNTAX        INTEGER
    {
        nop(0),
        associateBegin(665),
        associateUpdateIBMCFw(668),
        associateWaitForIBMCFwUpdate(669),
        associateActivateIBMCFw(670),
        associateResetIBMC(671),
        associatePreSanitize(672),
        associateSanitize(673),
        associateConfigUserAccess(674),
        associateBladePowerOff(675),
        associateUpdateBoardCtrlRequest(676),
        associatePollBoardCtrlUpdateStatus(677),
        associatePowerOn(678),
        associateBmcPreconfigPnuOSLocal(679),
        associateBmcPreconfigPnuOSPeer(680),
        associateBmcConfigPnuOS(681),
        associateSwConfigPnuOSLocal(682),
        associateSwConfigPnuOSPeer(683),
        associateUpdateAdaptorNwFwLocal(684),
        associateUpdateAdaptorNwFwPeer(685),
        associateWaitForAdaptorNwFwUpdateLocal(686),
        associateWaitForAdaptorNwFwUpdatePeer(687),
        associateActivateAdaptorNwFwLocal(688),
        associateActivateAdaptorNwFwPeer(689),
        associateNicConfigPnuOSLocal(690),
        associateNicConfigPnuOSPeer(691),
        associateBootPnuos(692),
        associateBootWait(693),
        associateBiosPostCompletion(694),
        associateHagPnuOSConnect(695),
        associatePnuOSIdent(696),
        associatePnuOSPolicy(697),
        associatePnuOSValidate(698),
        associatePnuOSSelfTest(699),
        associateBiosImgUpdate(700),
        associateStorageCtlrImgUpdate(701),
        associateHbaImgUpdate(702),
        associateNicImgUpdate(703),
        associatePnuOSInventory(704),
        associatePnuOSConfig(705),
        associatePnuOSLocalDiskConfig(706),
        associatePnuOSUnloadDrivers(707),
        associateBmcUnconfigPnuOS(708),
        associateNicUnconfigPnuOSLocal(709),
        associateNicUnconfigPnuOSPeer(710),
        associateSwUnconfigPnuOSLocal(711),
        associateSwUnconfigPnuOSPeer(712),
        associateSwConfigHostOSLocal(713),
        associateSwConfigHostOSPeer(714),
        associateNicConfigHostOSLocal(715),
        associateNicConfigHostOSPeer(716),
        associateHagPnuOSDisconnect(717),
        associateConfigSoL(718),
        associatePrepareForBoot(719),
        associateConfigUuid(720),
        associateBootHost(721),
        associateHagHostOSConnect(722),
        associateHostOSIdent(723),
        associateHostOSPolicy(724),
        associateHostOSValidate(725),
        associateHostOSConfig(726),
        disassociateBegin(727),
        disassociateConfigUserAccess(730),
        disassociatePowerOn(731),
        disassociatePreSanitize(732),
        disassociateSanitize(733),
        disassociateNicUnconfigHostOSLocal(734),
        disassociateNicUnconfigHostOSPeer(735),
        disassociateSwUnconfigHostOSLocal(736),
        disassociateSwUnconfigHostOSPeer(737),
        disassociateBmcPreconfigPnuOSLocal(738),
        disassociateBmcPreconfigPnuOSPeer(739),
        disassociateBmcConfigPnuOS(740),
        disassociateSwConfigPnuOSLocal(741),
        disassociateSwConfigPnuOSPeer(742),
        disassociateNicConfigPnuOSLocal(743),
        disassociateNicConfigPnuOSPeer(744),
        disassociateConfigBios(745),
        disassociateBootPnuos(746),
        disassociateBootWait(747),
        disassociateBiosPostCompletion(748),
        disassociateHagPnuOSConnect(749),
        disassociatePnuOSIdent(750),
        disassociatePnuOSPolicy(751),
        disassociatePnuOSValidate(752),
        disassociatePnuOSUnconfig(753),
        disassociatePnuOSScrub(754),
        disassociatePnuOSSelfTest(755),
        disassociateBmcUnconfigPnuOS(756),
        disassociateNicUnconfigPnuOSLocal(757),
        disassociateNicUnconfigPnuOSPeer(758),
        disassociateHagPnuOSDisconnect(759),
        disassociateUnconfigUuid(760),
        disassociateShutdown(761),
        disassociateUnconfigBios(762),
        disassociateSwUnconfigPnuOSLocal(763),
        disassociateSwUnconfigPnuOSPeer(764),
        disassociateUnconfigSoL(765),
        disassociateHandlePooling(766),
        powerCapBegin(767),
        powerCapConfig(768),
        decommissionBegin(769),
        decommissionExecute(770),
        softShutdownBegin(771),
        softShutdownExecute(772),
        hardShutdownBegin(773),
        hardShutdownExecute(774),
        turnupBegin(775),
        turnupExecute(776),
        powercycleBegin(777),
        powercyclePreSanitize(778),
        powercycleSanitize(779),
        powercycleExecute(780),
        hardresetBegin(781),
        hardresetPreSanitize(782),
        hardresetSanitize(783),
        hardresetExecute(784),
        softresetBegin(785),
        softresetPreSanitize(786),
        softresetSanitize(787),
        softresetExecute(788),
        swConnUpdBegin(789),
        swConnUpdA(790),
        swConnUpdB(791),
        biosRecoveryBegin(792),
        biosRecoveryShutdown(793),
        biosRecoveryPreSanitize(794),
        biosRecoverySanitize(795),
        biosRecoverySetupVmediaLocal(796),
        biosRecoverySetupVmediaPeer(797),
        biosRecoveryStart(798),
        biosRecoveryWait(799),
        biosRecoveryCleanup(800),
        biosRecoveryReset(801),
        biosRecoveryTeardownVmediaLocal(802),
        biosRecoveryTeardownVmediaPeer(803),
        cmosResetBegin(806),
        cmosResetPreSanitize(807),
        cmosResetSanitize(808),
        cmosResetExecute(809),
        cmosResetReconfigBios(810),
        cmosResetReconfigUuid(811),
        cmosResetBladePowerOn(812),
        resetBmcBegin(815),
        resetBmcExecute(816),
        updateExtUsersBegin(879),
        updateExtUsersDeploy(880),
        updateAdaptorBegin(891),
        updateAdaptorPowerOn(892),
        updateAdaptorUpdateRequestLocal(893),
        updateAdaptorUpdateRequestPeer(894),
        updateAdaptorPollUpdateStatusLocal(895),
        updateAdaptorPollUpdateStatusPeer(896),
        updateAdaptorPowerOff(897),
        activateAdaptorBegin(898),
        activateAdaptorPowerOn(899),
        activateAdaptorActivateLocal(900),
        activateAdaptorActivatePeer(901),
        activateAdaptorReset(902),
        configSoLBegin(932),
        configSoLExecute(933),
        unconfigSoLBegin(934),
        unconfigSoLExecute(935),
        activateAdaptorFail(940),
        activateAdaptorSuccess(941),
        associateFail(942),
        associateSuccess(943),
        biosRecoveryFail(946),
        biosRecoverySuccess(947),
        cmosResetFail(948),
        cmosResetSuccess(949),
        configSoLFail(950),
        configSoLSuccess(951),
        decommissionFail(952),
        decommissionSuccess(953),
        disassociateFail(954),
        disassociateSuccess(955),
        hardShutdownFail(956),
        hardShutdownSuccess(957),
        hardresetFail(958),
        hardresetSuccess(959),
        powerCapFail(960),
        powerCapSuccess(961),
        powercycleFail(962),
        powercycleSuccess(963),
        resetBmcFail(964),
        resetBmcSuccess(965),
        softShutdownFail(966),
        softShutdownSuccess(967),
        softresetFail(968),
        softresetSuccess(969),
        swConnUpdFail(970),
        swConnUpdSuccess(971),
        turnupFail(972),
        turnupSuccess(973),
        unconfigSoLFail(974),
        unconfigSoLSuccess(975),
        updateAdaptorFail(976),
        updateAdaptorSuccess(977),
        updateExtUsersFail(978),
        updateExtUsersSuccess(979),
        decommissionStopVMediaLocal(1019),
        decommissionStopVMediaPeer(1020),
        biosRecoveryStopVMediaLocal(1021),
        biosRecoveryStopVMediaPeer(1022),
        diagnosticInterruptBegin(1036),
        diagnosticInterruptExecute(1037),
        diagnosticInterruptFail(1038),
        diagnosticInterruptSuccess(1039),
        associateLocalDiskFwUpdate(1040),
        resetKvmBegin(1055),
        resetKvmExecute(1056),
        resetKvmFail(1057),
        resetKvmSuccess(1058),
        associateSwConfigPortNivLocal(1069),
        associateSwConfigPortNivPeer(1070),
        disassociateSwConfigPortNivLocal(1071),
        disassociateSwConfigPortNivPeer(1072),
        associateSolRedirectEnable(1104),
        associateSerialDebugPnuOSConnect(1105),
        associateSerialDebugPnuOSDisconnect(1106),
        associateSolRedirectDisable(1107),
        disassociateSolRedirectEnable(1108),
        disassociateSerialDebugPnuOSConnect(1109),
        disassociateSerialDebugPnuOSDisconnect(1110),
        disassociateSolRedirectDisable(1111),
        decommissionCleanupCIMC(1112),
        updateBIOSBegin(1152),
        updateBIOSClear(1153),
        updateBIOSPollClearStatus(1154),
        updateBIOSUpdateRequest(1155),
        updateBIOSPollUpdateStatus(1156),
        activateBIOSBegin(1157),
        activateBIOSPowerOff(1158),
        activateBIOSClear(1159),
        activateBIOSPollClearStatus(1160),
        activateBIOSActivate(1161),
        activateBIOSPollActivateStatus(1162),
        activateBIOSUpdateTokens(1163),
        activateBIOSPowerOn(1164),
        associateClearBiosUpdate(1169),
        associatePollClearBiosUpdateStatus(1170),
        associateUpdateBiosRequest(1171),
        associatePollBiosUpdateStatus(1172),
        associateActivateBios(1173),
        associatePollBiosActivateStatus(1174),
        associatePnuOSCatalog(1175),
        disassociatePnuOSCatalog(1176),
        activateBIOSFail(1178),
        activateBIOSSuccess(1179),
        updateBIOSFail(1180),
        updateBIOSSuccess(1181),
        associateMarkAdapterForReboot(1193),
        associateDeassertResetBypass(1194),
        associateVerifyFcZoneConfig(1195),
        disassociateDeassertResetBypass(1196),
        disassociateVerifyFcZoneConfig(1197),
        decommissionCleanupPortConfigLocal(1198),
        decommissionCleanupPortConfigPeer(1199),
        resetIpmiBegin(1200),
        resetIpmiExecute(1201),
        fwUpgradeBegin(1202),
        fwUpgradeUpdateIBMCFw(1203),
        fwUpgradeWaitForIBMCFwUpdate(1204),
        fwUpgradeActivateIBMCFw(1205),
        fwUpgradeResetIBMC(1206),
        fwUpgradePreSanitize(1207),
        fwUpgradeSanitize(1208),
        fwUpgradeBladePowerOff(1209),
        fwUpgradeUpdateBoardCtrlRequest(1210),
        fwUpgradePollBoardCtrlUpdateStatus(1211),
        fwUpgradeClearBiosUpdate(1212),
        fwUpgradePollClearBiosUpdateStatus(1213),
        fwUpgradeUpdateBiosRequest(1214),
        fwUpgradePollBiosUpdateStatus(1215),
        fwUpgradeActivateBios(1216),
        fwUpgradePollBiosActivateStatus(1217),
        fwUpgradePowerOn(1218),
        fwUpgradeBmcPreconfigPnuOSLocal(1219),
        fwUpgradeBmcPreconfigPnuOSPeer(1220),
        fwUpgradeSwConfigPortNivLocal(1221),
        fwUpgradeSwConfigPortNivPeer(1222),
        fwUpgradeSwConfigPnuOSLocal(1223),
        fwUpgradeSwConfigPnuOSPeer(1224),
        fwUpgradeUpdateAdaptorNwFwLocal(1225),
        fwUpgradeUpdateAdaptorNwFwPeer(1226),
        fwUpgradeWaitForAdaptorNwFwUpdateLocal(1227),
        fwUpgradeWaitForAdaptorNwFwUpdatePeer(1228),
        fwUpgradeActivateAdaptorNwFwLocal(1229),
        fwUpgradeActivateAdaptorNwFwPeer(1230),
        fwUpgradeNicConfigPnuOSLocal(1231),
        fwUpgradeNicConfigPnuOSPeer(1232),
        fwUpgradeBmcConfigPnuOS(1233),
        fwUpgradeSolRedirectEnable(1234),
        fwUpgradeSerialDebugPnuOSConnect(1235),
        fwUpgradeBootPnuos(1236),
        fwUpgradeBootWait(1237),
        fwUpgradeBiosPostCompletion(1238),
        fwUpgradeHagPnuOSConnect(1239),
        fwUpgradePnuOSIdent(1240),
        fwUpgradePnuOSPolicy(1241),
        fwUpgradePnuOSCatalog(1242),
        fwUpgradePnuOSValidate(1243),
        fwUpgradePnuOSSelfTest(1244),
        fwUpgradeStorageCtlrImgUpdate(1245),
        fwUpgradeHbaImgUpdate(1246),
        fwUpgradeNicImgUpdate(1247),
        fwUpgradeLocalDiskFwUpdate(1248),
        fwUpgradePnuOSConfig(1249),
        fwUpgradePnuOSInventory(1250),
        fwUpgradeBiosImgUpdate(1251),
        fwUpgradePnuOSUnloadDrivers(1252),
        fwUpgradeBmcUnconfigPnuOS(1253),
        fwUpgradeNicUnconfigPnuOSLocal(1254),
        fwUpgradeNicUnconfigPnuOSPeer(1255),
        fwUpgradeSwUnconfigPnuOSLocal(1256),
        fwUpgradeSwUnconfigPnuOSPeer(1257),
        fwUpgradeDeassertResetBypass(1258),
        fwUpgradeHagPnuOSDisconnect(1259),
        fwUpgradeSerialDebugPnuOSDisconnect(1260),
        fwUpgradeSolRedirectDisable(1261),
        fwUpgradeShutdown(1262),
        activateAdaptorDeassertResetBypass(1307),
        fwUpgradeFail(1386),
        fwUpgradeSuccess(1387),
        resetIpmiFail(1388),
        resetIpmiSuccess(1389),
        associateConfigFlexFlash(1468),
        associateSyncPowerState(1469),
        disassociateUnconfigFlexFlash(1470),
        cimcSessionDeleteBegin(1477),
        cimcSessionDeleteExecute(1478),
        cimcSessionDeleteFail(1483),
        cimcSessionDeleteSuccess(1484),
        updateBoardControllerBegin(1497),
        updateBoardControllerPrepareForUpdate(1498),
        updateBoardControllerServerPowerOff(1499),
        updateBoardControllerUpdateRequest(1500),
        updateBoardControllerPollUpdateStatus(1501),
        updateBoardControllerServerPowerOn(1502),
        configBoardBegin(1506),
        configBoardConfigMemoryPolicy(1507),
        resetMemoryErrorsBegin(1508),
        resetMemoryErrorsExecute(1509),
        associateOobStorageInventory(1520),
        associateSwConfigServiceInfraLocal(1521),
        associateSwConfigServiceInfraPeer(1522),
        associateNicConfigServiceInfraLocal(1523),
        associateNicConfigServiceInfraPeer(1524),
        disassociateNicUnconfigServiceInfraLocal(1525),
        disassociateNicUnconfigServiceInfraPeer(1526),
        disassociateConfigFlexFlashScrub(1527),
        serviceInfraDeployBegin(1531),
        serviceInfraDeploySwConfigLocal(1532),
        serviceInfraDeploySwConfigPeer(1533),
        serviceInfraDeployNicConfigLocal(1534),
        serviceInfraDeployNicConfigPeer(1535),
        serviceInfraWithdrawBegin(1536),
        serviceInfraWithdrawSwUnConfigLocal(1537),
        serviceInfraWithdrawSwUnConfigPeer(1538),
        serviceInfraWithdrawNicUnConfigLocal(1539),
        serviceInfraWithdrawNicUnConfigPeer(1540),
        configBoardFail(1541),
        configBoardSuccess(1542),
        resetMemoryErrorsFail(1543),
        resetMemoryErrorsSuccess(1544),
        serviceInfraDeployFail(1545),
        serviceInfraDeploySuccess(1546),
        serviceInfraWithdrawFail(1547),
        serviceInfraWithdrawSuccess(1548),
        updateBoardControllerFail(1549),
        updateBoardControllerSuccess(1550),
        associatePowerOnPreConfig(1561),
        disassociateResetSecureBootConfig(1562),
        associateDownloadImages(1576),
        associateCopyRemote(1577),
        associateUnconfigExtMgmtRules(1578),
        associateUnconfigExtMgmtGw(1579),
        associateUnconfigCimcVMedia(1580),
        associateGraphicsImageUpdate(1581),
        associateConfigExtMgmtRules(1582),
        associateConfigExtMgmtGw(1583),
        associateConfigCimcVMedia(1584),
        associateDeleteCurlDownloadedImages(1585),
        disassociateConfigKvmMgmtDefaultSetting(1586),
        disassociateUnconfigExtMgmtRules(1587),
        disassociateUnconfigExtMgmtGw(1588),
        disassociateUnconfigCimcVMedia(1589),
        decommissionUnconfigExtMgmtRules(1590),
        decommissionUnconfigExtMgmtGw(1591),
        fwUpgradeDownloadImages(1592),
        fwUpgradeCopyRemote(1593),
        fwUpgradeUnconfigExtMgmtRules(1594),
        fwUpgradeUnconfigExtMgmtGw(1595),
        fwUpgradeUnconfigCimcVMedia(1596),
        fwUpgradeGraphicsImageUpdate(1597),
        fwUpgradeDeleteCurlDownloadedImages(1598),
        flashControllerBegin(1599),
        flashControllerUpdateFlashLife(1600),
        flashControllerFail(1601),
        flashControllerSuccess(1602),
        enableCimcSecureBootBegin(1613),
        enableCimcSecureBootUpdateRequest(1614),
        enableCimcSecureBootPollUpdateStatus(1615),
        enableCimcSecureBootActivate(1616),
        enableCimcSecureBootReset(1617),
        enableCimcSecureBootFail(1620),
        enableCimcSecureBootSuccess(1621),
        associateCheckPowerAvailability(1698),
        associatePowerDeployWait(1699),
        associateOobStorageConfig(1700),
        associateNicConfigParamsHostOSLocal(1702),
        associateNicConfigParamsHostOSPeer(1703),
        disassociateCheckPowerAvailability(1706),
        disassociatePowerDeployWait(1707),
        turnupCheckPowerAvailability(1708),
        turnupPowerDeployWait(1709),
        powercycleCheckPowerAvailability(1710),
        powercyclePowerDeployWait(1711),
        hardresetCheckPowerAvailability(1712),
        hardresetPowerDeployWait(1713),
        softresetCheckPowerAvailability(1714),
        softresetPowerDeployWait(1715),
        biosRecoveryCheckPowerAvailability(1716),
        biosRecoveryPowerDeployWait(1717),
        cmosResetCheckPowerAvailability(1718),
        cmosResetPowerDeployWait(1719),
        fwUpgradeCheckPowerAvailability(1720),
        fwUpgradePowerDeployWait(1721),
        oobStorageAdminConfigBegin(1722),
        oobStorageAdminConfigPreSanitize(1723),
        oobStorageAdminConfigSanitize(1724),
        oobStorageAdminConfigTearDownVMediaLocal(1725),
        oobStorageAdminConfigTearDownVMediaPeer(1726),
        oobStorageAdminConfigBootHost(1727),
        oobStorageAdminConfigBootWait(1728),
        oobStorageAdminConfigOobStorageConfig(1729),
        oobStorageAdminConfigOobStorageInventory(1730),
        oobStorageAdminConfigShutdown(1731),
        activateBIOSCheckPowerAvailability(1800),
        activateBIOSPowerDeployWait(1801),
        updateAdaptorCheckPowerAvailability(1802),
        updateAdaptorPowerDeployWait(1803),
        activateAdaptorCheckPowerAvailability(1804),
        activateAdaptorPowerDeployWait(1805),
        updateBoardControllerCheckPowerAvailability(1806),
        updateBoardControllerPowerDeployWait(1807),
        oobStorageAdminConfigFail(1813),
        oobStorageAdminConfigSuccess(1814),
        associateDeleteImagesRemote(1880),
        disassociateOobDiskScrub(1881),
        fwUpgradeDeleteImagesRemote(1882),
        discoverBegin(1885),
        discoverCimcPresence(1886),
        discoverBmcInventory(1887),
        discoverPreSanitize(1888),
        discoverSanitize(1889),
        discoverConfigUserAccess(1890),
        discoverCleanupNicConfigLocal(1891),
        discoverCleanupNicConfigPeer(1892),
        discoverUnconfigExtMgmtRules(1893),
        discoverUnconfigExtMgmtGw(1894),
        discoverUnconfigCimcVMedia(1895),
        discoverBmcConfigPnuOS(1896),
        discoverBootPnuos(1897),
        discoverBladeBootWait(1898),
        discoverBiosPostCompletion(1899),
        discoverReadSmbios(1900),
        discoverBmcShutdownDiscovered(1901),
        discoverHandlePooling(1902),
        discoverSuccess(1903),
        discoverFail(1904),
        associateUnlockFirmwareImage(1943),
        decommissionPrecleanupPortConfig(1944),
        clearTPMBegin(1945),
        clearTPMPreSanitize(1946),
        clearTPMSanitize(1947),
        clearTPMClear(1948),
        clearTPMBootHost(1949),
        clearTPMBiosPostCompletion(1950),
        clearTPMReadSmBios(1951),
        clearTPMBladePowerOff(1952),
        clearTPMReconfigBios(1953),
        clearTPMBladePowerOn(1954),
        fwUpgradeUnlockFirmwareImage(1955),
        clearTPMFail(1957),
        clearTPMSuccess(1958),
        clearTPMStopVMediaLocal(1964),
        clearTPMStopVMediaPeer(1965),
        clearTPMSetupVmedia(1966),
        clearTPMUnconfigVmedia(1967),
        updateBoardControllerPowerCycleBoard(1968),
        updateBoardControllerPollBoardCtrlPowerCycle(1969),
        associatePowerCycleBoard(1970),
        associatePollBoardCtrlPowerCycle(1971),
        fwUpgradePowerCycleBoard(1972),
        fwUpgradePollBoardCtrlPowerCycle(1973),
        associateCalculateVlanGroupForHostOSLocal(1978),
        associateCalculateVlanGroupForHostOSPeer(1979),
        associateConfigFanSpeed(1998),
        associateSasExpanderImgUpdate(1999),
        fwUpgradeSasExpanderImgUpdate(2000),
        fwUpgradeOobStorageInventory(2001),
        associateOobSasExpanderImgUpdate(2030),
        associateOobPollSasExpanderUpdateStatus(2031),
        associateOobSasExpanderImgActivate(2032),
        associateOobPollSasExpanderActivateStatus(2033),
        associateCiscoOSOpenGate(2034),
        fwUpgradeOobSasExpanderImgUpdate(2037),
        fwUpgradeOobPollSasExpanderUpdateStatus(2038),
        fwUpgradeOobSasExpanderImgActivate(2039),
        fwUpgradeOobPollSasExpanderActivateStatus(2040),
        fwUpgradeCiscoOSOpenGate(2041),
        oobStorageAdminConfigCheckPowerAvailability(2043),
        oobStorageAdminConfigPowerDeployWait(2044),
        diskZoningInventoryBegin(2045),
        diskZoningInventoryPreSanitize(2046),
        diskZoningInventorySanitize(2047),
        diskZoningInventoryBootHost(2048),
        diskZoningInventoryBootWait(2049),
        diskZoningInventoryStorageInventory(2050),
        diskZoningInventoryShutdown(2051),
        discoverBmcFactoryReset(2052),
        diskZoningInventoryFail(2161),
        diskZoningInventorySuccess(2162),
        activateAdaptorAssertBypassWait(2200),
        diagBegin(2209),
        diagPreSanitize(2210),
        diagSanitize(2211),
        diagCheckPowerAvailability(2212),
        diagDisableScriptableVMedia(2213),
        diagPreconfigVmediaLocal(2214),
        diagPreconfigVmediaPeer(2215),
        diagSetupVmediaLocal(2216),
        diagSetupVmediaPeer(2217),
        diagSetupBootEnvironment(2218),
        diagSerialDebugConnect(2219),
        diagPowerOn(2220),
        diagPowerOnWait(2221),
        diagBiosPostCompletion(2222),
        diagHagConnect(2223),
        diagPnuOSIdent(2224),
        diagRunTests(2225),
        diagLogTransfer(2226),
        diagWaitForDebug(2227),
        diagTeardownVmediaLocal(2228),
        diagTeardownVmediaPeer(2229),
        diagHagDisconnect(2230),
        diagSerialDebugDisconnect(2231),
        diagTearDownBootEnvironment(2232),
        diagShutdown(2233),
        associatePnuOSPeripheralComponentConfig(2234),
        associateConfigMgmtIpRules(2235),
        associateAssertBypassWait(2236),
        associateHostOSConnect(2237),
        associateConfigHostOsAnnotations(2238),
        associateConfigServerIdentity(2239),
        disassociateUnconfigServerIdentity(2240),
        fwUpgradeAssertBypassWait(2241),
        cimcSecurityConfigBegin(2242),
        cimcSecurityConfigKmipCertConfig(2243),
        cimcSecurityConfigKmipSaveCert(2244),
        cimcSecurityConfigFail(2257),
        cimcSecurityConfigSuccess(2258),
        diagFail(2259),
        diagSuccess(2260),
        associateRestoreVdStatus(2271),
        associateOobSasExpanderBootImgActivate(2301),
        associateOobPollSasExpanderBootImgActivateStatus(2302),
        associateMswitchImgUpdate(2303),
        fwUpgradeOobSasExpanderBootImgActivate(2304),
        fwUpgradeOobPollSasExpanderBootImgActivateStatus(2305),
        fwUpgradeMswitchImgUpdate(2306),
        associatePciSwitchImageUpdate(2325),
        associateSharedComponentsOobInventory(2326),
        associateSharedComponentsOobInventoryPeer(2327),
        fwUpgradePciSwitchImageUpdate(2328),
        associatePersistentMemoryDimmFwUpdate(2334),
        associateWaitForBorderConfigCompletionLocal(2335),
        associateWaitForBorderConfigCompletionPeer(2336),
        executeActionsBegin(2337),
        executeActionsSoftShutdown(2338),
        executeActionsExecutePMAction(2339),
        executeActionsPowerOn(2340),
        executeActionsBiosPostCompletion(2341),
        fwUpgradePersistentMemoryDimmFwUpdate(2344),
        nvmeSwitchRecoveryBegin(2345),
        nvmeSwitchRecoveryWaitForAck(2346),
        nvmeSwitchRecoveryExecute(2347),
        nvmeSwitchRecoveryCheckStatus(2348),
        executeActionsFail(2363),
        executeActionsSuccess(2364),
        nvmeSwitchRecoveryFail(2365),
        nvmeSwitchRecoverySuccess(2366),
        reinitializeVirtualDriveBegin(2375),
        reinitializeVirtualDriveExecuteVDAction(2376),
        reinitializeVirtualDriveFail(2377),
        reinitializeVirtualDriveSuccess(2378),
        configureServerPersonalityBegin(2401),
        configureServerPersonalityExecute(2402),
        configureServerPersonalityFail(2403),
        configureServerPersonalitySuccess(2404),
        biosPasswordResetBegin(2407),
        biosPasswordResetPreSanitize(2408),
        biosPasswordResetSanitize(2409),
        biosPasswordResetExecute(2410),
        biosPasswordResetReconfigBios(2411),
        biosPasswordResetReconfigUuid(2412),
        biosPasswordResetCheckPowerAvailability(2413),
        biosPasswordResetPowerDeployWait(2414),
        biosPasswordResetBladePowerOn(2415),
        cimcSecurityUnconfigBegin(2416),
        cimcSecurityUnconfigKmipDelCert(2417),
        biosPasswordResetFail(2418),
        biosPasswordResetSuccess(2419),
        cimcSecurityUnconfigFail(2420),
        cimcSecurityUnconfigSuccess(2421),
        diagPowerDeployWait(2422),
        associateUpdateFruComponents(2424),
        associateWaitForUpdateFruComponents(2425),
        associateWaitForBiosPostCompletion(2426),
        associateUpdateNwSbAdaptorFw(2427),
        associateWaitForNwSbAdaptorFwUpdate(2428),
        associateActivateNwSbAdaptorFw(2429),
        associateWaitForNwSbAdaptorFwActivate(2430),
        fwUpgradeUpdateFruComponents(2433),
        fwUpgradeWaitForUpdateFruComponents(2434),
        fwUpgradeWaitForBiosPostCompletion(2435),
        fwUpgradeUpdateNwSbAdaptorFw(2436),
        fwUpgradeWaitForNwSbAdaptorFwUpdate(2437),
        fwUpgradeActivateNwSbAdaptorFw(2438),
        fwUpgradeWaitForNwSbAdaptorFwActivate(2439),
        associateHybridDriveSlotConfig(2446),
        associateUpdateFruComponentsAfterPoweredOn(2447),
        associateWaitForUpdateFruComponentsAfterPoweredOn(2448),
        associatePowerOffForSbAdaptorActivation(2449),
        associateNVMEVDConfig(2450),
        fwUpgradeUpdateFruComponentsAfterPoweredOn(2451),
        fwUpgradeWaitForUpdateFruComponentsAfterPoweredOn(2452),
        fwUpgradePowerOffForSbAdaptorActivation(2453),
        dataSanitizationBegin(2454),
        dataSanitizationPreSanitize(2455),
        dataSanitizationSanitize(2456),
        dataSanitizationCheckPowerAvailability(2457),
        dataSanitizationPowerDeployWait(2458),
        dataSanitizationDisableScriptableVMedia(2459),
        dataSanitizationPreconfigVmediaLocal(2460),
        dataSanitizationPreconfigVmediaPeer(2461),
        dataSanitizationSetupVmediaLocal(2462),
        dataSanitizationSetupVmediaPeer(2463),
        dataSanitizationSetupBootEnvironment(2464),
        dataSanitizationSerialDebugConnect(2465),
        dataSanitizationPowerOn(2466),
        dataSanitizationPowerOnWait(2467),
        dataSanitizationBiosPostCompletion(2468),
        dataSanitizationHagConnect(2469),
        dataSanitizationPnuOSIdent(2470),
        dataSanitizationStorageComponents(2471),
        dataSanitizationWaitForStorageComponent(2472),
        dataSanitizationTeardownVmediaLocal(2473),
        dataSanitizationTeardownVmediaPeer(2474),
        dataSanitizationHagDisconnect(2475),
        dataSanitizationSerialDebugDisconnect(2476),
        dataSanitizationTearDownBootEnvironment(2477),
        dataSanitizationNetworkAdapter(2478),
        dataSanitizationWaitForNetworkAdapter(2479),
        dataSanitizationHostComponents(2480),
        dataSanitizationWaitForHostComponents(2481),
        dataSanitizationBoardComponents(2482),
        dataSanitizationWaitForBoardComponents(2483),
        dataSanitizationShutdown(2484),
        dataSanitizationFail(2488),
        dataSanitizationSuccess(2489),
        associatePowerOnForStorageInit(2492),
        associateWaitForStorageInit(2493),
        associateConfigStorageRemoteSecurity(2494),
        associatePowerOff(2495),
        associateFetchBiosHealthReport(2496),
        disassociateOobStorageInventory(2497),
        associateSyncPowerStateForStorageInit(2507),
        associatePowerOnPreConfigForStorageInit(2508),
        associateCheckPowerAvailabilityForStorageInit(2509),
        associatePowerDeployWaitForStorageInit(2510)
    }

CucsComputeServerUnitFsmTaskFlags ::= TEXTUAL-CONVENTION
    STATUS        current
    DESCRIPTION
        ""
    SYNTAX        BITS
    {
        samDmeComputeServerUnitDiscoverCheckPoint(37)
    }

CucsComputeServerUnitFsmTaskItem ::= TEXTUAL-CONVENTION
    STATUS        current
    DESCRIPTION
        ""
    SYNTAX        INTEGER
    {
        nop(0),
        discover(1885)
    }

CucsComputeSlotQualMaxId ::= TEXTUAL-CONVENTION
    STATUS        current
    DESCRIPTION
        ""
    SYNTAX        Gauge32 (1..8)

CucsComputeSlotQualMinId ::= TEXTUAL-CONVENTION
    STATUS        current
    DESCRIPTION
        ""
    SYNTAX        Gauge32 (1..8)

CucsComputeStorageBladeMbTempStatsThresholded ::= TEXTUAL-CONVENTION
    STATUS        current
    DESCRIPTION
        ""
    SYNTAX        BITS
    {
        frontTemp(0),
        frontTempAvg(1),
        frontTempMax(2),
        frontTempMin(3),
        leftRearTemp(4),
        leftRearTempAvg(5),
        leftRearTempMax(6),
        leftRearTempMin(7),
        rightRearTemp(8),
        rightRearTempAvg(9),
        rightRearTempMax(10),
        rightRearTempMin(11)
    }

CucsComputeStorageBladeMbTempStatsHistThresholded ::= TEXTUAL-CONVENTION
    STATUS        current
    DESCRIPTION
        ""
    SYNTAX        BITS
    {
        frontTemp(0),
        frontTempAvg(1),
        frontTempMax(2),
        frontTempMin(3),
        leftRearTemp(4),
        leftRearTempAvg(5),
        leftRearTempMax(6),
        leftRearTempMin(7),
        rightRearTemp(8),
        rightRearTempAvg(9),
        rightRearTempMax(10),
        rightRearTempMin(11)
    }

CucsComputeStorageFeatureMask ::= TEXTUAL-CONVENTION
    STATUS        current
    DESCRIPTION
        ""
    SYNTAX        BITS
    {
        iscsiIpv6FeatureMask(0),
        fcZoningFeatureMask(1),
        storageProfileFeatureMask(2),
        storageConnectionFeatureMask(3)
    }

CucsComputeStorageInitType ::= TEXTUAL-CONVENTION
    STATUS        current
    DESCRIPTION
        ""
    SYNTAX        INTEGER
    {
        unknown(0),
        noInit(1),
        createInitialVolumes(2)
    }

CucsComputeStorageScrubType ::= TEXTUAL-CONVENTION
    STATUS        current
    DESCRIPTION
        ""
    SYNTAX        INTEGER
    {
        unknown(0),
        noScrub(1),
        scrub(2)
    }

CucsComputeSubscribeStatus ::= TEXTUAL-CONVENTION
    STATUS        current
    DESCRIPTION
        ""
    SYNTAX        INTEGER
    {
        ok(0),
        pending(1)
    }

CucsComputeSystemFsmCurrentFsm ::= TEXTUAL-CONVENTION
    STATUS        current
    DESCRIPTION
        ""
    SYNTAX        INTEGER
    {
        nop(0),
        register(212)
    }

CucsComputeSystemFsmStageName ::= TEXTUAL-CONVENTION
    STATUS        current
    DESCRIPTION
        ""
    SYNTAX        INTEGER
    {
        nop(0),
        registerBegin(212),
        registerAuthenticate(213),
        registerFail(216),
        registerSuccess(217)
    }

CucsComputeSystemFsmTaskItem ::= TEXTUAL-CONVENTION
    STATUS        current
    DESCRIPTION
        ""
    SYNTAX        INTEGER
    {
        nop(0),
        register(212)
    }

CucsComputeTriggerStatus ::= TEXTUAL-CONVENTION
    STATUS        current
    DESCRIPTION
        ""
    SYNTAX        INTEGER
    {
        unknown(0),
        triggerAcked(1),
        triggerFailed(2),
        triggered(3)
    }

CucsComputeUpgradeStatus ::= TEXTUAL-CONVENTION
    STATUS        current
    DESCRIPTION
        ""
    SYNTAX        INTEGER
    {
        notUpgraded(0),
        upgraded(1),
        notApplicable(2)
    }

CucsComputeUtilOSSupportedInterface ::= TEXTUAL-CONVENTION
    STATUS        current
    DESCRIPTION
        ""
    SYNTAX        INTEGER
    {
        serialCom(0),
        usbNic(1)
    }

CucsConditionAckAction ::= TEXTUAL-CONVENTION
    STATUS        current
    DESCRIPTION
        ""
    SYNTAX        INTEGER
    {
        deleteOnClear(1),
        initialSeverity(2)
    }

CucsConditionActionIndicator ::= TEXTUAL-CONVENTION
    STATUS        current
    DESCRIPTION
        ""
    SYNTAX        INTEGER
    {
        creation(0),
        modification(1),
        deletion(2),
        stateTransition(3),
        special(4),
        failure(5)
    }

CucsConditionAdminState ::= TEXTUAL-CONVENTION
    STATUS        current
    DESCRIPTION
        ""
    SYNTAX        INTEGER
    {
        disabled(0),
        enabled(1)
    }

CucsConditionCallHomeCause ::= TEXTUAL-CONVENTION
    STATUS        current
    DESCRIPTION
        ""
    SYNTAX        INTEGER
    {
        unspecified(0),
        equipmentInoperable(1),
        thermalProblem(2),
        connectivityProblem(3),
        licenseGraceperiodExpired(4),
        mgmtifDown(5),
        linkDown(6),
        electionFailure(7),
        managementServicesFailure(8),
        managementServicesUnresponsive(9),
        versionIncompatible(10),
        identityUnestablishable(11),
        equipmentInaccessible(12),
        configurationFailure(13),
        associationFailed(14),
        powerProblem(15),
        equipmentProblem(16),
        voltageProblem(17),
        fruProblem(18),
        equipmentDisabled(19),
        limitReached(20),
        equipmentOffline(21),
        inventoryFailed(22),
        portFailed(23),
        vifIdsMismatch(24),
        arpTargetsConfigError(25),
        equipmentDegraded(26),
        ndiscTargetsConfigError(27),
        adaptorMismatch(28),
        healthLedAmberBlinking(29),
        healthLedAmber(30),
        nearMaxLimit(31),
        memoryError(32),
        capacityProblem(33),
        healthProblem(34),
        invalidControllerProfileCount(35),
        equipmentRemoved(36),
        psuInsufficient(37),
        psuMixedMode(38),
        smallVolumeSpace(39),
        noVolumeSpace(40),
        raidgroupOffline(41),
        raidgroupDegraded(42),
        raidgroupRebuilding(43),
        raidgroupBad(44),
        adminStateOffline(45),
        cimcBackupTriggerNotEnabled(46),
        cimcHeartbeatTimedOut(47),
        notSupported(48),
        equipmentMissing(49),
        configurationMismatch(50),
        kernelMemCriticalThreshold(51),
        fanRemoval(52),
        healthCritical(53),
        healthMajor(58),
        equipmentDeprecated(59),
        equipmentUnhealthy(60),
        imageUnusable(61),
        equipmentUnacknowledged(62),
        backplanePortProblem(63),
        pciConfigIssue(64),
        fabricEvacuated(65),
        mgmtDbCorruption(66),
        hardwareMismatch(67),
        chassisIntrusion(68),
        configProblem(69),
        hardwareInventoryMismatch(70),
        pciConfigMismatch(71),
        unsupportedConfig(72),
        configMismatch(73),
        equipmentNonOptimal(74),
        inoperable(75),
        persistentMemoryDetection(76),
        equipmentPeerDimmDisabled(77),
        equipmentDimmDisabled(78),
        uplinkPortTypeMisconfigured(79),
        equipmentSelftestfailed(80),
        uplinkPortChannelMisconfigured(81),
        healthWarning(82),
        healthMinor(83),
        unsupportedController(84),
        configurationError(85),
        interfaceFailed(86),
        unsupportedDrive(87)
    }

CucsConditionCause ::= TEXTUAL-CONVENTION
    STATUS        current
    DESCRIPTION
        ""
    SYNTAX        INTEGER
    {
        unknown(0),
        transition(1),
        beginFailed(2),
        fsmFailed(3),
        checkLicenseFailed(4),
        identifyFailed(5),
        configureSwMgmtEndPointFailed(6),
        configureVifNsFailed(7),
        configureEndPointFailed(8),
        discoverChassisFailed(9),
        enableChassisFailed(10),
        decomissionFailed(11),
        unIdentifyLocalFailed(12),
        cleanupEntriesFailed(13),
        waitFailed(14),
        disableEndPointFailed(15),
        unIdentifyPeerFailed(16),
        executeFailed(17),
        deployFailed(18),
        bmcConfigureConnLocalFailed(20),
        swConfigureConnLocalFailed(21),
        bmcConfigureConnPeerFailed(22),
        swConfigureConnPeerFailed(23),
        bmcPresenceFailed(24),
        bmcInventoryFailed(25),
        preSanitizeFailed(26),
        sanitizeFailed(27),
        configUserAccessFailed(28),
        swConfigPnuoslocalFailed(29),
        swConfigPnuospeerFailed(30),
        configDiscoveryModeFailed(31),
        swUnconfigPortNivLocalFailed(32),
        swUnconfigPortNivPeerFailed(33),
        bootPnuosFailed(35),
        bootWaitFailed(36),
        biosPostCompletionFailed(37),
        readSmbiosFailed(38),
        hagConnectFailed(39),
        pnuosidentFailed(40),
        pnuospolicyFailed(41),
        pnuosinventoryFailed(42),
        pnuosscrubFailed(43),
        pnuosconnectivityFailed(44),
        pnuosconnStatusFailed(45),
        swPnuosconnectivityLocalFailed(46),
        swPnuosconnectivityPeerFailed(47),
        pnuosselfTestFailed(48),
        hagDisconnectFailed(51),
        bmcShutdownDiscoveredFailed(52),
        handlePoolingFailed(53),
        successFailed(54),
        failFailed(55),
        configFeLocalFailed(56),
        swConfigPortNivLocalFailed(57),
        swConfigPortNivPeerFailed(58),
        nicPresenceLocalFailed(59),
        nicPresencePeerFailed(60),
        nicInventoryLocalFailed(61),
        nicInventoryPeerFailed(62),
        deriveConfigFailed(63),
        configSolFailed(64),
        swConfigLocalFailed(65),
        swConfigPeerFailed(66),
        nicConfigLocalFailed(67),
        nicConfigPeerFailed(68),
        stopvmediaLocalFailed(69),
        stopvmediaPeerFailed(70),
        setupvmediaLocalFailed(71),
        setupvmediaPeerFailed(72),
        bladeBootFailed(73),
        bladeBootWaitFailed(74),
        bladeReadSmbiosFailed(75),
        hostConnectFailed(76),
        startMemoryTestStatusFailed(77),
        pollMemoryTestStatusFailed(78),
        hostIdentFailed(79),
        hostPolicyFailed(80),
        setDiagUserFailed(81),
        hostInventoryFailed(82),
        hostServerDiagFailed(83),
        hostServerDiagStatusFailed(84),
        disableServerConnSwBfailed(85),
        startFabricatrafficTestFailed(86),
        fabricatrafficTestStatusFailed(87),
        enableServerConnSwBfailed(88),
        disableServerConnSwAfailed(89),
        startFabricbtrafficTestFailed(90),
        fabricbtrafficTestStatusFailed(91),
        enableServerConnSwAfailed(92),
        generateReportFailed(93),
        generateLogWaitFailed(94),
        debugWaitFailed(95),
        removevmediaLocalFailed(96),
        removevmediaPeerFailed(97),
        nicUnconfigLocalFailed(98),
        nicUnconfigPeerFailed(99),
        swUnconfigLocalFailed(100),
        swUnconfigPeerFailed(101),
        removeConfigFailed(102),
        restoreConfigFeLocalFailed(103),
        restoreConfigFePeerFailed(104),
        unconfigUserAccessFailed(105),
        unconfigSolFailed(106),
        hostDisconnectFailed(107),
        bmcShutdownDiagCompletedFailed(108),
        evaluateStatusFailed(109),
        primaryFailed(110),
        secondaryFailed(111),
        executeLocalFailed(112),
        executePeerFailed(113),
        nicConfigPnuoslocalFailed(114),
        nicConfigPnuospeerFailed(115),
        setupVmediaLocalFailed(116),
        setupVmediaPeerFailed(117),
        bladeBootPnuosFailed(118),
        nicUnconfigPnuoslocalFailed(119),
        nicUnconfigPnuospeerFailed(120),
        swUnconfigPnuoslocalFailed(121),
        swUnconfigPnuospeerFailed(122),
        teardownVmediaLocalFailed(123),
        teardownVmediaPeerFailed(124),
        updateibmcfwFailed(125),
        waitForibmcfwUpdateFailed(126),
        activateibmcfwFailed(127),
        resetibmcFailed(128),
        powerOnFailed(129),
        updateAdaptorNwFwLocalFailed(130),
        updateAdaptorNwFwPeerFailed(131),
        waitForAdaptorNwFwUpdateLocalFailed(132),
        waitForAdaptorNwFwUpdatePeerFailed(133),
        activateAdaptorNwFwLocalFailed(134),
        activateAdaptorNwFwPeerFailed(135),
        hagPnuosconnectFailed(136),
        pnuosvalidateFailed(137),
        biosImgUpdateFailed(138),
        storageCtlrImgUpdateFailed(139),
        hbaImgUpdateFailed(140),
        nicImgUpdateFailed(141),
        pnuosconfigFailed(142),
        pnuoslocalDiskConfigFailed(143),
        swConfigHostoslocalFailed(144),
        swConfigHostospeerFailed(145),
        nicConfigHostoslocalFailed(146),
        nicConfigHostospeerFailed(147),
        hagPnuosdisconnectFailed(148),
        pnuosunloadDriversFailed(149),
        prepareForBootFailed(150),
        configUuidFailed(151),
        bootHostFailed(152),
        waitForConnReadyFailed(153),
        hostosidentFailed(154),
        hostospolicyFailed(155),
        hostosvalidateFailed(156),
        hostosconfigFailed(157),
        nicUnconfigHostoslocalFailed(158),
        nicUnconfigHostospeerFailed(159),
        swUnconfigHostoslocalFailed(160),
        swUnconfigHostospeerFailed(161),
        pnuosunconfigFailed(162),
        unconfigUuidFailed(163),
        shutdownFailed(164),
        unconfigSoLfailed(165),
        configFailed(166),
        swUnconfigureLocalFailed(167),
        swUnconfigurePeerFailed(168),
        startFailed(169),
        cleanupFailed(170),
        resetFailed(171),
        unconfigBiosFailed(172),
        applyTemplateFailed(173),
        applyIdentifiersFailed(174),
        applyPoliciesFailed(175),
        resolveBootConfigFailed(176),
        evaluateAssociationFailed(177),
        analyzeImpactFailed(178),
        waitForMaintPermissionFailed(179),
        waitForMaintWindowFailed(180),
        reconfigUuidFailed(181),
        updateEthMonFailed(182),
        updateFcMonFailed(183),
        serverMoved(186),
        serverIdentificationProblem(187),
        primaryVlanMissingIsolated(188),
        namedPolicyUnresolved(189),
        localFailed(190),
        peerFailed(191),
        lin(192),
        equipmentInoperable(193),
        thermalProblem(194),
        voltageProblem(195),
        capacityExceeded(196),
        equipmentDegraded(197),
        identityUnestablishable(198),
        setEpLocalFailed(199),
        setEpPeerFailed(200),
        propogateEpSettingsFailed(201),
        propogateEpTimeZoneSettingsLocalFailed(202),
        propogateEpTimeZoneSettingsPeerFailed(203),
        restartFailed(204),
        setRealmLocalFailed(205),
        setRealmPeerFailed(206),
        setUserPeerFailed(208),
        setKeyRingLocalFailed(209),
        setKeyRingPeerFailed(210),
        unidentifiableFru(211),
        equipmentMissing(212),
        connectivityProblem(213),
        linkDown(214),
        linkMisconnected(215),
        disableFailed(216),
        enableFailed(217),
        disableAfailed(218),
        enableAfailed(219),
        propogateEpTimeZoneSettingsToAdaptorsLocalFailed(220),
        propogateEpTimeZoneSettingsToAdaptorsPeerFailed(221),
        vifDown(222),
        updateConnectivityFailed(223),
        createLocalFailed(224),
        createRemoteFailed(225),
        unpackLocalFailed(226),
        deleteLocalFailed(227),
        copyRemoteFailed(228),
        remoteFailed(229),
        updateLocalFailed(230),
        verifyLocalFailed(231),
        resetLocalFailed(232),
        updateRemoteFailed(233),
        verifyRemoteFailed(234),
        resetRemoteFailed(235),
        updateRequestFailed(236),
        pollUpdateStatusFailed(237),
        activateFailed(238),
        updateRequestLocalFailed(239),
        updateRequestPeerFailed(240),
        pollUpdateStatusLocalFailed(241),
        pollUpdateStatusPeerFailed(242),
        powerOffFailed(243),
        copyPrimaryFailed(244),
        imageDeleted(245),
        imageUnusable(246),
        imageCannotBoot(247),
        psuInsufficient(248),
        rescanImagesFailed(249),
        pollUpdateOfcimcFailed(250),
        syncBladeaglocalFailed(251),
        syncBladeagremoteFailed(252),
        syncNicaglocalFailed(253),
        syncNicagremoteFailed(254),
        syncPortaglocalFailed(255),
        syncPortagremoteFailed(256),
        syncHostagentaglocalFailed(257),
        syncHostagentagremoteFailed(258),
        finalizeFailed(259),
        validateLocalFailed(260),
        validateRemoteFailed(261),
        deleteRemoteFailed(262),
        licenseGraceperiodEntered(263),
        licenseGraceperiod10days(264),
        oldChassisComponentFirmware(265),
        licenseGraceperiod60days(266),
        psuFailure(267),
        psuRedundancyFail(268),
        licenseGraceperiodExpired(269),
        powerConsumptionHitLimit(270),
        noAckFromBios(271),
        portFailed(272),
        interfaceFailed(273),
        operationalStateDown(274),
        cmcVifDown(275),
        setLocalFailed(276),
        setPeerFailed(277),
        switchFailed(278),
        limitReached(279),
        emptyPool(280),
        decommissioned(283),
        uploadFailed(284),
        downloadLocalFailed(285),
        tftpServerError(286),
        electionFailure(287),
        managementServicesFailure(288),
        managementServicesUnresponsive(289),
        haNotReady(290),
        versionIncompatible(291),
        logCapacity(293),
        fileTransferFailed(294),
        insufficientResources(296),
        insufficientlyEquipped(297),
        powerProblem(298),
        discoveryFailed(299),
        associationFailed(300),
        unsupportedTransceiver(301),
        resolveHostpackPolicyFailed(302),
        discoveryInProgress(303),
        resolveMaintPolicyFailed(304),
        unconfigurationInProgress(305),
        poweredOff(306),
        inMaintenance(307),
        underTest(308),
        serverUnassociated(309),
        serverAssociating(310),
        unassociated(311),
        serverDeassociating(312),
        serverUnassigned(313),
        serverAssigned(314),
        configurationNotApplied(315),
        configurationApplying(316),
        propogateEpTimeZoneSettingsToFexIomLocalFailed(317),
        serverFailed(318),
        configurationFailure(319),
        maintenanceFailed(320),
        equipmentRemoved(321),
        serverInaccessible(322),
        getVersionFailed(324),
        removeLocalFailed(325),
        setEpAfailed(326),
        setEpBfailed(327),
        satelliteConnectionAbsent(328),
        satelliteConnectionInit(329),
        satelliteMisConnected(330),
        unexpectedNumberOfLinks(331),
        equipmentOffline(332),
        performanceProblem(333),
        firmwareUpgradeProblem(334),
        unsupportedConnectivityConfiguration(335),
        equipmentUnacknowledged(336),
        autoFirmwareUpgrade(337),
        equipmentDisconnected(338),
        fruProblem(339),
        thresholdCrossed(340),
        deviceSEEPROMIOError(345),
        assignmentFailed(353),
        deviceSeepromError(355),
        newLink(360),
        bmcPreconfigPnuoslocalFailed(361),
        bmcPreconfigPnuospeerFailed(362),
        bmcConfigPnuosFailed(363),
        solRedirectEnableFailed(364),
        serialDebugConnectFailed(365),
        bmcUnconfigPnuosFailed(366),
        serialDebugDisconnectFailed(367),
        solRedirectDisableFailed(368),
        configNivModeFailed(369),
        cleanupLocalFailed(370),
        cleanupPeerFailed(371),
        configFePeerFailed(372),
        bladePowerOnFailed(373),
        cleanupServerConnSwAfailed(374),
        cleanupServerConnSwBfailed(375),
        bmcPreConfigPnuoslocalFailed(376),
        bmcPreConfigPnuospeerFailed(377),
        bladePowerOffFailed(378),
        updateBoardCtrlRequestFailed(379),
        pollBoardCtrlUpdateStatusFailed(380),
        serialDebugPnuosconnectFailed(381),
        localDiskFwUpdateFailed(382),
        serialDebugPnuosdisconnectFailed(383),
        configSoLfailed(384),
        hagHostosconnectFailed(385),
        configBiosFailed(386),
        cleanupcimcFailed(387),
        aFailed(388),
        bFailed(389),
        reconfigBiosFailed(390),
        applyConfigFailed(391),
        mgmtifDown(392),
        validateConfigurationFailed(393),
        applyPhysicalFailed(394),
        waitOnPhysFailed(395),
        emptyPinGroup(396),
        membershipDown(397),
        vsanMisconfigured(398),
        incompatibleSpeed(399),
        configError(400),
        vlanMisconfigured(401),
        interfaceMisconfigured(402),
        missingPrimaryVlan(403),
        pinningMismatch(404),
        pinningMisconfig(405),
        equipmentDisabled(406),
        propogateEpTimeZoneSettingsToFexIomPeerFailed(407),
        setUserLocalFailed(408),
        linkMissing(409),
        updateAdaptorFailed(410),
        enableBfailed(411),
        copySubFailed(412),
        deleteSubFailed(413),
        deletePrimaryFailed(414),
        groupCapInsufficient(415),
        oldFirmware(416),
        powerCapFail(417),
        noCapFail(418),
        portInventorySwAfailed(419),
        portInventorySwBfailed(420),
        configSwAfailed(421),
        updatecimcFailed(422),
        verifyPhysConfigFailed(423),
        activateLocalFailed(424),
        activatePeerFailed(425),
        prepareForUpdateFailed(426),
        activationFailed(427),
        applyFailed(428),
        licenseGraceperiod30days(430),
        licenseGraceperiod90days(432),
        licenseGraceperiod119days(433),
        licenseFileUninstallable(434),
        licenseFileNotDeleted(435),
        backupLocalFailed(436),
        reportResultsFailed(437),
        deviceSharedStorageError(438),
        haSshKeysMismatched(439),
        ucsmProcessFailure(440),
        equipmentInaccessible(441),
        nonExistentScheduler(442),
        executeAfailed(443),
        waitForFirmwareApplyFailed(444),
        powerDown(445),
        leadershipChange(446),
        deviceSharedStorageIOError(447),
        serverAssociated(448),
        configurationApplied(449),
        pollPostDiskZoneStorageInvcimcFailed(450),
        inventoryFailed(454),
        configureFailed(455),
        clearFailed(456),
        pollClearStatusFailed(457),
        pollActivateStatusFailed(458),
        updateTokensFailed(459),
        hostCatalogFailed(460),
        pnuoscatalogFailed(461),
        clearBiosUpdateFailed(462),
        pollClearBiosUpdateStatusFailed(463),
        updateBiosRequestFailed(464),
        pollBiosUpdateStatusFailed(465),
        activateBiosFailed(466),
        pollBiosActivateStatusFailed(467),
        fexUnsupported(468),
        invalidKeyringCertificate(469),
        invalidTrustpointCertChain(470),
        disassociationFailed(471),
        vifIdsMismatch(472),
        profileConfigIncorrect(473),
        updateVlanGroupsFailed(474),
        updateZonesFailed(475),
        vlanCompNotSupport(476),
        anotherConnectionAlreadyEnabled(477),
        connectionUnused(478),
        unsupportedConnectivity(479),
        reportFailed(480),
        providerGroupAlreadyExists(481),
        noVlanOptimization(482),
        roleConfigError(483),
        localeConfigError(484),
        userRoleConfigError(485),
        userLocaleConfigError(486),
        keyringConfigError(487),
        snmpConfigError(488),
        timezoneFileNotExists(489),
        userConfigError(490),
        snmpUserConfigError(491),
        commSvcConfigError(492),
        inaccessibleVlanReferenced(493),
        referencedVlanUnresolvable(494),
        invalidVlanInTheAllowedVlanList(495),
        vlanConflictPermit(496),
        vlanPermitUnresolved(497),
        groupPermitUnresolved(498),
        removeFailed(499),
        arpTargetsConfigError(500),
        newVnicVconSchemeApplied(501),
        suspendModeEntered(502),
        verifyGuidFailed(503),
        unregisterFailed(504),
        cleanOldDataFailed(505),
        requestFailed(506),
        verifyFailed(507),
        resolveFailed(508),
        releaseFailed(509),
        resolveManyFailed(510),
        releaseManyFailed(511),
        resolveAllFailed(512),
        releaseAllFailed(513),
        registerClientFailed(514),
        verifyRegistrationFailed(515),
        mountLocalFailed(516),
        mountPeerFailed(517),
        unmountLocalFailed(518),
        unmountPeerFailed(519),
        checkPowerAvailabilityFailed(520),
        markAdapterForRebootFailed(521),
        deassertResetBypassFailed(522),
        verifyFcZoneConfigFailed(523),
        cleanupPortConfigLocalFailed(524),
        cleanupPortConfigPeerFailed(525),
        powerCycleFailed(526),
        resolveIdentifiersFailed(527),
        applyDefaultIdentifiersFailed(528),
        resolveDefaultIdentifiersFailed(529),
        resolvePoliciesFailed(530),
        resolveDistributableNamesFailed(531),
        resolveDistributableFailed(532),
        resolveImagesFailed(533),
        resolveScheduleFailed(534),
        provisionStorageFailed(535),
        waitForStorageProvisionFailed(536),
        commitStorageFailed(537),
        waitForCommitStorageFailed(538),
        waitForAssocCompletionFailed(539),
        enablePortFailed(540),
        loadCatalogFailed(541),
        pingFailed(542),
        suppressStatusChange(543),
        fcoeUplinkUnsupportedFiSettings(544),
        fcoeUplinkPortChannelUnsupportedFiSettings(545),
        invalidTarget(546),
        fcZoningEnabled(547),
        configurationError(548),
        fcStorageportNpvMode(549),
        fcoeStorageportNpvMode(550),
        fcPortchannelMembersInconsistentSpeed(551),
        vlanMcastPolicyMisconfigured(552),
        clientLostConnectivity(553),
        callhomeConfigError(554),
        copyExtToLocalFailed(555),
        copyExtToPeerFailed(556),
        copyToLocalFailed(557),
        copyToPeerFailed(558),
        waitForDeployFailed(559),
        activateucsmFailed(560),
        pollActivateOfucsmFailed(561),
        updateiomFailed(562),
        pollUpdateOfiomFailed(563),
        activateiomFailed(564),
        pollActivateOfiomFailed(565),
        activateRemotefiFailed(566),
        pollActivateOfRemotefiFailed(567),
        waitForUserAckFailed(568),
        activateLocalfiFailed(569),
        pollActivateOfLocalfiFailed(570),
        activateCatalogFailed(571),
        referencedVsanUnresolvable(572),
        operationFailed(573),
        localeOrgConfigError(574),
        resolveNetworkPoliciesFailed(575),
        resolveNetworkTemplatesFailed(576),
        validatePolicyOwnershipFailed(577),
        configFlexFlashFailed(578),
        syncPowerStateFailed(579),
        unconfigFlexFlashFailed(580),
        syncFailed(581),
        reportFullInventoryFailed(582),
        healthLedAmberBlinking(583),
        healthLedAmber(584),
        extraPrimaryVlans(585),
        licenseInsufficient(586),
        checkInventoryStatusFailed(587),
        providerGroupSizeEmpty(589),
        postSetKeyRingLocalFailed(590),
        postSetKeyRingPeerFailed(591),
        cimcvlanCfgLocalFailed(592),
        cimcvlanCfgPeerFailed(593),
        cmcvlanCfgFailed(594),
        cmcvlanCfgPeerFailed(595),
        activeFailed(596),
        oobStorageInventoryFailed(597),
        configFlexFlashScrubFailed(598),
        powerOnPreConfigFailed(599),
        swConfigServiceInfraLocalFailed(600),
        swConfigServiceInfraPeerFailed(601),
        nicConfigServiceInfraLocalFailed(602),
        nicConfigServiceInfraPeerFailed(603),
        nicUnconfigServiceInfraLocalFailed(604),
        nicUnconfigServiceInfraPeerFailed(605),
        swUnConfigLocalFailed(606),
        swUnConfigPeerFailed(607),
        nicUnConfigLocalFailed(608),
        nicUnConfigPeerFailed(609),
        defaultHostpackMissing(610),
        defaultHostpackMissingVersions(611),
        serverPowerOffFailed(612),
        serverPowerOnFailed(613),
        namedVlanUnresolved(614),
        referencedRemoteVlanUnresolvable(615),
        referencedRemoteVsanUnresolvable(616),
        multipleConnectionPolicies(617),
        boardCtrlUpgraded(618),
        configMemoryPolicyFailed(619),
        incompatibleServerFirmware(620),
        inbandVlanNameResolutionFailure(621),
        ndiscTargetsConfigError(622),
        updateEthFlowMonFailed(623),
        equipmentUnhealthy(624),
        vmNetworkReferenceIncorrect(625),
        serverDoesNotSupportInband(626),
        udldLinkDown(627),
        vmediaMountInaccessible(630),
        cimcFirmwareMismatch(631),
        pldFirmwareMismatch(632),
        unconfigExtMgmtRulesFailed(633),
        unconfigExtMgmtGwFailed(634),
        unconfigCimcvmediaFailed(635),
        configExtMgmtRulesFailed(636),
        configExtMgmtGwFailed(637),
        configCimcvmediaFailed(638),
        graphicsImageUpdateFailed(639),
        configKvmMgmtDefaultSettingFailed(640),
        downloadImagesFailed(641),
        configBackupOutdated(642),
        updateFlashLifeFailed(643),
        copyImgFromRepFailed(644),
        copyiomimgToSubFailed(646),
        unsupportedCimcFirmware(647),
        primaryVlanMissingForIsolated(648),
        primaryVlanMissingForCommunity(649),
        vlanMismatch(650),
        vlanErrorAssocPrimary(651),
        deleteCurlDownloadedImagesFailed(652),
        svnicNotPresent(653),
        extraSecondaryVlans(654),
        extraSecondaryVlansPerPrimary(655),
        serverError(656),
        copyCatFromRepFailed(657),
        formatFailed(658),
        pairFailed(659),
        namedInbandVlanUnresolved(660),
        inbandUnsupportedServer(661),
        checkAssignedIdentifiersForDupFailed(662),
        checkAssignedDefaultIdentifiersForDupFailed(663),
        duplicatedAssigned(664),
        adaptorMismatch(665),
        tpmOnSlaveBoard(666),
        nearMaxLimit(667),
        memoryError(668),
        capacityProblem(669),
        healthProblem(670),
        invalidControllerProfileCount(671),
        psuMixedMode(673),
        powerBudgetUnavailable(674),
        smallVolumeSpace(675),
        noVolumeSpace(676),
        raidgroupOffline(677),
        raidgroupDegraded(678),
        raidgroupRebuilding(679),
        raidgroupBad(680),
        adminStateOffline(681),
        cimcBackupTriggerNotEnabled(682),
        cimcHeartbeatTimedOut(683),
        diskWearNonCriticalThreshold(684),
        diskWearCriticalThreshold(685),
        configDiskFailed(686),
        configLunFailed(687),
        verifyConfigFailed(688),
        verifySnapshotConfigFailed(689),
        verifyReplicationConfigFailed(690),
        initiatePollbmclocalFailed(691),
        initiatePollbmcremoteFailed(692),
        waitForosstatusFailed(693),
        connectsmelocalFailed(694),
        connectsmeremoteFailed(695),
        waitForsmeconnectionFailed(696),
        waitForInventoryFailed(697),
        disableStorageTargetFailed(698),
        waitForServerShutdownFailed(699),
        slotPowerCycleFailed(700),
        waitForhaquorumFailed(701),
        waitForServerPowerUpFailed(702),
        enableStorageTargetFailed(703),
        confighastateFailed(704),
        configNetworkFailed(705),
        configPlatformFailed(706),
        configStorageTargetIdentityFailed(707),
        configStorageReplicationServiceFailed(708),
        undeployStorageFailed(709),
        waitForUndeployStorageFailed(710),
        undeployTargetIdentityFailed(711),
        undeployPlatformFailed(712),
        undeployNetworkFailed(713),
        disassocStorageControllerFailed(714),
        waitForDisassocCompletionFailed(715),
        performHaTakeOverFailed(716),
        performEraseFailed(717),
        waitForEraseCompletionFailed(718),
        fullInventoryFailed(727),
        beginInventoryFailed(728),
        reportPhysicalInventoryFailed(729),
        reportOrgInventoryFailed(730),
        reportStorageInventoryFailed(731),
        endInventoryFailed(732),
        powerButtonLockConfigFailed(733),
        powerOffWaitFailed(734),
        powerOffReclaimFailed(735),
        evaluateIdentityFailed(742),
        configbmcpowerParamsFailed(743),
        powerDeployWaitFailed(744),
        pnuospowerProfilingFailed(745),
        sendBmcProfilingInitFailed(746),
        sendBmcProfilingDoneFailed(747),
        oobStorageConfigFailed(749),
        verifyRemoteStorageConfigFailed(750),
        nicConfigParamsHostoslocalFailed(751),
        nicConfigParamsHostospeerFailed(752),
        bmcUpdateHostPreBootFailed(753),
        waitForUnConfigAppliancesFailed(754),
        tearDownvmediaLocalFailed(756),
        tearDownvmediaPeerFailed(757),
        configChassisIdFailed(758),
        resolveStorageScheduleFailed(759),
        resolveVolumesFailed(760),
        setLocatorLedLocalFailed(764),
        setLocatorLedPeerFailed(765),
        waitForServerAssocFailed(768),
        waitForPlatformBootFailed(769),
        waitForosinstallFailed(770),
        waitForPlatformConfigFailed(771),
        hostBootForUpgradeFailed(772),
        hostBmcPreConfigLocalFailed(773),
        hostBmcPreConfigPeerFailed(774),
        hostSetupVmediaLocalFailed(775),
        hostSetupVmediaPeerFailed(776),
        hostClearOsInstallStatusFailed(777),
        hostSolRedirectEnableFailed(778),
        hostSerialDebugConnectFailed(779),
        hostBootFailed(780),
        hostBootWaitFailed(781),
        hostBiosPostCompletionFailed(782),
        hostReadSmbiosFailed(783),
        hostPreInstallFailed(784),
        hostPostInstallFailed(785),
        hostPreFirstBootFailed(786),
        hostPostFirstBootFailed(787),
        hostPostUpgradeFailed(788),
        hostTeardownVmediaLocalFailed(789),
        hostTeardownVmediaPeerFailed(790),
        hostSerialDebugDisconnectFailed(791),
        hostSolRedirectDisableFailed(792),
        activatePsuFailed(794),
        notSupported(795),
        equipmentInventory(796),
        cartridgeMoved(798),
        configurationMismatch(799),
        pollActivationFailed(800),
        powerOffServersFailed(801),
        serversPowerOffCompletionFailed(802),
        unsupportedModel(803),
        deleteImagesRemoteFailed(804),
        oobDiskScrubFailed(805),
        cimcPresenceFailed(806),
        cleanupNicConfigLocalFailed(807),
        cleanupNicConfigPeerFailed(808),
        cleanupVnicsLocalFailed(809),
        cleanupVnicsPeerFailed(810),
        sharediomoduleInventoryFailed(811),
        internalBackupFailed(812),
        pollInternalBackupFailed(813),
        unlockFirmwareImageFailed(814),
        precleanupPortConfigFailed(815),
        readSmBiosFailed(816),
        defaultauthConfigError(817),
        domainConfigError(818),
        fault(819),
        localInternalBackupFailed(820),
        reportFaultInventoryFailed(821),
        conditionCauseConfigurationFailure(822),
        conditionCauseFault(823),
        configMissing(825),
        pollWaitForUserAckFailed(826),
        setupVmediaFailed(827),
        unconfigVmediaFailed(828),
        equipmentAccessibilityProblem(829),
        equipmentLinkDegraded(830),
        powerCycleBoardFailed(831),
        pollBoardCtrlPowerCycleFailed(832),
        discoverSasExpanderFailed(833),
        vsanExceedLimit(834),
        comprSetsExhausted(836),
        kernelMemCriticalThreshold(837),
        unsupportedPolicyConfig(838),
        fanRemoval(839),
        healthWarning(840),
        healthMinor(841),
        healthMajor(842),
        healthCritical(843),
        checkAdaptorFw40gcapFailed(845),
        calculateVlanGroupForHostoslocalFailed(846),
        calculateVlanGroupForHostospeerFailed(847),
        applyMaintConfigFailed(848),
        unsupportedConfig(849),
        equipmentFailed(855),
        verifyBreakoutConfigFailed(857),
        copyAllImagesToPeerFailed(860),
        cleanUpvifsFailed(861),
        vlanCompGrpCountExceedsLimit(862),
        fiBQuerierIpEmptyOrSameAsPrimary(863),
        deprecated(864),
        invalidPinning(865),
        extraVif(866),
        equipmentDeprecated(867),
        nativeVlanNotFound(868),
        vlanCompression(869),
        configFanSpeedFailed(870),
        sasExpanderImgUpdateFailed(871),
        chassisLimitExceeded(872),
        conditionCauseKernelMemCriticalThreshold(873),
        mgmtDbCorruption(874),
        bmcFactoryResetFailed(875),
        applyMoPropsFailed(876),
        deleteAllMoRefsFailed(877),
        maxVlanLimitExceeded(878),
        initIptablesLocalFailed(879),
        initIptablesPeerFailed(880),
        replicationFailure(881),
        tpmMismatch(882),
        validateRemovalFailed(883),
        updateStorageInvcmcFailed(884),
        updateStorageInvcimcFailed(885),
        pollUpdateStorageInvcimcFailed(886),
        backplanePortProblem(887),
        standbycmcvlanCfgFailed(888),
        postScrubOobStorageInventoryFailed(889),
        oobSasExpanderImgUpdateFailed(890),
        oobPollSasExpanderUpdateStatusFailed(891),
        oobSasExpanderImgActivateFailed(892),
        oobPollSasExpanderActivateStatusFailed(893),
        ciscoosopenGateFailed(894),
        storageInventoryFailed(895),
        waitBeforeInstallationFailed(896),
        updateCmcFailed(897),
        pollUpdateCmcFailed(898),
        pollUpdateAdaptorFailed(900),
        updateSasExpanderFailed(901),
        pollUpdateSasExpanderFailed(902),
        activateSasExpanderFailed(903),
        pollSasExpanderActivateFailed(904),
        activateCmcFailed(905),
        pollCmcActivationFailed(906),
        waitForPowerOffFailed(907),
        activateAdaptorFailed(908),
        pollAdaptorActivationFailed(909),
        activateStorageCtlrFailed(910),
        pollStorageCtlrActivationFailed(911),
        activateBrdCtlrFailed(912),
        pollBrdCtlrActivationFailed(913),
        activateLocalDiskFailed(914),
        powerOnServersFailed(915),
        diskZoningConfigFailed(916),
        postDiskZoneStorageInvcmcFailed(917),
        postDiskZoneStorageInvcimcFailed(918),
        completeFailed(920),
        equipmentLinkMisconnect(921),
        equipmentFruMissing(922),
        equipmentUnavailable(923),
        equipmentHotspareUnsupported(924),
        equipmentOwnershipUnsupported(925),
        equipmentIoeOwnershipUnassigned(926),
        equipmentHddslotServer2OwnershipUnassigned(927),
        chassisProfileUnassociated(928),
        chassisProfileAssociating(929),
        chassisProfileAssociated(930),
        chassisProfileDeassociating(931),
        chassisProfileUnassigned(932),
        chassisProfileAssigned(933),
        verifyUserZoneConfigFailed(934),
        pollSecureBootStatusFailed(935),
        resetSasExpanderFailed(936),
        pollLocalDiskActivateFailed(937),
        waitForActivationFailed(938),
        updateFailed(939),
        versionHolderChange(940),
        networkSanGroupDoesNotExist(941),
        updateSpLocalFailed(942),
        updateSpRemoteFailed(943),
        assertBypassWaitFailed(944),
        fabEvacOnRemotefiFailed(945),
        pollFabEvacOnRemotefiFailed(946),
        fabEvacOffRemotefiFailed(947),
        pollFabEvacOffRemotefiFailed(948),
        failOverToRemotefiFailed(949),
        pollFailOverToRemotefiFailed(950),
        activateucsmservicePackFailed(951),
        pollActivateOfucsmservicePackFailed(952),
        disableScriptablevmediaFailed(953),
        preconfigVmediaLocalFailed(954),
        preconfigVmediaPeerFailed(955),
        setupBootEnvironmentFailed(956),
        powerOnWaitFailed(957),
        runTestsFailed(958),
        logTransferFailed(959),
        waitForDebugFailed(960),
        tearDownBootEnvironmentFailed(961),
        pnuosperipheralComponentConfigFailed(962),
        configMgmtIpRulesFailed(963),
        hostosconnectFailed(964),
        configHostOsAnnotationsFailed(965),
        configServerIdentityFailed(966),
        unconfigServerIdentityFailed(967),
        kmipCertConfigFailed(968),
        kmipSaveCertFailed(969),
        estimateApplyConfigFailed(970),
        configChassisAdapterConnectivityFailed(971),
        portMisconfigure(972),
        transceiverMismatch(973),
        pciConfigIssue(974),
        fabricEvacuated(975),
        unicastMacExhausted(976),
        multicastMacExhausted(977),
        pvlifVlanMbrExhausted(978),
        pvsystemExhausted(979),
        igmpGroupExhausted(980),
        hardwareMismatch(981),
        chassisIntrusion(982),
        configProblem(983),
        networkSanGroupMisconfigured(984),
        reportErrorFailed(985),
        resolveFromPolicyMgrFailed(986),
        resolveFromOpsMgrFailed(987),
        kmipFault(988),
        hardwareInventoryMismatch(989),
        pciConfigMismatch(990),
        equipmentSecondControllerAbsent(991),
        conditionCauseHardwareInventoryMismatch(992),
        conditionCausePciConfigMismatch(993),
        healthInfo(994),
        removePeerFailed(995),
        imageCorrupted(996),
        restoreVdStatusFailed(997),
        configMismatch(998),
        configSwitchPeerFailed(999),
        configSwitchLocalFailed(1000),
        sasExpanderConfigFailed(1001),
        pollSasExpanderConfigFailed(1002),
        swPortDetailsLocalFailed(1003),
        swPortDetailsPeerFailed(1004),
        swConfigurePortChannelLocalFailed(1005),
        swConfigurePortChannelPeerFailed(1006),
        pnuosBootWaitFailed(1007),
        swHostosmultiPortConnectivityLocalFailed(1008),
        swHostosmultiPortConnectivityPeerFailed(1009),
        swHostosconfigurePortChannelLocalFailed(1010),
        swHostosconfigurePortChannelPeerFailed(1011),
        oobSasExpanderBootImgActivateFailed(1012),
        oobPollSasExpanderBootImgActivateStatusFailed(1013),
        mswitchImgUpdateFailed(1014),
        resetCimcFailed(1015),
        equipmentNonOptimal(1016),
        vhbaNotSupported(1017),
        inoperable(1018),
        iftmcPvExhausted(1019),
        dvifExhausted(1020),
        certificateUnsupported(1021),
        certificateEmptyParams(1022),
        waitOnSwConfigHostFailed(1023),
        slowDrainRecoveryFailure(1024),
        unclaimedDevice(1025),
        sharedComponentsOobInventoryFailed(1026),
        sharedComponentsOobInventoryPeerFailed(1027),
        pciSwitchImageUpdateFailed(1028),
        chassisPeerAdapterRebootFailed(1029),
        persistentMemoryDimmFwUpdateFailed(1030),
        waitForBorderConfigCompletionLocalFailed(1031),
        waitForBorderConfigCompletionPeerFailed(1032),
        softShutdownFailed(1033),
        executepmactionFailed(1034),
        waitForAckFailed(1035),
        persistentMemoryDetection(1037),
        equipmentConfigNotMatching(1038),
        equipmentNamespaceNotMatching(1039),
        equipmentConfigError(1040),
        conditionCausePersistentMemoryDetection(1041),
        executevdactionFailed(1042),
        equippedUnsupported(1043),
        unsecureAdaptor(1044),
        unsecuredFpga(1045),
        activateRemoteFailed(1046),
        pollActivateFailed(1047),
        spdmFault(1048),
        kmipDelCertFailed(1049),
        fabricPortCountExceed(1050),
        exceedsMaxvalue(1051),
        equipmentPeerDimmDisabled(1052),
        equipmentDimmDisabled(1053),
        uplinkPortTypeMisconfigured(1054),
        equipmentSelftestfailed(1055),
        uplinkPortChannelMisconfigured(1056),
        fruComponentInventoryFailed(1057),
        updateFruComponentsFailed(1058),
        waitForUpdateFruComponentsFailed(1059),
        waitForBiosPostCompletionFailed(1060),
        updateNwSbAdaptorFwFailed(1061),
        waitForNwSbAdaptorFwUpdateFailed(1062),
        activateNwSbAdaptorFwFailed(1063),
        waitForNwSbAdaptorFwActivateFailed(1064),
        verifyKeyFailed(1065),
        disabledOrUnclaimedDevice(1066),
        pcieUnstableLink(1067),
        asicFatalError(1068),
        fcpuError(1069),
        unicastMacThresholdLimit(1070),
        passwordEncryptionKeyNotSet(1071),
        pcieNodeGpuMissing(1072),
        configGatewayFailed(1073),
        pcieNodeDiscoverFailed(1074),
        hybridDriveSlotConfigFailed(1075),
        updateFruComponentsAfterPoweredOnFailed(1076),
        waitForUpdateFruComponentsAfterPoweredOnFailed(1077),
        powerOffForSbAdaptorActivationFailed(1078),
        nvmevdconfigFailed(1079),
        storageComponentsFailed(1080),
        waitForStorageComponentFailed(1081),
        networkAdapterFailed(1082),
        waitForNetworkAdapterFailed(1083),
        hostComponentsFailed(1084),
        waitForHostComponentsFailed(1085),
        boardComponentsFailed(1086),
        waitForBoardComponentsFailed(1087),
        pcieNodePresent(1088),
        pcieNodeAbsent(1089),
        staticMacLimitReached(1090),
        riser1Absentcpu1Present(1091),
        riserMismatch(1092),
        riser2Presentcpu2Absent(1093),
        pcieLinkConfigIssue(1094),
        powerFault(1095),
        riser1PowerFault(1096),
        riser2PowerFault(1097),
        unsupportedpcieNodePresent(1098),
        unknownpcieNodePresent(1099),
        unsupportedpcieCardPresentOnRiser1(1100),
        unsupportedpcieCardPresentOnRiser2(1101),
        unknownpcieCardPresentOnRiser1(1102),
        unknownpcieCardPresentOnRiser2(1103),
        pcieNodePresentxfm1Absent(1104),
        retimerVersionMismatch(1105),
        pcienodeRemoved(1106),
        firmwareUpdateUnsupported(1107),
        macsecSessionStateChange(1108),
        macsecFallbackSession(1109),
        vicSudiValidationStateIsNotDetermined(1110),
        vicSudiHasBeenEvaluatedAndIsNotValid(1111),
        vicUbootStatusIsUnableToBeDetermined(1112),
        vicUbootIsRunningTheGoldenIeBackupImage(1113),
        vicApplicationStatusIsUnableToBeDetermined(1114),
        vicApplicationIsRunningAlternateImage(1115),
        vicApplicationIsRunningDiagnosticImage(1116),
        vicRunningApplicationImageIsNotReleaseKeySigned(1117),
        vicFpgaHas50OrLessUpgradesRemaining(1118),
        cosMisConfigured(1119),
        unsupportedController(1120),
        unsupportedDisk(1121),
        updateMacsecFailed(1122),
        updatesviFailed(1123),
        powerOnForStorageInitFailed(1124),
        waitForStorageInitFailed(1125),
        configStorageRemoteSecurityFailed(1126),
        fetchBiosHealthReportFailed(1127),
        configureLocalFailed(1128),
        deleteAfterConfigLocalFailed(1129),
        configurePeerFailed(1130),
        deleteAfterConfigPeerFailed(1131),
        waitForUpdateEncryptionFsmFailed(1132),
        syncPowerStateForStorageInitFailed(1133),
        powerOnPreConfigForStorageInitFailed(1134),
        checkPowerAvailabilityForStorageInitFailed(1135),
        powerDeployWaitForStorageInitFailed(1136),
        lowMemory(1137),
        vicFpgaHasNoFpgaUpgradesRemaining(1138),
        snmpTrapConfigError(1139),
        weakPasswordHashAlgorithm(1140),
        loginProfileDisabled(1141),
        unsupportedDrive(1142),
        expiredCaCertificate(1143),
        unsupportedSourceIntfVlanSharing(1144),
        speedReduced(16385),
        updateAttrFailed(16387),
        persistFailed(16388),
        coreFileGenerated(16389),
        providerLostConnectivity(16391),
        controllerLostConnectivity(16392),
        serviceRegistryVersionMismatch(16394),
        providerVersionMismatch(16395),
        controllerVersionMismatch(16396),
        clientVersionMismatch(16397),
        svcRegModification(16398),
        providerCreation(16399),
        providerModification(16400),
        controllerCreation(16401),
        controllerModification(16402),
        clientCreation(16403),
        clientDeletion(16404),
        clientModification(16405),
        quiesceMgmtControllerFailed(16406),
        quiesceResMgrFailed(16407),
        quiesceOpsMgrFailed(16408),
        quiescePolicyMgrFailed(16409),
        quiesceidmgrFailed(16410),
        quiesceStatsMgrFailed(16411),
        duplicatedDefined(16413),
        makeCfgDirsFailed(16414),
        moveCfgDirsToTmpLocationFailed(16415),
        moveCfgDirsFromTmpLocationFailed(16416),
        internalAddFailed(16417),
        peerAddFailed(16418),
        internalDeleteFailed(16419),
        peerDeleteFailed(16420),
        dmeDataExportFailed(16421),
        downloadFailed(16422),
        dmeImportFailed(16423),
        importFromXmlFailed(16424),
        downloadError(16425),
        failSyncToUcsm(16429),
        unassociatedVlan(16430),
        resolveStaticIdentifiersFailed(16431),
        applyThrottleFailed(16432),
        consumerVxanDeploymentFailed(16436),
        waitForConsumerReceivingVxanFailed(16437),
        ungroupedDomain(16438),
        authenticateFailed(16440),
        invalidConfig(16441),
        dbConnectReadWriteError(16443),
        remoteOperationFail(16444),
        deleteIdConsumerMapFailed(16445),
        processIdConsumerMapFailed(16446),
        reportIdDomainMapFailed(16447),
        getUsageTimeout(16450),
        getUsageFailed(16451),
        getDependencyTimeout(16452),
        getDependencyFailed(16453),
        importTimeout(16454),
        importFailed(16455),
        setRealmFailed(16456),
        setCertConfLocalFailed(16457),
        applyRenameFailed(16458),
        notFound(16459),
        configPeerFailed(16460),
        sendChangeFailed(16461),
        stateDisableFailed(16462),
        stateEnableFailed(16463),
        globalArrayStorageArrayNotOpted(16464),
        domainGroupMissing(16465),
        missingArrayAutoConfigRef(16466),
        storageBladeNotInDiscoveryMode(16467),
        missingArrayAutoConfigPolicy(16468),
        missingQualifier(16469),
        matchingQualifierError(16470),
        storageBladeAlreadyInUse(16471),
        throttleWaitFailed(16474),
        evaluateServerAssignFailed(16476),
        replaceIdAcquirerFailed(16478),
        vxanRangeCheckToUcsmFailed(16479),
        ucsmCheckVxanDeploymentToUcsmFailed(16480),
        enableSmartCallhomeFailed(16481),
        disableSmartCallhomeFailed(16482),
        sendInventoryFailed(16483),
        cleanUpFailed(16487),
        notInCompliance(16491),
        executeTestCliFailed(16492),
        retryReportFailed(16493),
        enableSmartLicenseFailed(16494),
        disableSmartLicenseFailed(16495),
        registerDeviceFailed(16496),
        retryRegisterDeviceFailed(16497),
        unregisterDeviceFailed(16498),
        retryUnregisterDeviceFailed(16499),
        roleConfigFailed(16502),
        pushVxanFailed(16503),
        vxanConfigFailed(16504),
        refreshStateFailed(16505),
        changeFailed(16507),
        registrationFailed(16513),
        pushSharedSecretFailed(16514),
        checkStatusFailed(16515),
        unRegistrationFailed(16516),
        validateFailed(16519),
        fetchDomainDataFailed(16520),
        evaluateFailed(16521),
        createPoliciesFailed(16522),
        createOrgFailed(16523),
        updateDomainMosFailed(16524),
        createVlanOrgPermissionFailed(16525),
        creategspFailed(16526),
        resolveGlobalPoolDnFailed(16527),
        addIdToGlobalPoolFailed(16528),
        assignIdsFailed(16529),
        unassignIdsFailed(16530),
        fetchVnetDependenciesFailed(16531),
        globalizeFailed(16532),
        waitGlobalizeFailed(16533),
        runPolicyResolveFailed(16534),
        waitForRunPolicyResolvedFailed(16535),
        triggerOperationFailed(16536),
        collectIdContextsFailed(16537),
        validateNetworkDesignFailed(16538),
        pushPoliciesFailed(16539),
        resolveDomainGroupPoliciesFailed(16540),
        waitForDomainGroupPoliciesFailed(16541),
        resolveOutbandPoolFailed(16542),
        waitForPoliciesFailed(16544),
        validationFailed(16545),
        consumerVsanDeploymentFailed(16546),
        waitForRecvVsanFailed(16547),
        ucsPolicyConfigFailed(16551),
        createUpdatePolicyScopeFailed(16552),
        reapplygspFailed(16553),
        any(-1)
    }

CucsConditionCode ::= TEXTUAL-CONVENTION
    STATUS        current
    DESCRIPTION
        ""
    SYNTAX        INTEGER
    {
        generic(0),
        f0156(156),
        f0157(157),
        f0169(169),
        f0170(170),
        f0174(174),
        f0175(175),
        f0176(176),
        f0177(177),
        f0178(178),
        f0179(179),
        f0180(180),
        f0181(181),
        f0182(182),
        f0183(183),
        f0184(184),
        f0185(185),
        f0186(186),
        f0187(187),
        f0188(188),
        f0189(189),
        f0190(190),
        f0191(191),
        f0200(200),
        f0203(203),
        f0206(206),
        f0207(207),
        f0209(209),
        f0276(276),
        f0277(277),
        f0278(278),
        f0279(279),
        f0282(282),
        f0283(283),
        f0291(291),
        f0293(293),
        f0294(294),
        f0304(304),
        f0305(305),
        f0306(306),
        f0310(310),
        f0311(311),
        f0312(312),
        f0313(313),
        f0314(314),
        f0315(315),
        f0317(317),
        f0318(318),
        f0319(319),
        f0320(320),
        f0321(321),
        f0322(322),
        f0324(324),
        f0326(326),
        f0327(327),
        f0329(329),
        f0330(330),
        f0331(331),
        f0332(332),
        f0334(334),
        f0337(337),
        f0367(367),
        f0368(368),
        f0369(369),
        f0371(371),
        f0373(373),
        f0374(374),
        f0376(376),
        f0377(377),
        f0378(378),
        f0379(379),
        f0380(380),
        f0381(381),
        f0382(382),
        f0383(383),
        f0384(384),
        f0385(385),
        f0387(387),
        f0389(389),
        f0391(391),
        f0392(392),
        f0393(393),
        f0394(394),
        f0395(395),
        f0396(396),
        f0397(397),
        f0398(398),
        f0399(399),
        f0400(400),
        f0401(401),
        f0402(402),
        f0403(403),
        f0404(404),
        f0405(405),
        f0406(406),
        f0407(407),
        f0408(408),
        f0409(409),
        f0410(410),
        f0411(411),
        f0424(424),
        f0425(425),
        f0428(428),
        f0429(429),
        f0430(430),
        f0434(434),
        f0435(435),
        f0436(436),
        f0440(440),
        f0451(451),
        f0452(452),
        f0453(453),
        f0454(454),
        f0455(455),
        f0456(456),
        f0458(458),
        f0459(459),
        f0460(460),
        f0461(461),
        f0462(462),
        f0463(463),
        f0464(464),
        f0465(465),
        f0466(466),
        f0470(470),
        f0471(471),
        f0476(476),
        f0478(478),
        f0479(479),
        f0480(480),
        f0481(481),
        f0484(484),
        f0502(502),
        f0517(517),
        f0528(528),
        f0531(531),
        f0532(532),
        f0533(533),
        f0535(535),
        f0536(536),
        f0537(537),
        f0538(538),
        f0539(539),
        f0540(540),
        f0543(543),
        f0549(549),
        f0620(620),
        f0621(621),
        f0622(622),
        f0625(625),
        f0626(626),
        f0635(635),
        f0637(637),
        f0640(640),
        f0642(642),
        f0643(643),
        f0670(670),
        f0671(671),
        f0672(672),
        f0673(673),
        f0674(674),
        f0675(675),
        f0676(676),
        f0677(677),
        f0678(678),
        f0688(688),
        f0689(689),
        f0702(702),
        f0703(703),
        f0708(708),
        f0713(713),
        f0717(717),
        f0727(727),
        f0728(728),
        f0729(729),
        f0730(730),
        f0731(731),
        f0733(733),
        f0734(734),
        f0735(735),
        f0736(736),
        f0740(740),
        f0741(741),
        f0742(742),
        f0743(743),
        f0744(744),
        f0747(747),
        f0757(757),
        f0764(764),
        f0765(765),
        f0766(766),
        f0772(772),
        f0775(775),
        f0776(776),
        f0777(777),
        f0778(778),
        f0791(791),
        f0792(792),
        f0793(793),
        f0794(794),
        f0795(795),
        f0796(796),
        f0797(797),
        f0798(798),
        f0801(801),
        f0807(807),
        f0821(821),
        f0826(826),
        f0829(829),
        f0831(831),
        f0832(832),
        f0833(833),
        f0834(834),
        f0835(835),
        f0836(836),
        f0837(837),
        f0838(838),
        f0840(840),
        f0841(841),
        f0842(842),
        f0843(843),
        f0844(844),
        f0846(846),
        f0855(855),
        f0856(856),
        f0857(857),
        f0858(858),
        f0859(859),
        f0861(861),
        f0862(862),
        f0863(863),
        f0864(864),
        f0865(865),
        f0866(866),
        f0867(867),
        f0868(868),
        f0869(869),
        f0872(872),
        f0874(874),
        f0875(875),
        f0876(876),
        f0877(877),
        f0878(878),
        f0879(879),
        f0880(880),
        f0881(881),
        f0882(882),
        f0883(883),
        f0884(884),
        f0885(885),
        f0887(887),
        f0890(890),
        f0900(900),
        f0901(901),
        f0902(902),
        f0903(903),
        f0909(909),
        f0910(910),
        f0915(915),
        f0916(916),
        f0917(917),
        f0918(918),
        f0919(919),
        f0920(920),
        f0921(921),
        f0928(928),
        f0932(932),
        f0933(933),
        f0934(934),
        f0935(935),
        f0936(936),
        f0937(937),
        f0943(943),
        f0944(944),
        f0945(945),
        f0946(946),
        f0947(947),
        f0948(948),
        f0949(949),
        f0950(950),
        f0951(951),
        f0952(952),
        f0953(953),
        f0954(954),
        f0957(957),
        f0958(958),
        f0959(959),
        f0967(967),
        f0968(968),
        f0969(969),
        f0970(970),
        f0971(971),
        f0972(972),
        f0973(973),
        f0974(974),
        f0975(975),
        f0976(976),
        f0977(977),
        f0978(978),
        f0979(979),
        f0980(980),
        f0981(981),
        f0982(982),
        f0988(988),
        f0996(996),
        f0997(997),
        f0998(998),
        f0999(999),
        f1000(1000),
        f1001(1001),
        f1002(1002),
        f1003(1003),
        f1004(1004),
        f1005(1005),
        f1006(1006),
        f1007(1007),
        f1008(1008),
        f1009(1009),
        f1010(1010),
        f1017(1017),
        f1026(1026),
        f1027(1027),
        f1028(1028),
        f1029(1029),
        f1030(1030),
        f1031(1031),
        f1032(1032),
        f1033(1033),
        f1034(1034),
        f1035(1035),
        f1036(1036),
        f1037(1037),
        f1040(1040),
        f1046(1046),
        f1047(1047),
        f1048(1048),
        f1049(1049),
        f1050(1050),
        f1051(1051),
        f1052(1052),
        f1053(1053),
        f1054(1054),
        f1055(1055),
        f1056(1056),
        f1057(1057),
        f1058(1058),
        f1080(1080),
        f1081(1081),
        f1082(1082),
        f1083(1083),
        f1084(1084),
        f1085(1085),
        f1086(1086),
        f1087(1087),
        f1088(1088),
        f1089(1089),
        f1090(1090),
        f1091(1091),
        f1092(1092),
        f1093(1093),
        f1094(1094),
        f1095(1095),
        f1097(1097),
        f1098(1098),
        f1099(1099),
        f1101(1101),
        f1102(1102),
        f1103(1103),
        f1104(1104),
        f1105(1105),
        f1106(1106),
        f1114(1114),
        f1202(1202),
        f1204(1204),
        f1205(1205),
        f1206(1206),
        f1207(1207),
        f1208(1208),
        f1209(1209),
        f1211(1211),
        f1212(1212),
        f1213(1213),
        f1214(1214),
        f1215(1215),
        f1216(1216),
        f1217(1217),
        f1218(1218),
        f1219(1219),
        f1220(1220),
        f1221(1221),
        f1222(1222),
        f1223(1223),
        f1224(1224),
        f1225(1225),
        f1226(1226),
        f1227(1227),
        f1228(1228),
        f1229(1229),
        f1232(1232),
        f1233(1233),
        f1236(1236),
        f1237(1237),
        f1249(1249),
        f1250(1250),
        f1251(1251),
        f1252(1252),
        f1256(1256),
        f1257(1257),
        f1258(1258),
        f1259(1259),
        f1260(1260),
        f1261(1261),
        f1262(1262),
        f1279(1279),
        f1284(1284),
        f1285(1285),
        f1304(1304),
        f1305(1305),
        f1306(1306),
        f1320(1320),
        f1321(1321),
        f1325(1325),
        f1328(1328),
        f1329(1329),
        f1358(1358),
        f1359(1359),
        f1360(1360),
        f1361(1361),
        f1362(1362),
        f1363(1363),
        f1365(1365),
        f1366(1366),
        f1367(1367),
        f1368(1368),
        f1369(1369),
        f1380(1380),
        f1382(1382),
        f1383(1383),
        f1384(1384),
        f1385(1385),
        f1386(1386),
        f1388(1388),
        f1389(1389),
        f1390(1390),
        f1391(1391),
        f1392(1392),
        f1396(1396),
        f1397(1397),
        f1398(1398),
        f1399(1399),
        f1400(1400),
        f1402(1402),
        f1404(1404),
        f1419(1419),
        f1420(1420),
        f1421(1421),
        f1428(1428),
        f1429(1429),
        f1430(1430),
        f1431(1431),
        f1432(1432),
        f1433(1433),
        f1434(1434),
        f1437(1437),
        f1438(1438),
        f1439(1439),
        f1448(1448),
        f1449(1449),
        f1450(1450),
        f1451(1451),
        f1452(1452),
        f1453(1453),
        f1454(1454),
        f1455(1455),
        f1456(1456),
        f1464(1464),
        f1465(1465),
        f1467(1467),
        f1472(1472),
        f1473(1473),
        f1474(1474),
        f1475(1475),
        f1476(1476),
        f1477(1477),
        f1478(1478),
        f1480(1480),
        f1481(1481),
        f1482(1482),
        f1483(1483),
        f1493(1493),
        f1498(1498),
        f1499(1499),
        f1501(1501),
        f1502(1502),
        f1503(1503),
        f1504(1504),
        f1505(1505),
        f1506(1506),
        f1507(1507),
        f1508(1508),
        f1509(1509),
        f1510(1510),
        f1511(1511),
        f1512(1512),
        f1513(1513),
        f1514(1514),
        f1515(1515),
        f1516(1516),
        f1517(1517),
        f1518(1518),
        f1519(1519),
        f1520(1520),
        f1521(1521),
        f1522(1522),
        f1523(1523),
        f1558(1558),
        f1559(1559),
        f1560(1560),
        f1561(1561),
        f1562(1562),
        f1563(1563),
        f1564(1564),
        f1565(1565),
        f1566(1566),
        f1604(1604),
        f1605(1605),
        f1606(1606),
        f1616(1616),
        f1617(1617),
        f1618(1618),
        f1620(1620),
        f1621(1621),
        f1622(1622),
        f1623(1623),
        f1624(1624),
        f1627(1627),
        f1634(1634),
        f1635(1635),
        f1654(1654),
        f1668(1668),
        f1669(1669),
        f1671(1671),
        f1672(1672),
        f1675(1675),
        f1676(1676),
        f1680(1680),
        f1681(1681),
        f1685(1685),
        f1686(1686),
        f1687(1687),
        f1688(1688),
        f1694(1694),
        f1700(1700),
        f1701(1701),
        f1702(1702),
        f1703(1703),
        f1704(1704),
        f1705(1705),
        f1706(1706),
        f1707(1707),
        f1708(1708),
        f1709(1709),
        f1710(1710),
        f1713(1713),
        f1719(1719),
        f1720(1720),
        f1721(1721),
        f1731(1731),
        f1732(1732),
        f1744(1744),
        f1745(1745),
        f1748(1748),
        f1749(1749),
        f1753(1753),
        f1754(1754),
        f1755(1755),
        f1756(1756),
        f1757(1757),
        f1758(1758),
        f1761(1761),
        f1764(1764),
        f1766(1766),
        f1767(1767),
        f1768(1768),
        f1769(1769),
        f1778(1778),
        f1781(1781),
        f1784(1784),
        f1792(1792),
        f1793(1793),
        f1794(1794),
        f1795(1795),
        f1796(1796),
        f1797(1797),
        f1798(1798),
        f1799(1799),
        f1825(1825),
        f1826(1826),
        f1831(1831),
        f1832(1832),
        f1833(1833),
        f1834(1834),
        f1835(1835),
        f1836(1836),
        f1837(1837),
        f1838(1838),
        f1839(1839),
        f1840(1840),
        f1841(1841),
        f1842(1842),
        f1843(1843),
        f1844(1844),
        f1845(1845),
        f1846(1846),
        f1847(1847),
        f1848(1848),
        f1849(1849),
        f1850(1850),
        f1851(1851),
        f1852(1852),
        f1864(1864),
        f1873(1873),
        f1889(1889),
        f1890(1890),
        f1891(1891),
        f1892(1892),
        f1893(1893),
        f1894(1894),
        f1895(1895),
        f1896(1896),
        f1897(1897),
        f1898(1898),
        f1899(1899),
        f1900(1900),
        f1901(1901),
        f1902(1902),
        f1903(1903),
        f1907(1907),
        f1908(1908),
        f1912(1912),
        f1913(1913),
        f1914(1914),
        f1915(1915),
        f1916(1916),
        f1917(1917),
        f1926(1926),
        f1927(1927),
        f1932(1932),
        f1933(1933),
        f1934(1934),
        f1945(1945),
        f1946(1946),
        f1947(1947),
        f1948(1948),
        f1949(1949),
        f1950(1950),
        f1951(1951),
        f1953(1953),
        f1954(1954),
        f1955(1955),
        f1956(1956),
        f1959(1959),
        f1960(1960),
        f1961(1961),
        f1962(1962),
        f1964(1964),
        f1965(1965),
        f1966(1966),
        f1967(1967),
        f1968(1968),
        f1969(1969),
        f1970(1970),
        f1974(1974),
        f1975(1975),
        f1979(1979),
        f1980(1980),
        f1981(1981),
        f1994(1994),
        f1998(1998),
        f1999(1999),
        f2000(2000),
        f2001(2001),
        f2002(2002),
        f2003(2003),
        f2004(2004),
        f2005(2005),
        f2006(2006),
        f2007(2007),
        f2008(2008),
        f2009(2009),
        f2010(2010),
        f2013(2013),
        f2014(2014),
        f2015(2015),
        f2016(2016),
        f2023(2023),
        f2042(2042),
        f2045(2045),
        f2046(2046),
        f2056(2056),
        f2057(2057),
        f2058(2058),
        f2059(2059),
        f2060(2060),
        f2061(2061),
        f2062(2062),
        f2063(2063),
        f2064(2064),
        f2065(2065),
        f2066(2066),
        f2067(2067),
        f2068(2068),
        f2069(2069),
        f2079(2079),
        f2080(2080),
        f2081(2081),
        f2082(2082),
        f2083(2083),
        f2084(2084),
        f2085(2085),
        f2086(2086),
        f2087(2087),
        f2091(2091),
        f2096(2096),
        f2097(2097),
        f2098(2098),
        f2099(2099),
        f2100(2100),
        f2101(2101),
        f2102(2102),
        f2103(2103),
        f2104(2104),
        f2105(2105),
        f2106(2106),
        f2107(2107),
        f2108(2108),
        f2109(2109),
        f2110(2110),
        f2111(2111),
        f2112(2112),
        f2113(2113),
        f2114(2114),
        f2115(2115),
        f2116(2116),
        f2117(2117),
        f2118(2118),
        f2127(2127),
        f2128(2128),
        f2130(2130),
        f2131(2131),
        f2132(2132),
        f2133(2133),
        f2134(2134),
        f2135(2135),
        f2136(2136),
        f2137(2137),
        f2138(2138),
        f2139(2139),
        f2140(2140),
        f2141(2141),
        f2142(2142),
        f2143(2143),
        f2153(2153),
        f2154(2154),
        f2155(2155),
        f2156(2156),
        f2163(2163),
        f2164(2164),
        f2165(2165),
        f2166(2166),
        f2167(2167),
        f16405(16405),
        f16406(16406),
        f16407(16407),
        f16408(16408),
        f16518(16518),
        f16519(16519),
        f16520(16520),
        f16533(16533),
        f16534(16534),
        f16535(16535),
        f16539(16539),
        f16550(16550),
        f16576(16576),
        f16577(16577),
        f16579(16579),
        f16580(16580),
        f16581(16581),
        f16582(16582),
        f16600(16600),
        f16601(16601),
        f16604(16604),
        f16605(16605),
        f16606(16606),
        f16634(16634),
        f16635(16635),
        f16636(16636),
        f16637(16637),
        f16641(16641),
        f16650(16650),
        f16651(16651),
        f16653(16653),
        f16654(16654),
        f16655(16655),
        f16656(16656),
        f16657(16657),
        f16670(16670),
        f16673(16673),
        f16674(16674),
        f16679(16679),
        f16680(16680),
        f16681(16681),
        f16682(16682),
        f16683(16683),
        f16684(16684),
        f16742(16742),
        f16745(16745),
        f16749(16749),
        f16750(16750),
        f16803(16803),
        f16815(16815),
        f16823(16823),
        f16852(16852),
        f16857(16857),
        f16858(16858),
        f16879(16879),
        f16880(16880),
        f16881(16881),
        f16898(16898),
        f16904(16904),
        f16906(16906),
        f16930(16930),
        f16931(16931),
        f16942(16942),
        f16943(16943),
        f16944(16944),
        f16945(16945),
        f16973(16973),
        f16974(16974),
        f16975(16975),
        f16976(16976),
        f16977(16977),
        f16978(16978),
        f16979(16979),
        f16980(16980),
        f16981(16981),
        f16982(16982),
        f16983(16983),
        f16984(16984),
        f16986(16986),
        f16987(16987),
        f16988(16988),
        f16994(16994),
        f16995(16995),
        f17000(17000),
        f17001(17001),
        f17002(17002),
        f17008(17008),
        f17012(17012),
        f17013(17013),
        f17014(17014),
        f17043(17043),
        f17044(17044),
        f17045(17045),
        f17046(17046),
        f17050(17050),
        f17051(17051),
        f17052(17052),
        f17053(17053),
        f17083(17083),
        f17084(17084),
        f17089(17089),
        f17116(17116),
        f17133(17133),
        f17134(17134),
        f17163(17163),
        f17169(17169),
        f17170(17170),
        f17187(17187),
        f17188(17188),
        f17190(17190),
        f17192(17192),
        f17195(17195),
        f17196(17196),
        f17207(17207),
        f17214(17214),
        f17223(17223),
        f17232(17232),
        f17239(17239),
        f17254(17254),
        f17259(17259),
        f17262(17262),
        f17271(17271),
        f17281(17281),
        f17282(17282),
        f17312(17312),
        f17313(17313),
        f17325(17325),
        f17326(17326),
        f17327(17327),
        f17328(17328),
        f17339(17339),
        f17340(17340),
        f17348(17348),
        f17349(17349),
        f17350(17350),
        f17358(17358),
        f17359(17359),
        f17360(17360),
        f17361(17361),
        f17367(17367),
        f17377(17377),
        f17378(17378),
        f17379(17379),
        f17381(17381),
        f17382(17382),
        f17383(17383),
        f17384(17384),
        f17395(17395),
        f17399(17399),
        f17400(17400),
        f17402(17402),
        f17403(17403),
        f17404(17404),
        f17405(17405),
        f17406(17406),
        f17407(17407),
        f17408(17408),
        f17409(17409),
        f17410(17410),
        f17411(17411),
        f17412(17412),
        f17413(17413),
        f17414(17414),
        f17415(17415),
        f17416(17416),
        f17418(17418),
        f17419(17419),
        f17420(17420),
        f17425(17425),
        f17426(17426),
        f17427(17427),
        f17428(17428),
        f17439(17439),
        f17445(17445),
        f17446(17446),
        f17447(17447),
        f17448(17448),
        f17449(17449),
        f17450(17450),
        f17451(17451),
        f17452(17452),
        f17453(17453),
        f17454(17454),
        f17455(17455),
        f17456(17456),
        f17457(17457),
        f17458(17458),
        f17459(17459),
        f17460(17460),
        f17461(17461),
        f17462(17462),
        f17476(17476),
        f17477(17477),
        f17478(17478),
        f17483(17483),
        f17484(17484),
        f17485(17485),
        f17491(17491),
        f17492(17492),
        f17493(17493),
        f17494(17494),
        f17499(17499),
        f17599(17599),
        f17601(17601),
        f17602(17602),
        f17608(17608),
        f17609(17609),
        f17612(17612),
        f17619(17619),
        f17639(17639),
        f17665(17665),
        f17667(17667),
        f17703(17703),
        f17707(17707),
        f17708(17708),
        f17714(17714),
        f17715(17715),
        f17716(17716),
        f17717(17717),
        f17755(17755),
        f17757(17757),
        f17762(17762),
        f17788(17788),
        f17791(17791),
        f17792(17792),
        f17793(17793),
        f17806(17806),
        f17818(17818),
        f17819(17819),
        f17820(17820),
        f17824(17824),
        f17826(17826),
        f17850(17850),
        f17921(17921),
        f17922(17922),
        f17923(17923),
        f17924(17924),
        f17925(17925),
        f17926(17926),
        f17927(17927),
        f17928(17928),
        f17933(17933),
        f17934(17934),
        f17935(17935),
        f17940(17940),
        f17941(17941),
        f17954(17954),
        f17978(17978),
        f17984(17984),
        f17987(17987),
        f18012(18012),
        f18013(18013),
        f18014(18014),
        f18015(18015),
        f18016(18016),
        f18017(18017),
        f18024(18024),
        f18025(18025),
        f18026(18026),
        f18032(18032),
        f18033(18033),
        f18034(18034),
        f18045(18045),
        f18046(18046),
        f18051(18051),
        f18102(18102),
        f18124(18124),
        f18146(18146),
        f18147(18147),
        f18161(18161),
        f18169(18169),
        f18184(18184),
        f18185(18185),
        f18186(18186),
        f18206(18206),
        f18207(18207),
        f18208(18208),
        f18237(18237),
        f18239(18239),
        f18240(18240),
        f18241(18241),
        f18242(18242),
        f18243(18243),
        f18244(18244),
        f18245(18245),
        f18246(18246),
        f18247(18247),
        f18259(18259),
        f18260(18260),
        f18261(18261),
        f18290(18290),
        f18293(18293),
        f18294(18294),
        f18336(18336),
        f18339(18339),
        f18342(18342),
        f18345(18345),
        f18346(18346),
        f18353(18353),
        f18361(18361),
        f18362(18362),
        f18375(18375),
        f18376(18376),
        f18377(18377),
        f18379(18379),
        f18380(18380),
        f18381(18381),
        f18395(18395),
        f18404(18404),
        f18406(18406),
        f18410(18410),
        f18411(18411),
        f18427(18427),
        f18428(18428),
        f18431(18431),
        f18432(18432),
        f18456(18456),
        f18478(18478),
        f18530(18530),
        f18533(18533),
        f33142(33142),
        f33144(33144),
        f33145(33145),
        f33146(33146),
        f33167(33167),
        f33168(33168),
        f33169(33169),
        f33170(33170),
        f33177(33177),
        f33178(33178),
        f33179(33179),
        f33180(33180),
        f33187(33187),
        f33188(33188),
        f33189(33189),
        f33190(33190),
        f33197(33197),
        f33198(33198),
        f33199(33199),
        f33200(33200),
        f33211(33211),
        f33212(33212),
        f33213(33213),
        f33214(33214),
        f33221(33221),
        f33222(33222),
        f33223(33223),
        f33224(33224),
        f33231(33231),
        f33232(33232),
        f33233(33233),
        f33234(33234),
        f33241(33241),
        f33242(33242),
        f33243(33243),
        f33244(33244),
        f33251(33251),
        f33252(33252),
        f33253(33253),
        f33254(33254),
        f33261(33261),
        f33262(33262),
        f33263(33263),
        f33264(33264),
        f33271(33271),
        f33272(33272),
        f33273(33273),
        f33274(33274),
        f33281(33281),
        f33282(33282),
        f33283(33283),
        f33284(33284),
        f33291(33291),
        f33292(33292),
        f33293(33293),
        f33294(33294),
        f33301(33301),
        f33302(33302),
        f33303(33303),
        f33304(33304),
        f33483(33483),
        f33485(33485),
        f33486(33486),
        f33487(33487),
        f33491(33491),
        f33493(33493),
        f33494(33494),
        f33495(33495),
        f33499(33499),
        f33501(33501),
        f33502(33502),
        f33503(33503),
        f33720(33720),
        f33721(33721),
        f33722(33722),
        f33723(33723),
        f33730(33730),
        f33731(33731),
        f33732(33732),
        f33733(33733),
        f33740(33740),
        f33741(33741),
        f33742(33742),
        f33743(33743),
        f33750(33750),
        f33751(33751),
        f33752(33752),
        f33753(33753),
        f33760(33760),
        f33761(33761),
        f33762(33762),
        f33763(33763),
        f33770(33770),
        f33771(33771),
        f33772(33772),
        f33773(33773),
        f33810(33810),
        f33811(33811),
        f33812(33812),
        f33813(33813),
        f33820(33820),
        f33821(33821),
        f33822(33822),
        f33823(33823),
        f33830(33830),
        f33831(33831),
        f33832(33832),
        f33833(33833),
        f33840(33840),
        f33841(33841),
        f33842(33842),
        f33843(33843),
        f33850(33850),
        f33851(33851),
        f33852(33852),
        f33853(33853),
        f33860(33860),
        f33861(33861),
        f33862(33862),
        f33863(33863),
        f33875(33875),
        f33876(33876),
        f33877(33877),
        f33878(33878),
        f33885(33885),
        f33886(33886),
        f33887(33887),
        f33888(33888),
        f33895(33895),
        f33896(33896),
        f33897(33897),
        f33898(33898),
        f33905(33905),
        f33906(33906),
        f33907(33907),
        f33908(33908),
        f33915(33915),
        f33916(33916),
        f33917(33917),
        f33918(33918),
        f33925(33925),
        f33926(33926),
        f33927(33927),
        f33928(33928),
        f33940(33940),
        f33941(33941),
        f33942(33942),
        f33943(33943),
        f33950(33950),
        f33951(33951),
        f33952(33952),
        f33953(33953),
        f33960(33960),
        f33961(33961),
        f33962(33962),
        f33963(33963),
        f33970(33970),
        f33971(33971),
        f33972(33972),
        f33973(33973),
        f33980(33980),
        f33981(33981),
        f33982(33982),
        f33983(33983),
        f33995(33995),
        f33996(33996),
        f33997(33997),
        f33998(33998),
        f34005(34005),
        f34006(34006),
        f34007(34007),
        f34008(34008),
        f34015(34015),
        f34016(34016),
        f34017(34017),
        f34018(34018),
        f34030(34030),
        f34031(34031),
        f34032(34032),
        f34033(34033),
        f34040(34040),
        f34041(34041),
        f34042(34042),
        f34043(34043),
        f34050(34050),
        f34051(34051),
        f34052(34052),
        f34053(34053),
        f34064(34064),
        f34065(34065),
        f34066(34066),
        f34067(34067),
        f34074(34074),
        f34075(34075),
        f34076(34076),
        f34077(34077),
        f34084(34084),
        f34085(34085),
        f34086(34086),
        f34087(34087),
        f34094(34094),
        f34095(34095),
        f34096(34096),
        f34097(34097),
        f34108(34108),
        f34109(34109),
        f34110(34110),
        f34111(34111),
        f34118(34118),
        f34119(34119),
        f34120(34120),
        f34121(34121),
        f34128(34128),
        f34129(34129),
        f34130(34130),
        f34131(34131),
        f34138(34138),
        f34139(34139),
        f34140(34140),
        f34141(34141),
        f34148(34148),
        f34149(34149),
        f34150(34150),
        f34151(34151),
        f34158(34158),
        f34159(34159),
        f34160(34160),
        f34161(34161),
        f34168(34168),
        f34169(34169),
        f34170(34170),
        f34171(34171),
        f34178(34178),
        f34179(34179),
        f34180(34180),
        f34181(34181),
        f34192(34192),
        f34193(34193),
        f34194(34194),
        f34195(34195),
        f34202(34202),
        f34203(34203),
        f34204(34204),
        f34205(34205),
        f34212(34212),
        f34213(34213),
        f34214(34214),
        f34215(34215),
        f34222(34222),
        f34223(34223),
        f34224(34224),
        f34225(34225),
        f34232(34232),
        f34233(34233),
        f34234(34234),
        f34235(34235),
        f34246(34246),
        f34247(34247),
        f34248(34248),
        f34249(34249),
        f34256(34256),
        f34257(34257),
        f34258(34258),
        f34259(34259),
        f34271(34271),
        f34272(34272),
        f34273(34273),
        f34274(34274),
        f34281(34281),
        f34282(34282),
        f34283(34283),
        f34284(34284),
        f34291(34291),
        f34292(34292),
        f34293(34293),
        f34294(34294),
        f34301(34301),
        f34302(34302),
        f34303(34303),
        f34304(34304),
        f34316(34316),
        f34317(34317),
        f34318(34318),
        f34319(34319),
        f34326(34326),
        f34327(34327),
        f34328(34328),
        f34329(34329),
        f34336(34336),
        f34337(34337),
        f34338(34338),
        f34339(34339),
        f34346(34346),
        f34347(34347),
        f34348(34348),
        f34349(34349),
        f34361(34361),
        f34362(34362),
        f34363(34363),
        f34364(34364),
        f34371(34371),
        f34372(34372),
        f34373(34373),
        f34374(34374),
        f34381(34381),
        f34382(34382),
        f34383(34383),
        f34384(34384),
        f34396(34396),
        f34397(34397),
        f34398(34398),
        f34399(34399),
        f34406(34406),
        f34407(34407),
        f34408(34408),
        f34409(34409),
        f34416(34416),
        f34417(34417),
        f34418(34418),
        f34419(34419),
        f34426(34426),
        f34427(34427),
        f34428(34428),
        f34429(34429),
        f34436(34436),
        f34437(34437),
        f34438(34438),
        f34439(34439),
        f34451(34451),
        f34452(34452),
        f34453(34453),
        f34454(34454),
        f34461(34461),
        f34462(34462),
        f34463(34463),
        f34464(34464),
        f34471(34471),
        f34472(34472),
        f34473(34473),
        f34474(34474),
        f34481(34481),
        f34482(34482),
        f34483(34483),
        f34484(34484),
        f34496(34496),
        f34497(34497),
        f34498(34498),
        f34499(34499),
        f34506(34506),
        f34507(34507),
        f34508(34508),
        f34509(34509),
        f34516(34516),
        f34517(34517),
        f34518(34518),
        f34519(34519),
        f34526(34526),
        f34527(34527),
        f34528(34528),
        f34529(34529),
        f34542(34542),
        f34543(34543),
        f34544(34544),
        f34545(34545),
        f34552(34552),
        f34553(34553),
        f34554(34554),
        f34555(34555),
        f34562(34562),
        f34563(34563),
        f34564(34564),
        f34565(34565),
        f34572(34572),
        f34573(34573),
        f34574(34574),
        f34575(34575),
        f34588(34588),
        f34589(34589),
        f34590(34590),
        f34591(34591),
        f34598(34598),
        f34599(34599),
        f34600(34600),
        f34601(34601),
        f34608(34608),
        f34609(34609),
        f34610(34610),
        f34611(34611),
        f34618(34618),
        f34619(34619),
        f34620(34620),
        f34621(34621),
        f34633(34633),
        f34634(34634),
        f34635(34635),
        f34636(34636),
        f34643(34643),
        f34644(34644),
        f34645(34645),
        f34646(34646),
        f34653(34653),
        f34654(34654),
        f34655(34655),
        f34656(34656),
        f34663(34663),
        f34664(34664),
        f34665(34665),
        f34666(34666),
        f34673(34673),
        f34674(34674),
        f34675(34675),
        f34676(34676),
        f34688(34688),
        f34689(34689),
        f34690(34690),
        f34691(34691),
        f34698(34698),
        f34699(34699),
        f34700(34700),
        f34701(34701),
        f34708(34708),
        f34709(34709),
        f34710(34710),
        f34711(34711),
        f34718(34718),
        f34719(34719),
        f34720(34720),
        f34721(34721),
        f34733(34733),
        f34734(34734),
        f34735(34735),
        f34736(34736),
        f34743(34743),
        f34744(34744),
        f34745(34745),
        f34746(34746),
        f34753(34753),
        f34754(34754),
        f34755(34755),
        f34756(34756),
        f34763(34763),
        f34764(34764),
        f34765(34765),
        f34766(34766),
        f34778(34778),
        f34779(34779),
        f34780(34780),
        f34781(34781),
        f34788(34788),
        f34789(34789),
        f34790(34790),
        f34791(34791),
        f34798(34798),
        f34799(34799),
        f34800(34800),
        f34801(34801),
        f34808(34808),
        f34809(34809),
        f34810(34810),
        f34811(34811),
        f34822(34822),
        f34823(34823),
        f34824(34824),
        f34825(34825),
        f34832(34832),
        f34833(34833),
        f34834(34834),
        f34835(34835),
        f34842(34842),
        f34843(34843),
        f34844(34844),
        f34845(34845),
        f34852(34852),
        f34853(34853),
        f34854(34854),
        f34855(34855),
        f34862(34862),
        f34863(34863),
        f34864(34864),
        f34865(34865),
        f34872(34872),
        f34873(34873),
        f34874(34874),
        f34875(34875),
        f34882(34882),
        f34883(34883),
        f34884(34884),
        f34885(34885),
        f34892(34892),
        f34893(34893),
        f34894(34894),
        f34895(34895),
        f34906(34906),
        f34907(34907),
        f34908(34908),
        f34909(34909),
        f34916(34916),
        f34917(34917),
        f34918(34918),
        f34919(34919),
        f34926(34926),
        f34927(34927),
        f34928(34928),
        f34929(34929),
        f34936(34936),
        f34937(34937),
        f34938(34938),
        f34939(34939),
        f34950(34950),
        f34951(34951),
        f34952(34952),
        f34953(34953),
        f34960(34960),
        f34961(34961),
        f34962(34962),
        f34963(34963),
        f34970(34970),
        f34971(34971),
        f34972(34972),
        f34973(34973),
        f34980(34980),
        f34981(34981),
        f34982(34982),
        f34983(34983),
        f34990(34990),
        f34991(34991),
        f34992(34992),
        f34993(34993),
        f35000(35000),
        f35001(35001),
        f35002(35002),
        f35003(35003),
        f35010(35010),
        f35011(35011),
        f35012(35012),
        f35013(35013),
        f35020(35020),
        f35021(35021),
        f35022(35022),
        f35023(35023),
        f35166(35166),
        f35168(35168),
        f35169(35169),
        f35170(35170),
        f35174(35174),
        f35176(35176),
        f35177(35177),
        f35178(35178),
        f35198(35198),
        f35200(35200),
        f35201(35201),
        f35202(35202),
        f35206(35206),
        f35208(35208),
        f35209(35209),
        f35210(35210),
        f35214(35214),
        f35216(35216),
        f35217(35217),
        f35218(35218),
        f35222(35222),
        f35224(35224),
        f35225(35225),
        f35226(35226),
        f35234(35234),
        f35236(35236),
        f35237(35237),
        f35238(35238),
        f35242(35242),
        f35244(35244),
        f35245(35245),
        f35246(35246),
        f35250(35250),
        f35252(35252),
        f35253(35253),
        f35254(35254),
        f35275(35275),
        f35276(35276),
        f35277(35277),
        f35278(35278),
        f35285(35285),
        f35286(35286),
        f35287(35287),
        f35288(35288),
        f35295(35295),
        f35296(35296),
        f35297(35297),
        f35298(35298),
        f35305(35305),
        f35306(35306),
        f35307(35307),
        f35308(35308),
        f35315(35315),
        f35316(35316),
        f35317(35317),
        f35318(35318),
        f35329(35329),
        f35330(35330),
        f35331(35331),
        f35332(35332),
        f35339(35339),
        f35340(35340),
        f35341(35341),
        f35342(35342),
        f35349(35349),
        f35350(35350),
        f35351(35351),
        f35352(35352),
        f35359(35359),
        f35360(35360),
        f35361(35361),
        f35362(35362),
        f35369(35369),
        f35370(35370),
        f35371(35371),
        f35372(35372),
        f35379(35379),
        f35380(35380),
        f35381(35381),
        f35382(35382),
        f35962(35962),
        f35964(35964),
        f35965(35965),
        f35966(35966),
        f35974(35974),
        f35976(35976),
        f35977(35977),
        f35978(35978),
        f36234(36234),
        f36236(36236),
        f36237(36237),
        f36238(36238),
        f36242(36242),
        f36244(36244),
        f36245(36245),
        f36246(36246),
        f36266(36266),
        f36268(36268),
        f36269(36269),
        f36270(36270),
        f36274(36274),
        f36276(36276),
        f36277(36277),
        f36278(36278),
        f36282(36282),
        f36284(36284),
        f36285(36285),
        f36286(36286),
        f36294(36294),
        f36296(36296),
        f36297(36297),
        f36298(36298),
        f36302(36302),
        f36304(36304),
        f36305(36305),
        f36306(36306),
        f36310(36310),
        f36312(36312),
        f36313(36313),
        f36314(36314),
        f36323(36323),
        f36325(36325),
        f36326(36326),
        f36327(36327),
        f36335(36335),
        f36337(36337),
        f36338(36338),
        f36339(36339),
        f37154(37154),
        f37156(37156),
        f37157(37157),
        f37158(37158),
        f37162(37162),
        f37164(37164),
        f37165(37165),
        f37166(37166),
        f37170(37170),
        f37172(37172),
        f37173(37173),
        f37174(37174),
        f37269(37269),
        f37271(37271),
        f37272(37272),
        f37273(37273),
        f37313(37313),
        f37314(37314),
        f37315(37315),
        f37316(37316),
        f37323(37323),
        f37324(37324),
        f37325(37325),
        f37326(37326),
        f37333(37333),
        f37334(37334),
        f37335(37335),
        f37336(37336),
        f37343(37343),
        f37344(37344),
        f37345(37345),
        f37346(37346),
        f37353(37353),
        f37354(37354),
        f37355(37355),
        f37356(37356),
        f37363(37363),
        f37364(37364),
        f37365(37365),
        f37366(37366),
        f37383(37383),
        f37384(37384),
        f37385(37385),
        f37386(37386),
        f37393(37393),
        f37394(37394),
        f37395(37395),
        f37396(37396),
        f37403(37403),
        f37404(37404),
        f37405(37405),
        f37406(37406),
        f37413(37413),
        f37414(37414),
        f37415(37415),
        f37416(37416),
        f37423(37423),
        f37424(37424),
        f37425(37425),
        f37426(37426),
        f37443(37443),
        f37444(37444),
        f37445(37445),
        f37446(37446),
        f37453(37453),
        f37454(37454),
        f37455(37455),
        f37456(37456),
        f37463(37463),
        f37464(37464),
        f37465(37465),
        f37466(37466),
        f37473(37473),
        f37474(37474),
        f37475(37475),
        f37476(37476),
        f37485(37485),
        f37486(37486),
        f37487(37487),
        f37488(37488),
        f37495(37495),
        f37496(37496),
        f37497(37497),
        f37498(37498),
        f37505(37505),
        f37506(37506),
        f37507(37507),
        f37508(37508),
        f37532(37532),
        f37533(37533),
        f37534(37534),
        f37535(37535),
        f37543(37543),
        f37544(37544),
        f37545(37545),
        f37546(37546),
        f37553(37553),
        f37554(37554),
        f37555(37555),
        f37556(37556),
        f37564(37564),
        f37566(37566),
        f37567(37567),
        f37568(37568),
        f37572(37572),
        f37574(37574),
        f37575(37575),
        f37576(37576),
        f37580(37580),
        f37582(37582),
        f37583(37583),
        f37584(37584),
        f37600(37600),
        f37602(37602),
        f37603(37603),
        f37604(37604),
        f37610(37610),
        f37612(37612),
        f37613(37613),
        f37614(37614),
        f37771(37771),
        f37773(37773),
        f37774(37774),
        f37775(37775),
        f37779(37779),
        f37781(37781),
        f37782(37782),
        f37783(37783),
        f38022(38022),
        f38032(38032),
        f38044(38044),
        f38054(38054),
        f38064(38064),
        f38086(38086),
        f38096(38096),
        f38106(38106),
        f38128(38128),
        f38138(38138),
        f38148(38148),
        f38158(38158),
        f38311(38311),
        f38313(38313),
        f38314(38314),
        f38315(38315),
        f38349(38349),
        f38351(38351),
        f38352(38352),
        f38353(38353),
        f38357(38357),
        f38359(38359),
        f38360(38360),
        f38361(38361),
        f38408(38408),
        f38409(38409),
        f38410(38410),
        f38411(38411),
        f38438(38438),
        f38440(38440),
        f38441(38441),
        f38442(38442),
        f38451(38451),
        f38453(38453),
        f38454(38454),
        f38455(38455),
        f38779(38779),
        f38788(38788),
        f38797(38797),
        f38806(38806),
        f38815(38815),
        f38829(38829),
        f38838(38838),
        f38847(38847),
        f38856(38856),
        f38909(38909),
        f39032(39032),
        f39034(39034),
        f39035(39035),
        f39036(39036),
        f39040(39040),
        f39042(39042),
        f39043(39043),
        f39044(39044),
        f39240(39240),
        f39242(39242),
        f39243(39243),
        f39244(39244),
        f39421(39421),
        f39423(39423),
        f39424(39424),
        f39425(39425),
        f39429(39429),
        f39431(39431),
        f39432(39432),
        f39433(39433),
        f39437(39437),
        f39439(39439),
        f39440(39440),
        f39441(39441),
        f39445(39445),
        f39447(39447),
        f39448(39448),
        f39449(39449),
        f39453(39453),
        f39455(39455),
        f39456(39456),
        f39457(39457),
        f39464(39464),
        f39466(39466),
        f39467(39467),
        f39468(39468),
        f39472(39472),
        f39474(39474),
        f39475(39475),
        f39476(39476),
        f39480(39480),
        f39482(39482),
        f39483(39483),
        f39484(39484),
        f39488(39488),
        f39490(39490),
        f39491(39491),
        f39492(39492),
        f39498(39498),
        f39500(39500),
        f39501(39501),
        f39502(39502),
        f39506(39506),
        f39508(39508),
        f39509(39509),
        f39510(39510),
        f39514(39514),
        f39516(39516),
        f39517(39517),
        f39518(39518),
        f39525(39525),
        f39527(39527),
        f39528(39528),
        f39529(39529),
        f39533(39533),
        f39535(39535),
        f39536(39536),
        f39537(39537),
        f39541(39541),
        f39543(39543),
        f39544(39544),
        f39545(39545),
        f39549(39549),
        f39551(39551),
        f39552(39552),
        f39553(39553),
        f39557(39557),
        f39559(39559),
        f39560(39560),
        f39561(39561),
        f39565(39565),
        f39567(39567),
        f39568(39568),
        f39569(39569),
        f39575(39575),
        f39577(39577),
        f39578(39578),
        f39579(39579),
        f40092(40092),
        f40094(40094),
        f40095(40095),
        f40096(40096),
        f40100(40100),
        f40102(40102),
        f40103(40103),
        f40104(40104),
        f40108(40108),
        f40110(40110),
        f40111(40111),
        f40112(40112),
        f40116(40116),
        f40118(40118),
        f40119(40119),
        f40120(40120),
        f40124(40124),
        f40126(40126),
        f40127(40127),
        f40128(40128),
        f40441(40441),
        f40443(40443),
        f40444(40444),
        f40445(40445),
        f40449(40449),
        f40451(40451),
        f40452(40452),
        f40453(40453),
        f40457(40457),
        f40459(40459),
        f40460(40460),
        f40461(40461),
        f40547(40547),
        f40549(40549),
        f40550(40550),
        f40551(40551),
        f40555(40555),
        f40557(40557),
        f40558(40558),
        f40559(40559),
        f40563(40563),
        f40565(40565),
        f40566(40566),
        f40567(40567),
        f40574(40574),
        f40576(40576),
        f40577(40577),
        f40578(40578),
        f40582(40582),
        f40583(40583),
        f40584(40584),
        f40585(40585),
        f40586(40586),
        f40587(40587),
        f40591(40591),
        f40593(40593),
        f40594(40594),
        f40595(40595),
        f40967(40967),
        f40969(40969),
        f40970(40970),
        f40971(40971),
        f40975(40975),
        f40978(40978),
        f40979(40979),
        f40980(40980),
        f40984(40984),
        f40986(40986),
        f40987(40987),
        f40988(40988),
        f41016(41016),
        f41018(41018),
        f41019(41019),
        f41020(41020),
        f41024(41024),
        f41026(41026),
        f41027(41027),
        f41028(41028),
        f41032(41032),
        f41034(41034),
        f41035(41035),
        f41036(41036),
        f41049(41049),
        f41050(41050),
        f41051(41051),
        f41052(41052),
        f41059(41059),
        f41060(41060),
        f41061(41061),
        f41062(41062),
        f41069(41069),
        f41070(41070),
        f41071(41071),
        f41072(41072),
        f41079(41079),
        f41080(41080),
        f41081(41081),
        f41082(41082),
        f41089(41089),
        f41090(41090),
        f41091(41091),
        f41092(41092),
        f41099(41099),
        f41100(41100),
        f41101(41101),
        f41102(41102),
        f41109(41109),
        f41110(41110),
        f41111(41111),
        f41112(41112),
        f41119(41119),
        f41120(41120),
        f41121(41121),
        f41122(41122),
        f41199(41199),
        f41201(41201),
        f41202(41202),
        f41203(41203),
        f41207(41207),
        f41209(41209),
        f41210(41210),
        f41211(41211),
        f41215(41215),
        f41217(41217),
        f41218(41218),
        f41219(41219),
        f41289(41289),
        f41290(41290),
        f41291(41291),
        f41292(41292),
        f41299(41299),
        f41300(41300),
        f41301(41301),
        f41302(41302),
        f41309(41309),
        f41310(41310),
        f41311(41311),
        f41312(41312),
        f41319(41319),
        f41320(41320),
        f41321(41321),
        f41322(41322),
        f41329(41329),
        f41330(41330),
        f41331(41331),
        f41332(41332),
        f41339(41339),
        f41340(41340),
        f41341(41341),
        f41342(41342),
        f41349(41349),
        f41350(41350),
        f41351(41351),
        f41352(41352),
        f41359(41359),
        f41360(41360),
        f41361(41361),
        f41362(41362),
        f41443(41443),
        f41444(41444),
        f41445(41445),
        f41446(41446),
        f41453(41453),
        f41454(41454),
        f41455(41455),
        f41456(41456),
        f41463(41463),
        f41464(41464),
        f41465(41465),
        f41466(41466),
        f41473(41473),
        f41474(41474),
        f41475(41475),
        f41476(41476),
        f41483(41483),
        f41484(41484),
        f41485(41485),
        f41486(41486),
        f41493(41493),
        f41494(41494),
        f41495(41495),
        f41496(41496),
        f41503(41503),
        f41504(41504),
        f41505(41505),
        f41506(41506),
        f41513(41513),
        f41514(41514),
        f41515(41515),
        f41516(41516),
        f43132(43132),
        f43133(43133),
        f43134(43134),
        f43135(43135),
        f43142(43142),
        f43143(43143),
        f43144(43144),
        f43145(43145),
        f43152(43152),
        f43153(43153),
        f43154(43154),
        f43155(43155),
        f43162(43162),
        f43163(43163),
        f43164(43164),
        f43165(43165),
        f43172(43172),
        f43173(43173),
        f43174(43174),
        f43175(43175),
        f43294(43294),
        f43295(43295),
        f43296(43296),
        f43297(43297),
        f43304(43304),
        f43305(43305),
        f43306(43306),
        f43307(43307),
        f43314(43314),
        f43315(43315),
        f43316(43316),
        f43317(43317),
        f43324(43324),
        f43325(43325),
        f43326(43326),
        f43327(43327),
        f43334(43334),
        f43335(43335),
        f43336(43336),
        f43337(43337),
        f43549(43549),
        f43551(43551),
        f43552(43552),
        f43553(43553),
        f43557(43557),
        f43559(43559),
        f43560(43560),
        f43561(43561),
        f43567(43567),
        f43569(43569),
        f43570(43570),
        f43571(43571),
        f43575(43575),
        f43577(43577),
        f43578(43578),
        f43579(43579),
        f43583(43583),
        f43585(43585),
        f43586(43586),
        f43587(43587),
        f43591(43591),
        f43593(43593),
        f43594(43594),
        f43595(43595),
        f43599(43599),
        f43601(43601),
        f43602(43602),
        f43603(43603),
        f43607(43607),
        f43609(43609),
        f43610(43610),
        f43611(43611),
        f43615(43615),
        f43617(43617),
        f43618(43618),
        f43619(43619),
        f43935(43935),
        f43937(43937),
        f43938(43938),
        f43939(43939),
        f43943(43943),
        f43945(43945),
        f43946(43946),
        f43947(43947),
        f44035(44035),
        f44037(44037),
        f44038(44038),
        f44039(44039),
        f44043(44043),
        f44045(44045),
        f44046(44046),
        f44047(44047),
        f44051(44051),
        f44053(44053),
        f44054(44054),
        f44055(44055),
        f44131(44131),
        f44133(44133),
        f44134(44134),
        f44135(44135),
        f44139(44139),
        f44141(44141),
        f44142(44142),
        f44143(44143),
        f44217(44217),
        f44219(44219),
        f44220(44220),
        f44221(44221),
        f44225(44225),
        f44227(44227),
        f44228(44228),
        f44229(44229),
        f44564(44564),
        f44566(44566),
        f44567(44567),
        f44568(44568),
        f44728(44728),
        f44730(44730),
        f44731(44731),
        f44732(44732),
        f44733(44733),
        f44738(44738),
        f44740(44740),
        f44741(44741),
        f44742(44742),
        f44743(44743),
        f44748(44748),
        f44750(44750),
        f44751(44751),
        f44752(44752),
        f44753(44753),
        f44760(44760),
        f44761(44761),
        f44762(44762),
        f44763(44763),
        f45019(45019),
        f45021(45021),
        f45022(45022),
        f45023(45023),
        f45027(45027),
        f45029(45029),
        f45030(45030),
        f45031(45031),
        f45035(45035),
        f45037(45037),
        f45038(45038),
        f45039(45039),
        f45043(45043),
        f45045(45045),
        f45046(45046),
        f45047(45047),
        f45051(45051),
        f45053(45053),
        f45054(45054),
        f45055(45055),
        f45154(45154),
        f45156(45156),
        f45157(45157),
        f45158(45158),
        f45162(45162),
        f45164(45164),
        f45165(45165),
        f45166(45166),
        f45170(45170),
        f45172(45172),
        f45173(45173),
        f45174(45174),
        f45178(45178),
        f45180(45180),
        f45181(45181),
        f45182(45182),
        f45186(45186),
        f45188(45188),
        f45189(45189),
        f45190(45190),
        f45211(45211),
        f45213(45213),
        f45214(45214),
        f45215(45215),
        f45266(45266),
        f45267(45267),
        f45268(45268),
        f45272(45272),
        f45273(45273),
        f45274(45274),
        f45278(45278),
        f45279(45279),
        f45280(45280),
        f45284(45284),
        f45286(45286),
        f45287(45287),
        f45288(45288),
        f45374(45374),
        f45376(45376),
        f45377(45377),
        f45378(45378),
        f45382(45382),
        f45384(45384),
        f45385(45385),
        f45386(45386),
        f45390(45390),
        f45392(45392),
        f45393(45393),
        f45394(45394),
        f45398(45398),
        f45400(45400),
        f45401(45401),
        f45402(45402),
        f45506(45506),
        f45508(45508),
        f45509(45509),
        f45510(45510),
        f45514(45514),
        f45516(45516),
        f45517(45517),
        f45518(45518),
        f45522(45522),
        f45524(45524),
        f45525(45525),
        f45526(45526),
        f45530(45530),
        f45532(45532),
        f45533(45533),
        f45534(45534),
        f45538(45538),
        f45540(45540),
        f45541(45541),
        f45542(45542),
        f45647(45647),
        f45649(45649),
        f45650(45650),
        f45651(45651),
        f45655(45655),
        f45657(45657),
        f45658(45658),
        f45659(45659),
        f46020(46020),
        f46022(46022),
        f46023(46023),
        f46024(46024),
        f46028(46028),
        f46030(46030),
        f46031(46031),
        f46032(46032),
        f46036(46036),
        f46038(46038),
        f46039(46039),
        f46040(46040),
        f46044(46044),
        f46046(46046),
        f46047(46047),
        f46048(46048),
        f46262(46262),
        f46273(46273),
        f46284(46284),
        f46295(46295),
        f46306(46306),
        f46317(46317),
        f46329(46329),
        f46340(46340),
        f46351(46351),
        f46362(46362),
        f46389(46389),
        f46400(46400),
        f46476(46476),
        f46478(46478),
        f46479(46479),
        f46480(46480),
        f46643(46643),
        f46654(46654),
        f46665(46665),
        f46676(46676),
        f46687(46687),
        f46698(46698),
        f46709(46709),
        f46720(46720),
        f46732(46732),
        f46743(46743),
        f46754(46754),
        f46765(46765),
        f46776(46776),
        f46788(46788),
        f46799(46799),
        f46810(46810),
        f46821(46821),
        f46833(46833),
        f46844(46844),
        f46856(46856),
        f46867(46867),
        f46878(46878),
        f46889(46889),
        f46900(46900),
        f46911(46911),
        f46922(46922),
        f46933(46933),
        f46945(46945),
        f46956(46956),
        f46968(46968),
        f46979(46979),
        f46990(46990),
        f47001(47001),
        f47012(47012),
        f47023(47023),
        f47034(47034),
        f47045(47045),
        f47252(47252),
        f47254(47254),
        f47255(47255),
        f47256(47256),
        f47262(47262),
        f47264(47264),
        f47265(47265),
        f47266(47266),
        f47272(47272),
        f47274(47274),
        f47275(47275),
        f47276(47276),
        f47282(47282),
        f47284(47284),
        f47285(47285),
        f47286(47286),
        f47374(47374),
        f47376(47376),
        f47377(47377),
        f47378(47378),
        f47410(47410),
        f47411(47411),
        f47412(47412),
        f47413(47413),
        f47420(47420),
        f47421(47421),
        f47422(47422),
        f47423(47423),
        f47430(47430),
        f47431(47431),
        f47432(47432),
        f47433(47433),
        f47440(47440),
        f47441(47441),
        f47442(47442),
        f47443(47443),
        f47450(47450),
        f47451(47451),
        f47452(47452),
        f47453(47453),
        f47460(47460),
        f47461(47461),
        f47462(47462),
        f47463(47463),
        f47470(47470),
        f47471(47471),
        f47472(47472),
        f47473(47473),
        f47480(47480),
        f47481(47481),
        f47482(47482),
        f47483(47483),
        f47490(47490),
        f47491(47491),
        f47492(47492),
        f47493(47493),
        f47500(47500),
        f47501(47501),
        f47502(47502),
        f47503(47503),
        f47510(47510),
        f47511(47511),
        f47512(47512),
        f47513(47513),
        f47522(47522),
        f47523(47523),
        f47524(47524),
        f47525(47525),
        f47532(47532),
        f47533(47533),
        f47534(47534),
        f47535(47535),
        f47542(47542),
        f47543(47543),
        f47544(47544),
        f47545(47545),
        f47552(47552),
        f47553(47553),
        f47554(47554),
        f47555(47555),
        f47562(47562),
        f47563(47563),
        f47564(47564),
        f47565(47565),
        f47572(47572),
        f47573(47573),
        f47574(47574),
        f47575(47575),
        f47582(47582),
        f47583(47583),
        f47584(47584),
        f47585(47585),
        f47592(47592),
        f47593(47593),
        f47594(47594),
        f47595(47595),
        f47602(47602),
        f47603(47603),
        f47604(47604),
        f47605(47605),
        f47612(47612),
        f47613(47613),
        f47614(47614),
        f47615(47615),
        f47622(47622),
        f47623(47623),
        f47624(47624),
        f47625(47625),
        f47686(47686),
        f47687(47687),
        f47688(47688),
        f47689(47689),
        f47698(47698),
        f47700(47700),
        f47701(47701),
        f47702(47702),
        f47706(47706),
        f47708(47708),
        f47709(47709),
        f47710(47710),
        f47714(47714),
        f47716(47716),
        f47717(47717),
        f47718(47718),
        f47722(47722),
        f47724(47724),
        f47725(47725),
        f47726(47726),
        f47730(47730),
        f47732(47732),
        f47733(47733),
        f47734(47734),
        f47738(47738),
        f47740(47740),
        f47741(47741),
        f47742(47742),
        f47746(47746),
        f47748(47748),
        f47749(47749),
        f47750(47750),
        f47754(47754),
        f47756(47756),
        f47757(47757),
        f47758(47758),
        f77845(77845),
        f77846(77846),
        f77847(77847),
        f77848(77848),
        f77958(77958),
        f77959(77959),
        f77960(77960),
        f77973(77973),
        f77974(77974),
        f77975(77975),
        f77979(77979),
        f77990(77990),
        f78016(78016),
        f78017(78017),
        f78019(78019),
        f78020(78020),
        f78021(78021),
        f78022(78022),
        f78040(78040),
        f78041(78041),
        f78044(78044),
        f78045(78045),
        f78046(78046),
        f78074(78074),
        f78075(78075),
        f78076(78076),
        f78077(78077),
        f78081(78081),
        f78090(78090),
        f78091(78091),
        f78093(78093),
        f78094(78094),
        f78095(78095),
        f78096(78096),
        f78097(78097),
        f78110(78110),
        f78113(78113),
        f78114(78114),
        f78119(78119),
        f78120(78120),
        f78121(78121),
        f78122(78122),
        f78123(78123),
        f78124(78124),
        f78182(78182),
        f78185(78185),
        f78189(78189),
        f78190(78190),
        f78243(78243),
        f78255(78255),
        f78263(78263),
        f78292(78292),
        f78297(78297),
        f78298(78298),
        f78319(78319),
        f78320(78320),
        f78321(78321),
        f78338(78338),
        f78344(78344),
        f78346(78346),
        f78370(78370),
        f78371(78371),
        f78382(78382),
        f78383(78383),
        f78384(78384),
        f78385(78385),
        f78413(78413),
        f78414(78414),
        f78415(78415),
        f78416(78416),
        f78417(78417),
        f78418(78418),
        f78419(78419),
        f78420(78420),
        f78421(78421),
        f78422(78422),
        f78423(78423),
        f78424(78424),
        f78426(78426),
        f78427(78427),
        f78428(78428),
        f78434(78434),
        f78435(78435),
        f78440(78440),
        f78441(78441),
        f78442(78442),
        f78448(78448),
        f78452(78452),
        f78453(78453),
        f78454(78454),
        f78483(78483),
        f78484(78484),
        f78485(78485),
        f78486(78486),
        f78490(78490),
        f78491(78491),
        f78492(78492),
        f78493(78493),
        f78523(78523),
        f78524(78524),
        f78529(78529),
        f78556(78556),
        f78573(78573),
        f78574(78574),
        f78603(78603),
        f78609(78609),
        f78610(78610),
        f78627(78627),
        f78628(78628),
        f78630(78630),
        f78632(78632),
        f78635(78635),
        f78636(78636),
        f78647(78647),
        f78654(78654),
        f78663(78663),
        f78672(78672),
        f78679(78679),
        f78694(78694),
        f78699(78699),
        f78702(78702),
        f78711(78711),
        f78721(78721),
        f78722(78722),
        f78752(78752),
        f78753(78753),
        f78765(78765),
        f78766(78766),
        f78767(78767),
        f78768(78768),
        f78779(78779),
        f78780(78780),
        f78788(78788),
        f78789(78789),
        f78790(78790),
        f78798(78798),
        f78799(78799),
        f78800(78800),
        f78801(78801),
        f78807(78807),
        f78817(78817),
        f78818(78818),
        f78819(78819),
        f78821(78821),
        f78822(78822),
        f78823(78823),
        f78824(78824),
        f78835(78835),
        f78839(78839),
        f78840(78840),
        f78842(78842),
        f78843(78843),
        f78844(78844),
        f78845(78845),
        f78846(78846),
        f78847(78847),
        f78848(78848),
        f78849(78849),
        f78850(78850),
        f78851(78851),
        f78852(78852),
        f78853(78853),
        f78854(78854),
        f78855(78855),
        f78856(78856),
        f78858(78858),
        f78859(78859),
        f78860(78860),
        f78865(78865),
        f78866(78866),
        f78867(78867),
        f78868(78868),
        f78879(78879),
        f78885(78885),
        f78886(78886),
        f78887(78887),
        f78888(78888),
        f78889(78889),
        f78890(78890),
        f78891(78891),
        f78892(78892),
        f78893(78893),
        f78894(78894),
        f78895(78895),
        f78896(78896),
        f78897(78897),
        f78898(78898),
        f78899(78899),
        f78900(78900),
        f78901(78901),
        f78902(78902),
        f78916(78916),
        f78917(78917),
        f78918(78918),
        f78923(78923),
        f78924(78924),
        f78925(78925),
        f78931(78931),
        f78932(78932),
        f78933(78933),
        f78934(78934),
        f78939(78939),
        f79039(79039),
        f79041(79041),
        f79042(79042),
        f79048(79048),
        f79049(79049),
        f79052(79052),
        f79059(79059),
        f79079(79079),
        f79100(79100),
        f79101(79101),
        f79102(79102),
        f79103(79103),
        f79105(79105),
        f79107(79107),
        f79142(79142),
        f79143(79143),
        f79147(79147),
        f79148(79148),
        f79154(79154),
        f79155(79155),
        f79156(79156),
        f79157(79157),
        f79195(79195),
        f79197(79197),
        f79202(79202),
        f79228(79228),
        f79231(79231),
        f79232(79232),
        f79233(79233),
        f79246(79246),
        f79258(79258),
        f79259(79259),
        f79260(79260),
        f79264(79264),
        f79266(79266),
        f79290(79290),
        f79361(79361),
        f79362(79362),
        f79363(79363),
        f79364(79364),
        f79365(79365),
        f79366(79366),
        f79367(79367),
        f79368(79368),
        f79373(79373),
        f79374(79374),
        f79375(79375),
        f79380(79380),
        f79381(79381),
        f79394(79394),
        f79418(79418),
        f79424(79424),
        f79427(79427),
        f79452(79452),
        f79453(79453),
        f79454(79454),
        f79455(79455),
        f79456(79456),
        f79457(79457),
        f79464(79464),
        f79465(79465),
        f79466(79466),
        f79472(79472),
        f79473(79473),
        f79474(79474),
        f79485(79485),
        f79486(79486),
        f79491(79491),
        f79542(79542),
        f79564(79564),
        f79586(79586),
        f79587(79587),
        f79601(79601),
        f79609(79609),
        f79624(79624),
        f79625(79625),
        f79626(79626),
        f79646(79646),
        f79647(79647),
        f79648(79648),
        f79677(79677),
        f79679(79679),
        f79680(79680),
        f79681(79681),
        f79682(79682),
        f79683(79683),
        f79684(79684),
        f79685(79685),
        f79686(79686),
        f79687(79687),
        f79699(79699),
        f79700(79700),
        f79701(79701),
        f79730(79730),
        f79733(79733),
        f79734(79734),
        f79776(79776),
        f79779(79779),
        f79782(79782),
        f79785(79785),
        f79786(79786),
        f79793(79793),
        f79801(79801),
        f79802(79802),
        f79815(79815),
        f79816(79816),
        f79817(79817),
        f79819(79819),
        f79820(79820),
        f79821(79821),
        f79835(79835),
        f79844(79844),
        f79846(79846),
        f79850(79850),
        f79851(79851),
        f79867(79867),
        f79868(79868),
        f79871(79871),
        f79872(79872),
        f79896(79896),
        f79918(79918),
        f79970(79970),
        f79973(79973),
        f999445(999445),
        f999446(999446),
        f999447(999447),
        f999448(999448),
        f999558(999558),
        f999559(999559),
        f999560(999560),
        f999573(999573),
        f999574(999574),
        f999575(999575),
        f999579(999579),
        f999590(999590),
        f999616(999616),
        f999617(999617),
        f999619(999619),
        f999620(999620),
        f999621(999621),
        f999622(999622),
        f999640(999640),
        f999641(999641),
        f999644(999644),
        f999645(999645),
        f999646(999646),
        f999674(999674),
        f999675(999675),
        f999676(999676),
        f999677(999677),
        f999681(999681),
        f999690(999690),
        f999691(999691),
        f999693(999693),
        f999694(999694),
        f999695(999695),
        f999696(999696),
        f999697(999697),
        f999710(999710),
        f999713(999713),
        f999714(999714),
        f999719(999719),
        f999720(999720),
        f999721(999721),
        f999722(999722),
        f999723(999723),
        f999724(999724),
        f999782(999782),
        f999785(999785),
        f999789(999789),
        f999790(999790),
        f999843(999843),
        f999855(999855),
        f999863(999863),
        f999892(999892),
        f999897(999897),
        f999898(999898),
        f999919(999919),
        f999920(999920),
        f999921(999921),
        f999938(999938),
        f999944(999944),
        f999946(999946),
        f999970(999970),
        f999971(999971),
        f999982(999982),
        f999983(999983),
        f999984(999984),
        f999985(999985),
        f1000013(1000013),
        f1000014(1000014),
        f1000015(1000015),
        f1000016(1000016),
        f1000017(1000017),
        f1000018(1000018),
        f1000019(1000019),
        f1000020(1000020),
        f1000021(1000021),
        f1000022(1000022),
        f1000023(1000023),
        f1000024(1000024),
        f1000026(1000026),
        f1000027(1000027),
        f1000028(1000028),
        f1000034(1000034),
        f1000035(1000035),
        f1000040(1000040),
        f1000041(1000041),
        f1000042(1000042),
        f1000048(1000048),
        f1000052(1000052),
        f1000053(1000053),
        f1000054(1000054),
        f1000083(1000083),
        f1000084(1000084),
        f1000085(1000085),
        f1000086(1000086),
        f1000090(1000090),
        f1000091(1000091),
        f1000092(1000092),
        f1000093(1000093),
        f1000123(1000123),
        f1000124(1000124),
        f1000129(1000129),
        f1000156(1000156),
        f1000173(1000173),
        f1000174(1000174),
        f1000203(1000203),
        f1000209(1000209),
        f1000210(1000210),
        f1000227(1000227),
        f1000228(1000228),
        f1000230(1000230),
        f1000232(1000232),
        f1000235(1000235),
        f1000236(1000236),
        f1000247(1000247),
        f1000254(1000254),
        f1000263(1000263),
        f1000272(1000272),
        f1000279(1000279),
        f1000294(1000294),
        f1000299(1000299),
        f1000302(1000302),
        f1000311(1000311),
        f1000321(1000321),
        f1000322(1000322),
        f1000352(1000352),
        f1000353(1000353),
        f1000365(1000365),
        f1000366(1000366),
        f1000367(1000367),
        f1000368(1000368),
        f1000379(1000379),
        f1000380(1000380),
        f1000388(1000388),
        f1000389(1000389),
        f1000390(1000390),
        f1000398(1000398),
        f1000399(1000399),
        f1000400(1000400),
        f1000401(1000401),
        f1000407(1000407),
        f1000417(1000417),
        f1000418(1000418),
        f1000419(1000419),
        f1000421(1000421),
        f1000422(1000422),
        f1000423(1000423),
        f1000424(1000424),
        f1000435(1000435),
        f1000439(1000439),
        f1000440(1000440),
        f1000442(1000442),
        f1000443(1000443),
        f1000444(1000444),
        f1000445(1000445),
        f1000446(1000446),
        f1000447(1000447),
        f1000448(1000448),
        f1000449(1000449),
        f1000450(1000450),
        f1000451(1000451),
        f1000452(1000452),
        f1000453(1000453),
        f1000454(1000454),
        f1000455(1000455),
        f1000456(1000456),
        f1000458(1000458),
        f1000459(1000459),
        f1000460(1000460),
        f1000465(1000465),
        f1000466(1000466),
        f1000467(1000467),
        f1000468(1000468),
        f1000479(1000479),
        f1000485(1000485),
        f1000486(1000486),
        f1000487(1000487),
        f1000488(1000488),
        f1000489(1000489),
        f1000490(1000490),
        f1000491(1000491),
        f1000492(1000492),
        f1000493(1000493),
        f1000494(1000494),
        f1000495(1000495),
        f1000496(1000496),
        f1000497(1000497),
        f1000498(1000498),
        f1000499(1000499),
        f1000500(1000500),
        f1000501(1000501),
        f1000502(1000502),
        f1000516(1000516),
        f1000517(1000517),
        f1000518(1000518),
        f1000523(1000523),
        f1000524(1000524),
        f1000525(1000525),
        f1000531(1000531),
        f1000532(1000532),
        f1000533(1000533),
        f1000534(1000534),
        f1000539(1000539),
        f1000639(1000639),
        f1000641(1000641),
        f1000642(1000642),
        f1000648(1000648),
        f1000649(1000649),
        f1000652(1000652),
        f1000659(1000659),
        f1000679(1000679),
        f1000705(1000705),
        f1000707(1000707),
        f1000743(1000743),
        f1000747(1000747),
        f1000748(1000748),
        f1000754(1000754),
        f1000755(1000755),
        f1000756(1000756),
        f1000757(1000757),
        f1000795(1000795),
        f1000797(1000797),
        f1000802(1000802),
        f1000828(1000828),
        f1000831(1000831),
        f1000832(1000832),
        f1000833(1000833),
        f1000846(1000846),
        f1000858(1000858),
        f1000859(1000859),
        f1000860(1000860),
        f1000864(1000864),
        f1000866(1000866),
        f1000890(1000890),
        f1000961(1000961),
        f1000962(1000962),
        f1000963(1000963),
        f1000964(1000964),
        f1000965(1000965),
        f1000966(1000966),
        f1000967(1000967),
        f1000968(1000968),
        f1000973(1000973),
        f1000974(1000974),
        f1000975(1000975),
        f1000980(1000980),
        f1000981(1000981),
        f1000994(1000994),
        f1001018(1001018),
        f1001024(1001024),
        f1001027(1001027),
        f1001052(1001052),
        f1001053(1001053),
        f1001054(1001054),
        f1001055(1001055),
        f1001056(1001056),
        f1001057(1001057),
        f1001064(1001064),
        f1001065(1001065),
        f1001066(1001066),
        f1001072(1001072),
        f1001073(1001073),
        f1001074(1001074),
        f1001085(1001085),
        f1001086(1001086),
        f1001091(1001091),
        f1001142(1001142),
        f1001164(1001164),
        f1001186(1001186),
        f1001187(1001187),
        f1001201(1001201),
        f1001209(1001209),
        f1001224(1001224),
        f1001225(1001225),
        f1001226(1001226),
        f1001246(1001246),
        f1001247(1001247),
        f1001248(1001248),
        f1001277(1001277),
        f1001279(1001279),
        f1001280(1001280),
        f1001281(1001281),
        f1001282(1001282),
        f1001283(1001283),
        f1001284(1001284),
        f1001285(1001285),
        f1001286(1001286),
        f1001287(1001287),
        f1001299(1001299),
        f1001300(1001300),
        f1001301(1001301),
        f1001330(1001330),
        f1001333(1001333),
        f1001334(1001334),
        f1001376(1001376),
        f1001379(1001379),
        f1001382(1001382),
        f1001385(1001385),
        f1001386(1001386),
        f1001393(1001393),
        f1001401(1001401),
        f1001402(1001402),
        f1001415(1001415),
        f1001416(1001416),
        f1001417(1001417),
        f1001419(1001419),
        f1001420(1001420),
        f1001421(1001421),
        f1001435(1001435),
        f1001444(1001444),
        f1001446(1001446),
        f1001450(1001450),
        f1001451(1001451),
        f1001467(1001467),
        f1001468(1001468),
        f1001471(1001471),
        f1001472(1001472),
        f1001496(1001496),
        f1001518(1001518),
        f1001570(1001570),
        f1001573(1001573),
        e4194528(4194528),
        e4194529(4194529),
        e4194530(4194530),
        e4194531(4194531),
        e4194532(4194532),
        e4194533(4194533),
        e4194534(4194534),
        e4194535(4194535),
        e4194536(4194536),
        e4194537(4194537),
        e4194538(4194538),
        e4194539(4194539),
        e4194540(4194540),
        e4194541(4194541),
        e4194542(4194542),
        e4194543(4194543),
        e4194544(4194544),
        e4194545(4194545),
        e4194546(4194546),
        e4194547(4194547),
        e4194548(4194548),
        e4194549(4194549),
        e4194550(4194550),
        e4194551(4194551),
        e4194552(4194552),
        e4194553(4194553),
        e4194554(4194554),
        e4194555(4194555),
        e4194556(4194556),
        e4194557(4194557),
        e4194558(4194558),
        e4194559(4194559),
        e4194560(4194560),
        e4194561(4194561),
        e4194562(4194562),
        e4194563(4194563),
        e4194564(4194564),
        e4194565(4194565),
        e4194566(4194566),
        e4194567(4194567),
        e4194568(4194568),
        e4194569(4194569),
        e4194570(4194570),
        e4194571(4194571),
        e4194572(4194572),
        e4194573(4194573),
        e4194574(4194574),
        e4194575(4194575),
        e4194576(4194576),
        e4194577(4194577),
        e4194578(4194578),
        e4194579(4194579),
        e4194580(4194580),
        e4194581(4194581),
        e4194582(4194582),
        e4194583(4194583),
        e4194584(4194584),
        e4194585(4194585),
        e4194586(4194586),
        e4194587(4194587),
        e4194591(4194591),
        e4194592(4194592),
        e4194593(4194593),
        e4194594(4194594),
        e4194595(4194595),
        e4194596(4194596),
        e4194597(4194597),
        e4194598(4194598),
        e4194599(4194599),
        e4194600(4194600),
        e4194601(4194601),
        e4194602(4194602),
        e4194603(4194603),
        e4194604(4194604),
        e4194605(4194605),
        e4194607(4194607),
        e4194608(4194608),
        e4194609(4194609),
        e4194610(4194610),
        e4194611(4194611),
        e4194612(4194612),
        e4194613(4194613),
        e4194614(4194614),
        e4194615(4194615),
        e4194616(4194616),
        e4194617(4194617),
        e4194620(4194620),
        e4194621(4194621),
        e4194622(4194622),
        e4194623(4194623),
        e4194624(4194624),
        e4194626(4194626),
        e4194627(4194627),
        e4194628(4194628),
        e4194629(4194629),
        e4194630(4194630),
        e4194631(4194631),
        e4194632(4194632),
        e4194652(4194652),
        e4194654(4194654),
        e4194655(4194655),
        e4194656(4194656),
        e4194657(4194657),
        e4194658(4194658),
        e4194659(4194659),
        e4194660(4194660),
        e4194661(4194661),
        e4194662(4194662),
        e4194663(4194663),
        e4194664(4194664),
        e4194665(4194665),
        e4194671(4194671),
        e4194672(4194672),
        e4194673(4194673),
        e4194674(4194674),
        e4194675(4194675),
        e4194676(4194676),
        e4194683(4194683),
        e4194684(4194684),
        e4194685(4194685),
        e4194686(4194686),
        e4194687(4194687),
        e4194688(4194688),
        e4194689(4194689),
        e4194693(4194693),
        e4194694(4194694),
        e4194695(4194695),
        e4194697(4194697),
        e4194698(4194698),
        e4194699(4194699),
        e4194700(4194700),
        e4194701(4194701),
        e4194702(4194702),
        e4194703(4194703),
        e4194704(4194704),
        e4194705(4194705),
        e4194706(4194706),
        e4194714(4194714),
        e4194715(4194715),
        e4194717(4194717),
        e4194718(4194718),
        e4194719(4194719),
        e4194720(4194720),
        e4194721(4194721),
        e4194722(4194722),
        e4194723(4194723),
        e4194724(4194724),
        e4194725(4194725),
        e4194726(4194726),
        e4194727(4194727),
        e4194728(4194728),
        e4194729(4194729),
        e4194730(4194730),
        e4194734(4194734),
        e4194736(4194736),
        e4194737(4194737),
        e4194738(4194738),
        e4194739(4194739),
        e4194740(4194740),
        e4194741(4194741),
        e4194744(4194744),
        e4194745(4194745),
        e4194746(4194746),
        e4194747(4194747),
        e4194748(4194748),
        e4194749(4194749),
        e4194750(4194750),
        e4194751(4194751),
        e4194752(4194752),
        e4194753(4194753),
        e4194754(4194754),
        e4194755(4194755),
        e4194763(4194763),
        e4194764(4194764),
        e4194765(4194765),
        e4194766(4194766),
        e4194767(4194767),
        e4194768(4194768),
        e4194769(4194769),
        e4194770(4194770),
        e4194771(4194771),
        e4194773(4194773),
        e4194774(4194774),
        e4194775(4194775),
        e4194776(4194776),
        e4194777(4194777),
        e4194778(4194778),
        e4194787(4194787),
        e4194788(4194788),
        e4194789(4194789),
        e4194790(4194790),
        e4194791(4194791),
        e4194792(4194792),
        e4194793(4194793),
        e4194794(4194794),
        e4194795(4194795),
        e4194796(4194796),
        e4194797(4194797),
        e4194798(4194798),
        e4194799(4194799),
        e4194800(4194800),
        e4194801(4194801),
        e4194802(4194802),
        e4194803(4194803),
        e4194804(4194804),
        e4194805(4194805),
        e4194806(4194806),
        e4194807(4194807),
        e4194812(4194812),
        e4194828(4194828),
        e4194830(4194830),
        e4194831(4194831),
        e4194832(4194832),
        e4194833(4194833),
        e4194834(4194834),
        e4194835(4194835),
        e4194836(4194836),
        e4194839(4194839),
        e4194840(4194840),
        e4194841(4194841),
        e4194842(4194842),
        e4194843(4194843),
        e4194844(4194844),
        e4194847(4194847),
        e4194848(4194848),
        e4194849(4194849),
        e4194855(4194855),
        e4194856(4194856),
        e4194859(4194859),
        e4194860(4194860),
        e4194861(4194861),
        e4194862(4194862),
        e4194863(4194863),
        e4194864(4194864),
        e4194865(4194865),
        e4194866(4194866),
        e4194867(4194867),
        e4194868(4194868),
        e4194869(4194869),
        e4194871(4194871),
        e4194876(4194876),
        e4194878(4194878),
        e4194879(4194879),
        e4194880(4194880),
        e4194881(4194881),
        e4194883(4194883),
        e4194884(4194884),
        e4194885(4194885),
        e4194886(4194886),
        e4194887(4194887),
        e4194888(4194888),
        e4194889(4194889),
        e4194890(4194890),
        e4194891(4194891),
        e4194892(4194892),
        e4194894(4194894),
        e4194895(4194895),
        e4194896(4194896),
        e4194897(4194897),
        e4194899(4194899),
        e4194900(4194900),
        e4194901(4194901),
        e4194902(4194902),
        e4194903(4194903),
        e4194904(4194904),
        e4194905(4194905),
        e4194906(4194906),
        e4194907(4194907),
        e4194908(4194908),
        e4194909(4194909),
        e4194910(4194910),
        e4194911(4194911),
        e4194918(4194918),
        e4194919(4194919),
        e4194920(4194920),
        e4194921(4194921),
        e4194922(4194922),
        e4194923(4194923),
        e4194924(4194924),
        e4194925(4194925),
        e4194926(4194926),
        e4194927(4194927),
        e4194928(4194928),
        e4194929(4194929),
        e4194930(4194930),
        e4194931(4194931),
        e4194932(4194932),
        e4194933(4194933),
        e4194934(4194934),
        e4194935(4194935),
        e4194936(4194936),
        e4194937(4194937),
        e4194938(4194938),
        e4194939(4194939),
        e4194940(4194940),
        e4194941(4194941),
        e4194942(4194942),
        e4194943(4194943),
        e4194944(4194944),
        e4194945(4194945),
        e4194946(4194946),
        e4194947(4194947),
        e4194948(4194948),
        e4194949(4194949),
        e4194950(4194950),
        e4194951(4194951),
        e4194952(4194952),
        e4194953(4194953),
        e4194954(4194954),
        e4194955(4194955),
        e4194956(4194956),
        e4194957(4194957),
        e4194958(4194958),
        e4194959(4194959),
        e4194960(4194960),
        e4194961(4194961),
        e4194962(4194962),
        e4194963(4194963),
        e4194964(4194964),
        e4194965(4194965),
        e4194966(4194966),
        e4194967(4194967),
        e4194968(4194968),
        e4194969(4194969),
        e4194970(4194970),
        e4194971(4194971),
        e4194972(4194972),
        e4194973(4194973),
        e4194974(4194974),
        e4194975(4194975),
        e4194976(4194976),
        e4194977(4194977),
        e4194978(4194978),
        e4194979(4194979),
        e4194980(4194980),
        e4194981(4194981),
        e4194982(4194982),
        e4194983(4194983),
        e4194984(4194984),
        e4194985(4194985),
        e4194986(4194986),
        e4194987(4194987),
        e4194988(4194988),
        e4194989(4194989),
        e4194990(4194990),
        e4194991(4194991),
        e4194992(4194992),
        e4194993(4194993),
        e4194994(4194994),
        e4194995(4194995),
        e4194996(4194996),
        e4194997(4194997),
        e4195000(4195000),
        e4195001(4195001),
        e4195002(4195002),
        e4195003(4195003),
        e4195004(4195004),
        e4195006(4195006),
        e4195007(4195007),
        e4195008(4195008),
        e4195009(4195009),
        e4195010(4195010),
        e4195011(4195011),
        e4195012(4195012),
        e4195013(4195013),
        e4195014(4195014),
        e4195015(4195015),
        e4195016(4195016),
        e4195017(4195017),
        e4195018(4195018),
        e4195019(4195019),
        e4195020(4195020),
        e4195021(4195021),
        e4195022(4195022),
        e4195023(4195023),
        e4195024(4195024),
        e4195025(4195025),
        e4195026(4195026),
        e4195027(4195027),
        e4195028(4195028),
        e4195029(4195029),
        e4195030(4195030),
        e4195031(4195031),
        e4195032(4195032),
        e4195033(4195033),
        e4195034(4195034),
        e4195036(4195036),
        e4195037(4195037),
        e4195038(4195038),
        e4195039(4195039),
        e4195040(4195040),
        e4195041(4195041),
        e4195042(4195042),
        e4195043(4195043),
        e4195044(4195044),
        e4195045(4195045),
        e4195046(4195046),
        e4195047(4195047),
        e4195048(4195048),
        e4195049(4195049),
        e4195050(4195050),
        e4195051(4195051),
        e4195052(4195052),
        e4195053(4195053),
        e4195054(4195054),
        e4195055(4195055),
        e4195056(4195056),
        e4195057(4195057),
        e4195058(4195058),
        e4195059(4195059),
        e4195060(4195060),
        e4195061(4195061),
        e4195064(4195064),
        e4195065(4195065),
        e4195066(4195066),
        e4195067(4195067),
        e4195068(4195068),
        e4195069(4195069),
        e4195071(4195071),
        e4195072(4195072),
        e4195073(4195073),
        e4195074(4195074),
        e4195075(4195075),
        e4195076(4195076),
        e4195077(4195077),
        e4195078(4195078),
        e4195080(4195080),
        e4195081(4195081),
        e4195082(4195082),
        e4195083(4195083),
        e4195084(4195084),
        e4195085(4195085),
        e4195086(4195086),
        e4195087(4195087),
        e4195088(4195088),
        e4195207(4195207),
        e4195208(4195208),
        e4195209(4195209),
        e4195213(4195213),
        e4195214(4195214),
        e4195215(4195215),
        e4195216(4195216),
        e4195217(4195217),
        e4195218(4195218),
        e4195220(4195220),
        e4195221(4195221),
        e4195222(4195222),
        e4195223(4195223),
        e4195224(4195224),
        e4195225(4195225),
        e4195226(4195226),
        e4195227(4195227),
        e4195228(4195228),
        e4195229(4195229),
        e4195230(4195230),
        e4195231(4195231),
        e4195232(4195232),
        e4195233(4195233),
        e4195234(4195234),
        e4195235(4195235),
        e4195236(4195236),
        e4195237(4195237),
        e4195238(4195238),
        e4195239(4195239),
        e4195242(4195242),
        e4195243(4195243),
        e4195244(4195244),
        e4195245(4195245),
        e4195246(4195246),
        e4195247(4195247),
        e4195248(4195248),
        e4195249(4195249),
        e4195250(4195250),
        e4195251(4195251),
        e4195252(4195252),
        e4195253(4195253),
        e4195254(4195254),
        e4195255(4195255),
        e4195256(4195256),
        e4195257(4195257),
        e4195258(4195258),
        e4195259(4195259),
        e4195260(4195260),
        e4195261(4195261),
        e4195262(4195262),
        e4195263(4195263),
        e4195264(4195264),
        e4195265(4195265),
        e4195266(4195266),
        e4195267(4195267),
        e4195268(4195268),
        e4195269(4195269),
        e4195270(4195270),
        e4195271(4195271),
        e4195272(4195272),
        e4195273(4195273),
        e4195274(4195274),
        e4195275(4195275),
        e4195276(4195276),
        e4195277(4195277),
        e4195278(4195278),
        e4195279(4195279),
        e4195281(4195281),
        e4195282(4195282),
        e4195283(4195283),
        e4195284(4195284),
        e4195285(4195285),
        e4195286(4195286),
        e4195287(4195287),
        e4195288(4195288),
        e4195289(4195289),
        e4195290(4195290),
        e4195291(4195291),
        e4195292(4195292),
        e4195293(4195293),
        e4195294(4195294),
        e4195295(4195295),
        e4195296(4195296),
        e4195297(4195297),
        e4195298(4195298),
        e4195299(4195299),
        e4195300(4195300),
        e4195301(4195301),
        e4195302(4195302),
        e4195303(4195303),
        e4195304(4195304),
        e4195305(4195305),
        e4195306(4195306),
        e4195307(4195307),
        e4195308(4195308),
        e4195309(4195309),
        e4195310(4195310),
        e4195311(4195311),
        e4195312(4195312),
        e4195313(4195313),
        e4195314(4195314),
        e4195315(4195315),
        e4195316(4195316),
        e4195317(4195317),
        e4195318(4195318),
        e4195319(4195319),
        e4195320(4195320),
        e4195321(4195321),
        e4195331(4195331),
        e4195332(4195332),
        e4195333(4195333),
        e4195334(4195334),
        e4195335(4195335),
        e4195336(4195336),
        e4195337(4195337),
        e4195338(4195338),
        e4195339(4195339),
        e4195340(4195340),
        e4195341(4195341),
        e4195342(4195342),
        e4195343(4195343),
        e4195344(4195344),
        e4195345(4195345),
        e4195346(4195346),
        e4195347(4195347),
        e4195348(4195348),
        e4195349(4195349),
        e4195350(4195350),
        e4195351(4195351),
        e4195352(4195352),
        e4195353(4195353),
        e4195354(4195354),
        e4195355(4195355),
        e4195356(4195356),
        e4195357(4195357),
        e4195358(4195358),
        e4195359(4195359),
        e4195360(4195360),
        e4195361(4195361),
        e4195362(4195362),
        e4195363(4195363),
        e4195364(4195364),
        e4195365(4195365),
        e4195366(4195366),
        e4195367(4195367),
        e4195368(4195368),
        e4195369(4195369),
        e4195370(4195370),
        e4195371(4195371),
        e4195372(4195372),
        e4195373(4195373),
        e4195374(4195374),
        e4195375(4195375),
        e4195376(4195376),
        e4195377(4195377),
        e4195378(4195378),
        e4195379(4195379),
        e4195380(4195380),
        e4195381(4195381),
        e4195382(4195382),
        e4195387(4195387),
        e4195388(4195388),
        e4195389(4195389),
        e4195390(4195390),
        e4195391(4195391),
        e4195392(4195392),
        e4195393(4195393),
        e4195394(4195394),
        e4195395(4195395),
        e4195396(4195396),
        e4195397(4195397),
        e4195398(4195398),
        e4195399(4195399),
        e4195400(4195400),
        e4195401(4195401),
        e4195402(4195402),
        e4195403(4195403),
        e4195404(4195404),
        e4195405(4195405),
        e4195406(4195406),
        e4195407(4195407),
        e4195408(4195408),
        e4195409(4195409),
        e4195410(4195410),
        e4195411(4195411),
        e4195412(4195412),
        e4195413(4195413),
        e4195414(4195414),
        e4195415(4195415),
        e4195416(4195416),
        e4195417(4195417),
        e4195418(4195418),
        e4195419(4195419),
        e4195460(4195460),
        e4195461(4195461),
        e4195462(4195462),
        e4195463(4195463),
        e4195464(4195464),
        e4195465(4195465),
        e4195466(4195466),
        e4195467(4195467),
        e4195468(4195468),
        e4195469(4195469),
        e4195470(4195470),
        e4195471(4195471),
        e4195472(4195472),
        e4195473(4195473),
        e4195474(4195474),
        e4195475(4195475),
        e4195476(4195476),
        e4195477(4195477),
        e4195478(4195478),
        e4195479(4195479),
        e4195480(4195480),
        e4195481(4195481),
        e4195482(4195482),
        e4195483(4195483),
        e4195484(4195484),
        e4195485(4195485),
        e4195486(4195486),
        e4195487(4195487),
        e4195488(4195488),
        e4195489(4195489),
        e4195490(4195490),
        e4195491(4195491),
        e4195492(4195492),
        e4195493(4195493),
        e4195494(4195494),
        e4195495(4195495),
        e4195496(4195496),
        e4195497(4195497),
        e4195498(4195498),
        e4195499(4195499),
        e4195500(4195500),
        e4195501(4195501),
        e4195502(4195502),
        e4195503(4195503),
        e4195504(4195504),
        e4195505(4195505),
        e4195506(4195506),
        e4195507(4195507),
        e4195508(4195508),
        e4195509(4195509),
        e4195510(4195510),
        e4195511(4195511),
        e4195512(4195512),
        e4195513(4195513),
        e4195514(4195514),
        e4195515(4195515),
        e4195516(4195516),
        e4195517(4195517),
        e4195518(4195518),
        e4195519(4195519),
        e4195520(4195520),
        e4195521(4195521),
        e4195522(4195522),
        e4195523(4195523),
        e4195524(4195524),
        e4195525(4195525),
        e4195526(4195526),
        e4195527(4195527),
        e4195528(4195528),
        e4195529(4195529),
        e4195530(4195530),
        e4195531(4195531),
        e4195532(4195532),
        e4195533(4195533),
        e4195534(4195534),
        e4195535(4195535),
        e4195536(4195536),
        e4195537(4195537),
        e4195538(4195538),
        e4195539(4195539),
        e4195540(4195540),
        e4195541(4195541),
        e4195542(4195542),
        e4195543(4195543),
        e4195544(4195544),
        e4195545(4195545),
        e4195546(4195546),
        e4195547(4195547),
        e4195548(4195548),
        e4195549(4195549),
        e4195550(4195550),
        e4195551(4195551),
        e4195552(4195552),
        e4195553(4195553),
        e4195554(4195554),
        e4195555(4195555),
        e4195556(4195556),
        e4195557(4195557),
        e4195558(4195558),
        e4195559(4195559),
        e4195560(4195560),
        e4195561(4195561),
        e4195562(4195562),
        e4195563(4195563),
        e4195564(4195564),
        e4195565(4195565),
        e4195566(4195566),
        e4195567(4195567),
        e4195568(4195568),
        e4195571(4195571),
        e4195572(4195572),
        e4195573(4195573),
        e4195574(4195574),
        e4195575(4195575),
        e4195576(4195576),
        e4195577(4195577),
        e4195578(4195578),
        e4195579(4195579),
        e4195580(4195580),
        e4195581(4195581),
        e4195582(4195582),
        e4195583(4195583),
        e4195584(4195584),
        e4195585(4195585),
        e4195586(4195586),
        e4195587(4195587),
        e4195588(4195588),
        e4195592(4195592),
        e4195593(4195593),
        e4195594(4195594),
        e4195595(4195595),
        e4195596(4195596),
        e4195597(4195597),
        e4195598(4195598),
        e4195599(4195599),
        e4195601(4195601),
        e4195602(4195602),
        e4195603(4195603),
        e4195604(4195604),
        e4195605(4195605),
        e4195606(4195606),
        e4195607(4195607),
        e4195615(4195615),
        e4195616(4195616),
        e4195617(4195617),
        e4195655(4195655),
        e4195656(4195656),
        e4195660(4195660),
        e4195661(4195661),
        e4195662(4195662),
        e4195663(4195663),
        e4195664(4195664),
        e4195665(4195665),
        e4195666(4195666),
        e4195667(4195667),
        e4195669(4195669),
        e4195670(4195670),
        e4195671(4195671),
        e4195672(4195672),
        e4195673(4195673),
        e4195674(4195674),
        e4195698(4195698),
        e4195699(4195699),
        e4195700(4195700),
        e4195701(4195701),
        e4195702(4195702),
        e4195703(4195703),
        e4195704(4195704),
        e4195705(4195705),
        e4195706(4195706),
        e4195707(4195707),
        e4195708(4195708),
        e4195709(4195709),
        e4195710(4195710),
        e4195711(4195711),
        e4195712(4195712),
        e4195713(4195713),
        e4195714(4195714),
        e4195715(4195715),
        e4195716(4195716),
        e4195718(4195718),
        e4195721(4195721),
        e4195730(4195730),
        e4195731(4195731),
        e4195732(4195732),
        e4195733(4195733),
        e4195734(4195734),
        e4195735(4195735),
        e4195736(4195736),
        e4195737(4195737),
        e4195738(4195738),
        e4195739(4195739),
        e4195740(4195740),
        e4195741(4195741),
        e4195742(4195742),
        e4195743(4195743),
        e4195744(4195744),
        e4195745(4195745),
        e4195746(4195746),
        e4195747(4195747),
        e4195748(4195748),
        e4195749(4195749),
        e4195750(4195750),
        e4195751(4195751),
        e4195752(4195752),
        e4195753(4195753),
        e4195754(4195754),
        e4195755(4195755),
        e4195756(4195756),
        e4195757(4195757),
        e4195758(4195758),
        e4195759(4195759),
        e4195760(4195760),
        e4195761(4195761),
        e4195762(4195762),
        e4195763(4195763),
        e4195764(4195764),
        e4195765(4195765),
        e4195766(4195766),
        e4195767(4195767),
        e4195768(4195768),
        e4195769(4195769),
        e4195770(4195770),
        e4195771(4195771),
        e4195772(4195772),
        e4195773(4195773),
        e4195774(4195774),
        e4195775(4195775),
        e4195776(4195776),
        e4195777(4195777),
        e4195778(4195778),
        e4195779(4195779),
        e4195786(4195786),
        e4195787(4195787),
        e4195788(4195788),
        e4195789(4195789),
        e4195790(4195790),
        e4195791(4195791),
        e4195792(4195792),
        e4195793(4195793),
        e4195794(4195794),
        e4195795(4195795),
        e4195796(4195796),
        e4195797(4195797),
        e4195798(4195798),
        e4195799(4195799),
        e4195800(4195800),
        e4195801(4195801),
        e4195802(4195802),
        e4195803(4195803),
        e4195804(4195804),
        e4195807(4195807),
        e4195808(4195808),
        e4195809(4195809),
        e4195810(4195810),
        e4195811(4195811),
        e4195812(4195812),
        e4195813(4195813),
        e4195814(4195814),
        e4195815(4195815),
        e4195818(4195818),
        e4195819(4195819),
        e4195820(4195820),
        e4195821(4195821),
        e4195822(4195822),
        e4195823(4195823),
        e4195824(4195824),
        e4195825(4195825),
        e4195826(4195826),
        e4195827(4195827),
        e4195828(4195828),
        e4195829(4195829),
        e4195830(4195830),
        e4195831(4195831),
        e4195832(4195832),
        e4195833(4195833),
        e4195834(4195834),
        e4195835(4195835),
        e4195836(4195836),
        e4195837(4195837),
        e4195838(4195838),
        e4195839(4195839),
        e4195840(4195840),
        e4195841(4195841),
        e4195842(4195842),
        e4195843(4195843),
        e4195844(4195844),
        e4195845(4195845),
        e4195846(4195846),
        e4195847(4195847),
        e4195848(4195848),
        e4195849(4195849),
        e4195850(4195850),
        e4195851(4195851),
        e4195852(4195852),
        e4195853(4195853),
        e4195854(4195854),
        e4195855(4195855),
        e4195856(4195856),
        e4195857(4195857),
        e4195858(4195858),
        e4195859(4195859),
        e4195860(4195860),
        e4195861(4195861),
        e4195862(4195862),
        e4195863(4195863),
        e4195864(4195864),
        e4195865(4195865),
        e4195866(4195866),
        e4195867(4195867),
        e4195868(4195868),
        e4195869(4195869),
        e4195870(4195870),
        e4195871(4195871),
        e4195872(4195872),
        e4195873(4195873),
        e4195874(4195874),
        e4195875(4195875),
        e4195876(4195876),
        e4195877(4195877),
        e4195880(4195880),
        e4195881(4195881),
        e4195882(4195882),
        e4195883(4195883),
        e4195884(4195884),
        e4195885(4195885),
        e4195886(4195886),
        e4195887(4195887),
        e4195888(4195888),
        e4195889(4195889),
        e4195890(4195890),
        e4195891(4195891),
        e4195892(4195892),
        e4195893(4195893),
        e4195894(4195894),
        e4195895(4195895),
        e4195896(4195896),
        e4195897(4195897),
        e4195898(4195898),
        e4195899(4195899),
        e4195900(4195900),
        e4195901(4195901),
        e4195902(4195902),
        e4195903(4195903),
        e4195904(4195904),
        e4195905(4195905),
        e4195906(4195906),
        e4195907(4195907),
        e4195908(4195908),
        e4195909(4195909),
        e4195910(4195910),
        e4195911(4195911),
        e4195912(4195912),
        e4195913(4195913),
        e4195914(4195914),
        e4195915(4195915),
        e4195916(4195916),
        e4195917(4195917),
        e4195918(4195918),
        e4195919(4195919),
        e4195920(4195920),
        e4195921(4195921),
        e4195922(4195922),
        e4195923(4195923),
        e4195924(4195924),
        e4195925(4195925),
        e4195926(4195926),
        e4195927(4195927),
        e4195928(4195928),
        e4195929(4195929),
        e4195930(4195930),
        e4195931(4195931),
        e4195932(4195932),
        e4195933(4195933),
        e4195934(4195934),
        e4195935(4195935),
        e4195936(4195936),
        e4195937(4195937),
        e4195938(4195938),
        e4195939(4195939),
        e4195940(4195940),
        e4195941(4195941),
        e4195942(4195942),
        e4195943(4195943),
        e4195944(4195944),
        e4195945(4195945),
        e4195946(4195946),
        e4195947(4195947),
        e4195948(4195948),
        e4195949(4195949),
        e4195950(4195950),
        e4195951(4195951),
        e4195952(4195952),
        e4195953(4195953),
        e4195956(4195956),
        e4195957(4195957),
        e4195958(4195958),
        e4195959(4195959),
        e4195960(4195960),
        e4195961(4195961),
        e4195962(4195962),
        e4195963(4195963),
        e4195964(4195964),
        e4195965(4195965),
        e4195966(4195966),
        e4195967(4195967),
        e4195968(4195968),
        e4195969(4195969),
        e4195970(4195970),
        e4195971(4195971),
        e4195972(4195972),
        e4195973(4195973),
        e4195976(4195976),
        e4195977(4195977),
        e4195978(4195978),
        e4195979(4195979),
        e4195980(4195980),
        e4195981(4195981),
        e4195982(4195982),
        e4195983(4195983),
        e4195984(4195984),
        e4195985(4195985),
        e4195986(4195986),
        e4195987(4195987),
        e4195988(4195988),
        e4195989(4195989),
        e4195991(4195991),
        e4195992(4195992),
        e4195993(4195993),
        e4195994(4195994),
        e4195995(4195995),
        e4195996(4195996),
        e4195997(4195997),
        e4195998(4195998),
        e4195999(4195999),
        e4196000(4196000),
        e4196001(4196001),
        e4196002(4196002),
        e4196003(4196003),
        e4196004(4196004),
        e4196005(4196005),
        e4196006(4196006),
        e4196007(4196007),
        e4196008(4196008),
        e4196009(4196009),
        e4196010(4196010),
        e4196011(4196011),
        e4196012(4196012),
        e4196013(4196013),
        e4196014(4196014),
        e4196015(4196015),
        e4196016(4196016),
        e4196017(4196017),
        e4196018(4196018),
        e4196019(4196019),
        e4196020(4196020),
        e4196021(4196021),
        e4196022(4196022),
        e4196023(4196023),
        e4196024(4196024),
        e4196025(4196025),
        e4196026(4196026),
        e4196027(4196027),
        e4196028(4196028),
        e4196029(4196029),
        e4196030(4196030),
        e4196031(4196031),
        e4196032(4196032),
        e4196033(4196033),
        e4196034(4196034),
        e4196035(4196035),
        e4196036(4196036),
        e4196041(4196041),
        e4196042(4196042),
        e4196045(4196045),
        e4196047(4196047),
        e4196048(4196048),
        e4196049(4196049),
        e4196051(4196051),
        e4196052(4196052),
        e4196055(4196055),
        e4196056(4196056),
        e4196060(4196060),
        e4196061(4196061),
        e4196062(4196062),
        e4196063(4196063),
        e4196065(4196065),
        e4196066(4196066),
        e4196067(4196067),
        e4196068(4196068),
        e4196069(4196069),
        e4196070(4196070),
        e4196071(4196071),
        e4196072(4196072),
        e4196073(4196073),
        e4196074(4196074),
        e4196075(4196075),
        e4196076(4196076),
        e4196077(4196077),
        e4196078(4196078),
        e4196079(4196079),
        e4196080(4196080),
        e4196081(4196081),
        e4196082(4196082),
        e4196083(4196083),
        e4196084(4196084),
        e4196085(4196085),
        e4196086(4196086),
        e4196087(4196087),
        e4196088(4196088),
        e4196089(4196089),
        e4196090(4196090),
        e4196091(4196091),
        e4196092(4196092),
        e4196093(4196093),
        e4196094(4196094),
        e4196095(4196095),
        e4196096(4196096),
        e4196097(4196097),
        e4196098(4196098),
        e4196099(4196099),
        e4196100(4196100),
        e4196101(4196101),
        e4196102(4196102),
        e4196103(4196103),
        e4196104(4196104),
        e4196105(4196105),
        e4196106(4196106),
        e4196107(4196107),
        e4196108(4196108),
        e4196109(4196109),
        e4196110(4196110),
        e4196111(4196111),
        e4196112(4196112),
        e4196113(4196113),
        e4196114(4196114),
        e4196115(4196115),
        e4196116(4196116),
        e4196117(4196117),
        e4196118(4196118),
        e4196119(4196119),
        e4196120(4196120),
        e4196121(4196121),
        e4196122(4196122),
        e4196123(4196123),
        e4196124(4196124),
        e4196125(4196125),
        e4196126(4196126),
        e4196127(4196127),
        e4196128(4196128),
        e4196129(4196129),
        e4196130(4196130),
        e4196131(4196131),
        e4196132(4196132),
        e4196133(4196133),
        e4196134(4196134),
        e4196135(4196135),
        e4196136(4196136),
        e4196137(4196137),
        e4196138(4196138),
        e4196139(4196139),
        e4196140(4196140),
        e4196141(4196141),
        e4196142(4196142),
        e4196143(4196143),
        e4196144(4196144),
        e4196145(4196145),
        e4196146(4196146),
        e4196147(4196147),
        e4196149(4196149),
        e4196150(4196150),
        e4196151(4196151),
        e4196152(4196152),
        e4196153(4196153),
        e4196154(4196154),
        e4196155(4196155),
        e4196156(4196156),
        e4196157(4196157),
        e4196158(4196158),
        e4196159(4196159),
        e4196160(4196160),
        e4196161(4196161),
        e4196162(4196162),
        e4196163(4196163),
        e4196164(4196164),
        e4196165(4196165),
        e4196168(4196168),
        e4196169(4196169),
        e4196170(4196170),
        e4196171(4196171),
        e4196172(4196172),
        e4196173(4196173),
        e4196174(4196174),
        e4196175(4196175),
        e4196176(4196176),
        e4196177(4196177),
        e4196178(4196178),
        e4196179(4196179),
        e4196180(4196180),
        e4196181(4196181),
        e4196182(4196182),
        e4196183(4196183),
        e4196184(4196184),
        e4196185(4196185),
        e4196186(4196186),
        e4196187(4196187),
        e4196188(4196188),
        e4196189(4196189),
        e4196190(4196190),
        e4196191(4196191),
        e4196192(4196192),
        e4196193(4196193),
        e4196194(4196194),
        e4196195(4196195),
        e4196196(4196196),
        e4196197(4196197),
        e4196198(4196198),
        e4196199(4196199),
        e4196200(4196200),
        e4196201(4196201),
        e4196202(4196202),
        e4196203(4196203),
        e4196204(4196204),
        e4196205(4196205),
        e4196206(4196206),
        e4196207(4196207),
        e4196208(4196208),
        e4196209(4196209),
        e4196210(4196210),
        e4196211(4196211),
        e4196214(4196214),
        e4196215(4196215),
        e4196216(4196216),
        e4196217(4196217),
        e4196218(4196218),
        e4196219(4196219),
        e4196220(4196220),
        e4196221(4196221),
        e4196222(4196222),
        e4196223(4196223),
        e4196224(4196224),
        e4196225(4196225),
        e4196226(4196226),
        e4196227(4196227),
        e4196228(4196228),
        e4196229(4196229),
        e4196230(4196230),
        e4196231(4196231),
        e4196232(4196232),
        e4196233(4196233),
        e4196234(4196234),
        e4196235(4196235),
        e4196236(4196236),
        e4196237(4196237),
        e4196241(4196241),
        e4196242(4196242),
        e4196243(4196243),
        e4196244(4196244),
        e4196245(4196245),
        e4196246(4196246),
        e4196247(4196247),
        e4196249(4196249),
        e4196250(4196250),
        e4196251(4196251),
        e4196252(4196252),
        e4196253(4196253),
        e4196254(4196254),
        e4196255(4196255),
        e4196256(4196256),
        e4196257(4196257),
        e4196258(4196258),
        e4196259(4196259),
        e4196260(4196260),
        e4196261(4196261),
        e4196262(4196262),
        e4196263(4196263),
        e4196264(4196264),
        e4196265(4196265),
        e4196266(4196266),
        e4196267(4196267),
        e4196268(4196268),
        e4196269(4196269),
        e4196270(4196270),
        e4196271(4196271),
        e4196272(4196272),
        e4196273(4196273),
        e4196274(4196274),
        e4196275(4196275),
        e4196276(4196276),
        e4196277(4196277),
        e4196278(4196278),
        e4196279(4196279),
        e4196280(4196280),
        e4196281(4196281),
        e4196282(4196282),
        e4196283(4196283),
        e4196284(4196284),
        e4196285(4196285),
        e4196286(4196286),
        e4196287(4196287),
        e4196288(4196288),
        e4196289(4196289),
        e4196290(4196290),
        e4196291(4196291),
        e4196292(4196292),
        e4196293(4196293),
        e4196294(4196294),
        e4196295(4196295),
        e4196296(4196296),
        e4196297(4196297),
        e4196298(4196298),
        e4196299(4196299),
        e4196300(4196300),
        e4196301(4196301),
        e4196302(4196302),
        e4196303(4196303),
        e4196304(4196304),
        e4196305(4196305),
        e4196306(4196306),
        e4196307(4196307),
        e4196308(4196308),
        e4196309(4196309),
        e4196310(4196310),
        e4196317(4196317),
        e4196318(4196318),
        e4196319(4196319),
        e4196320(4196320),
        e4196321(4196321),
        e4196322(4196322),
        e4196323(4196323),
        e4196324(4196324),
        e4196325(4196325),
        e4196326(4196326),
        e4196327(4196327),
        e4196328(4196328),
        e4196329(4196329),
        e4196330(4196330),
        e4196331(4196331),
        e4196332(4196332),
        e4196333(4196333),
        e4196334(4196334),
        e4196335(4196335),
        e4196336(4196336),
        e4196337(4196337),
        e4196338(4196338),
        e4196339(4196339),
        e4196340(4196340),
        e4196341(4196341),
        e4196342(4196342),
        e4196343(4196343),
        e4196344(4196344),
        e4196345(4196345),
        e4196346(4196346),
        e4196347(4196347),
        e4196348(4196348),
        e4196349(4196349),
        e4196350(4196350),
        e4196354(4196354),
        e4196355(4196355),
        e4196356(4196356),
        e4196357(4196357),
        e4196358(4196358),
        e4196359(4196359),
        e4196360(4196360),
        e4196361(4196361),
        e4196362(4196362),
        e4196363(4196363),
        e4196364(4196364),
        e4196365(4196365),
        e4196366(4196366),
        e4196367(4196367),
        e4196368(4196368),
        e4196369(4196369),
        e4196370(4196370),
        e4196371(4196371),
        e4196372(4196372),
        e4196373(4196373),
        e4196374(4196374),
        e4196375(4196375),
        e4196376(4196376),
        e4196377(4196377),
        e4196378(4196378),
        e4196379(4196379),
        e4196380(4196380),
        e4196381(4196381),
        e4196382(4196382),
        e4196383(4196383),
        e4196384(4196384),
        e4196385(4196385),
        e4196386(4196386),
        e4196387(4196387),
        e4196388(4196388),
        e4196389(4196389),
        e4196390(4196390),
        e4196391(4196391),
        e4196392(4196392),
        e4196393(4196393),
        e4196394(4196394),
        e4196395(4196395),
        e4196396(4196396),
        e4196397(4196397),
        e4196398(4196398),
        e4196399(4196399),
        e4196400(4196400),
        e4196401(4196401),
        e4196402(4196402),
        e4196403(4196403),
        e4196404(4196404),
        e4196405(4196405),
        e4196406(4196406),
        e4196407(4196407),
        e4196408(4196408),
        e4196409(4196409),
        e4196410(4196410),
        e4196411(4196411),
        e4196412(4196412),
        e4196413(4196413),
        e4196414(4196414),
        e4196415(4196415),
        e4196416(4196416),
        e4196417(4196417),
        e4196418(4196418),
        e4196419(4196419),
        e4196420(4196420),
        e4196421(4196421),
        e4196422(4196422),
        e4196423(4196423),
        e4196424(4196424),
        e4196425(4196425),
        e4196426(4196426),
        e4196427(4196427),
        e4196428(4196428),
        e4196429(4196429),
        e4196430(4196430),
        e4196431(4196431),
        e4196432(4196432),
        e4196433(4196433),
        e4196434(4196434),
        e4196435(4196435),
        e4196436(4196436),
        e4196437(4196437),
        e4196438(4196438),
        e4196439(4196439),
        e4196440(4196440),
        e4196441(4196441),
        e4196442(4196442),
        e4196443(4196443),
        e4196444(4196444),
        e4196445(4196445),
        e4196446(4196446),
        e4196447(4196447),
        e4196448(4196448),
        e4196449(4196449),
        e4196450(4196450),
        e4196451(4196451),
        e4196452(4196452),
        e4196453(4196453),
        e4196454(4196454),
        e4196455(4196455),
        e4196456(4196456),
        e4196457(4196457),
        e4196458(4196458),
        e4196459(4196459),
        e4196460(4196460),
        e4196461(4196461),
        e4196462(4196462),
        e4196463(4196463),
        e4196464(4196464),
        e4196465(4196465),
        e4196466(4196466),
        e4196467(4196467),
        e4196468(4196468),
        e4196469(4196469),
        e4196470(4196470),
        e4196471(4196471),
        e4196472(4196472),
        e4196474(4196474),
        e4196475(4196475),
        e4196477(4196477),
        e4196478(4196478),
        e4196480(4196480),
        e4196481(4196481),
        e4196483(4196483),
        e4196484(4196484),
        e4196485(4196485),
        e4196486(4196486),
        e4196487(4196487),
        e4196488(4196488),
        e4196489(4196489),
        e4196490(4196490),
        e4196491(4196491),
        e4196492(4196492),
        e4196493(4196493),
        e4196494(4196494),
        e4196495(4196495),
        e4196496(4196496),
        e4196497(4196497),
        e4196498(4196498),
        e4196499(4196499),
        e4196500(4196500),
        e4196501(4196501),
        e4196502(4196502),
        e4196503(4196503),
        e4196504(4196504),
        e4196505(4196505),
        e4196506(4196506),
        e4196507(4196507),
        e4196508(4196508),
        e4196509(4196509),
        e4196510(4196510),
        e4196511(4196511),
        e4196512(4196512),
        e4196513(4196513),
        e4196514(4196514),
        e4196515(4196515),
        e4196516(4196516),
        e4196517(4196517),
        e4196518(4196518),
        e4196519(4196519),
        e4196520(4196520),
        e4196521(4196521),
        e4196522(4196522),
        e4196523(4196523),
        e4196524(4196524),
        e4196525(4196525),
        e4196526(4196526),
        e4196527(4196527),
        e4196528(4196528),
        e4196529(4196529),
        e4196530(4196530),
        e4196531(4196531),
        e4196532(4196532),
        e4196533(4196533),
        e4196534(4196534),
        e4196535(4196535),
        e4196536(4196536),
        e4196537(4196537),
        e4196538(4196538),
        e4196539(4196539),
        e4196540(4196540),
        e4196541(4196541),
        e4196542(4196542),
        e4196543(4196543),
        e4196544(4196544),
        e4196545(4196545),
        e4196546(4196546),
        e4196555(4196555),
        e4196556(4196556),
        e4196557(4196557),
        e4196558(4196558),
        e4196559(4196559),
        e4196560(4196560),
        e4196561(4196561),
        e4196562(4196562),
        e4196563(4196563),
        e4196564(4196564),
        e4196565(4196565),
        e4196566(4196566),
        e4196567(4196567),
        e4196568(4196568),
        e4196569(4196569),
        e4196570(4196570),
        e4196571(4196571),
        e4196572(4196572),
        e4196573(4196573),
        e4196574(4196574),
        e4196575(4196575),
        e4196576(4196576),
        e4196577(4196577),
        e4196578(4196578),
        e4196579(4196579),
        e4196580(4196580),
        e4196581(4196581),
        e4196582(4196582),
        e4196583(4196583),
        e4196584(4196584),
        e4196585(4196585),
        e4196586(4196586),
        e4196587(4196587),
        e4196588(4196588),
        e4196589(4196589),
        e4196590(4196590),
        e4196591(4196591),
        e4196592(4196592),
        e4196593(4196593),
        e4196594(4196594),
        e4196595(4196595),
        e4196596(4196596),
        e4196597(4196597),
        e4196598(4196598),
        e4196599(4196599),
        e4196600(4196600),
        e4196601(4196601),
        e4196602(4196602),
        e4196603(4196603),
        e4196604(4196604),
        e4196605(4196605),
        e4196606(4196606),
        e4196607(4196607),
        e4196608(4196608),
        e4196609(4196609),
        e4196610(4196610),
        e4196611(4196611),
        e4196612(4196612),
        e4196613(4196613),
        e4196614(4196614),
        e4196619(4196619),
        e4196620(4196620),
        e4196621(4196621),
        e4196622(4196622),
        e4196623(4196623),
        e4196624(4196624),
        e4196625(4196625),
        e4196626(4196626),
        e4196627(4196627),
        e4196628(4196628),
        e4196629(4196629),
        e4196630(4196630),
        e4196631(4196631),
        e4196632(4196632),
        e4196633(4196633),
        e4196634(4196634),
        e4196635(4196635),
        e4196636(4196636),
        e4196637(4196637),
        e4196638(4196638),
        e4196639(4196639),
        e4196640(4196640),
        e4196641(4196641),
        e4196642(4196642),
        e4196643(4196643),
        e4196644(4196644),
        e4196645(4196645),
        e4196646(4196646),
        e4196647(4196647),
        e4196648(4196648),
        e4196649(4196649),
        e4196650(4196650),
        e4196651(4196651),
        e4196652(4196652),
        e4196653(4196653),
        e4196654(4196654),
        e4196655(4196655),
        e4196656(4196656),
        e4196657(4196657),
        e4196658(4196658),
        e4196659(4196659),
        e4196660(4196660),
        e4196661(4196661),
        e4196662(4196662),
        e4196663(4196663),
        e4196664(4196664),
        e4196665(4196665),
        e4196666(4196666),
        e4196667(4196667),
        e4196668(4196668),
        e4196669(4196669),
        e4196670(4196670),
        e4196671(4196671),
        e4196672(4196672),
        e4196673(4196673),
        e4196674(4196674),
        e4196675(4196675),
        e4196676(4196676),
        e4196677(4196677),
        e4196678(4196678),
        e4196679(4196679),
        e4196680(4196680),
        e4196681(4196681),
        e4196682(4196682),
        e4196683(4196683),
        e4196684(4196684),
        e4196685(4196685),
        e4196686(4196686),
        e4196687(4196687),
        e4196688(4196688),
        e4196689(4196689),
        e4196690(4196690),
        e4196691(4196691),
        e4196692(4196692),
        e4196693(4196693),
        e4196694(4196694),
        e4196695(4196695),
        e4196696(4196696),
        e4196697(4196697),
        e4196698(4196698),
        e4196699(4196699),
        e4196700(4196700),
        e4196701(4196701),
        e4196702(4196702),
        e4196703(4196703),
        e4196704(4196704),
        e4196705(4196705),
        e4196706(4196706),
        e4196707(4196707),
        e4196708(4196708),
        e4196709(4196709),
        e4196710(4196710),
        e4196711(4196711),
        e4196712(4196712),
        e4196713(4196713),
        e4196714(4196714),
        e4196715(4196715),
        e4196716(4196716),
        e4196717(4196717),
        e4196718(4196718),
        e4196719(4196719),
        e4196720(4196720),
        e4196721(4196721),
        e4196722(4196722),
        e4196723(4196723),
        e4196724(4196724),
        e4196725(4196725),
        e4196726(4196726),
        e4196727(4196727),
        e4196728(4196728),
        e4196729(4196729),
        e4196730(4196730),
        e4196731(4196731),
        e4196732(4196732),
        e4196733(4196733),
        e4196734(4196734),
        e4196735(4196735),
        e4196736(4196736),
        e4196737(4196737),
        e4196738(4196738),
        e4196739(4196739),
        e4196740(4196740),
        e4196741(4196741),
        e4196742(4196742),
        e4196743(4196743),
        e4196744(4196744),
        e4196745(4196745),
        e4196746(4196746),
        e4196747(4196747),
        e4196748(4196748),
        e4196749(4196749),
        e4196750(4196750),
        e4196751(4196751),
        e4196752(4196752),
        e4196753(4196753),
        e4196754(4196754),
        e4196755(4196755),
        e4196756(4196756),
        e4196757(4196757),
        e4196758(4196758),
        e4196759(4196759),
        e4196760(4196760),
        e4196761(4196761),
        e4196762(4196762),
        e4196763(4196763),
        e4196764(4196764),
        e4196765(4196765),
        e4196766(4196766),
        e4196767(4196767),
        e4196768(4196768),
        e4196769(4196769),
        e4196770(4196770),
        e4196771(4196771),
        e4196772(4196772),
        e4196773(4196773),
        e4196774(4196774),
        e4196775(4196775),
        e4196776(4196776),
        e4196777(4196777),
        e4196778(4196778),
        e4196779(4196779),
        e4196780(4196780),
        e4196781(4196781),
        e4196785(4196785),
        e4196787(4196787),
        e4196788(4196788),
        e4196789(4196789),
        e4196790(4196790),
        e4196791(4196791),
        e4196792(4196792),
        e4196793(4196793),
        e4196794(4196794),
        e4196795(4196795),
        e4196796(4196796),
        e4196797(4196797),
        e4196798(4196798),
        e4196799(4196799),
        e4196800(4196800),
        e4196801(4196801),
        e4196802(4196802),
        e4196803(4196803),
        e4196804(4196804),
        e4196805(4196805),
        e4196806(4196806),
        e4196807(4196807),
        e4196808(4196808),
        e4196809(4196809),
        e4196810(4196810),
        e4196811(4196811),
        e4196812(4196812),
        e4196813(4196813),
        e4196814(4196814),
        e4196815(4196815),
        e4196816(4196816),
        e4196817(4196817),
        e4196818(4196818),
        e4196819(4196819),
        e4196820(4196820),
        e4196821(4196821),
        e4196822(4196822),
        e4196823(4196823),
        e4196824(4196824),
        e4196825(4196825),
        e4196826(4196826),
        e4196827(4196827),
        e4196828(4196828),
        e4196829(4196829),
        e4196830(4196830),
        e4196831(4196831),
        e4196832(4196832),
        e4196833(4196833),
        e4196834(4196834),
        e4196835(4196835),
        e4196836(4196836),
        e4196837(4196837),
        e4196838(4196838),
        e4196839(4196839),
        e4196840(4196840),
        e4196841(4196841),
        e4196842(4196842),
        e4196843(4196843),
        e4196844(4196844),
        e4196845(4196845),
        e4196846(4196846),
        e4196847(4196847),
        e4196848(4196848),
        e4196849(4196849),
        e4196850(4196850),
        e4196851(4196851),
        e4196852(4196852),
        e4196853(4196853),
        e4196854(4196854),
        e4196855(4196855),
        e4196856(4196856),
        e4196857(4196857),
        e4196858(4196858),
        e4196859(4196859),
        e4196860(4196860),
        e4196861(4196861),
        e4196862(4196862),
        e4196863(4196863),
        e4196864(4196864),
        e4196865(4196865),
        e4196866(4196866),
        e4196867(4196867),
        e4196868(4196868),
        e4196869(4196869),
        e4196870(4196870),
        e4196871(4196871),
        e4196872(4196872),
        e4196873(4196873),
        e4196874(4196874),
        e4196875(4196875),
        e4196876(4196876),
        e4196877(4196877),
        e4196878(4196878),
        e4196879(4196879),
        e4196880(4196880),
        e4196881(4196881),
        e4196882(4196882),
        e4196883(4196883),
        e4196884(4196884),
        e4196885(4196885),
        e4196886(4196886),
        e4196887(4196887),
        e4196888(4196888),
        e4196889(4196889),
        e4196890(4196890),
        e4196891(4196891),
        e4196892(4196892),
        e4196893(4196893),
        e4196894(4196894),
        e4196895(4196895),
        e4196896(4196896),
        e4196897(4196897),
        e4196898(4196898),
        e4196899(4196899),
        e4196900(4196900),
        e4196901(4196901),
        e4196902(4196902),
        e4196903(4196903),
        e4196904(4196904),
        e4196905(4196905),
        e4196906(4196906),
        e4196907(4196907),
        e4196908(4196908),
        e4196909(4196909),
        e4196910(4196910),
        e4196911(4196911),
        e4196912(4196912),
        e4196913(4196913),
        e4196914(4196914),
        e4196915(4196915),
        e4196916(4196916),
        e4196917(4196917),
        e4196918(4196918),
        e4196919(4196919),
        e4196920(4196920),
        e4196921(4196921),
        e4196922(4196922),
        e4196923(4196923),
        e4196924(4196924),
        e4196925(4196925),
        e4196926(4196926),
        e4196927(4196927),
        e4196928(4196928),
        e4196929(4196929),
        e4196930(4196930),
        e4196931(4196931),
        e4196932(4196932),
        e4196933(4196933),
        e4196934(4196934),
        e4196935(4196935),
        e4196936(4196936),
        e4196937(4196937),
        e4196938(4196938),
        e4196939(4196939),
        e4196940(4196940),
        e4196941(4196941),
        e4196942(4196942),
        e4196943(4196943),
        e4196944(4196944),
        e4196945(4196945),
        e4196946(4196946),
        e4196947(4196947),
        e4196948(4196948),
        e4196949(4196949),
        e4196950(4196950),
        e4196951(4196951),
        e4196952(4196952),
        e4196953(4196953),
        e4196954(4196954),
        e4196955(4196955),
        e4196956(4196956),
        e4196957(4196957),
        e4196958(4196958),
        e4196959(4196959),
        e4196960(4196960),
        e4196961(4196961),
        e4196962(4196962),
        e4196963(4196963),
        e4196964(4196964),
        e4196965(4196965),
        e4196966(4196966),
        e4196967(4196967),
        e4196968(4196968),
        e4196969(4196969),
        e4196970(4196970),
        e4196971(4196971),
        e4196972(4196972),
        e4196973(4196973),
        e4196974(4196974),
        e4196975(4196975),
        e4196976(4196976),
        e4196977(4196977),
        e4196978(4196978),
        e4196979(4196979),
        e4196980(4196980),
        e4196981(4196981),
        e4196982(4196982),
        e4196983(4196983),
        e4196984(4196984),
        e4196985(4196985),
        e4196986(4196986),
        e4196987(4196987),
        e4196988(4196988),
        e4196989(4196989),
        e4196990(4196990),
        e4196991(4196991),
        e4196992(4196992),
        e4196993(4196993),
        e4196994(4196994),
        e4196995(4196995),
        e4196996(4196996),
        e4196997(4196997),
        e4196998(4196998),
        e4196999(4196999),
        e4197000(4197000),
        e4197001(4197001),
        e4197002(4197002),
        e4197003(4197003),
        e4197004(4197004),
        e4197005(4197005),
        e4197006(4197006),
        e4197007(4197007),
        e4197008(4197008),
        e4197009(4197009),
        e4197010(4197010),
        e4197011(4197011),
        e4197012(4197012),
        e4197013(4197013),
        e4197014(4197014),
        e4197015(4197015),
        e4197016(4197016),
        e4197017(4197017),
        e4197018(4197018),
        e4197019(4197019),
        e4197020(4197020),
        e4197021(4197021),
        e4197022(4197022),
        e4197023(4197023),
        e4197024(4197024),
        e4197025(4197025),
        e4197026(4197026),
        e4197027(4197027),
        e4197028(4197028),
        e4197029(4197029),
        e4197030(4197030),
        e4197031(4197031),
        e4197032(4197032),
        e4197033(4197033),
        e4197034(4197034),
        e4197035(4197035),
        e4197036(4197036),
        e4197037(4197037),
        e4197038(4197038),
        e4197039(4197039),
        e4197040(4197040),
        e4197041(4197041),
        e4197042(4197042),
        e4197043(4197043),
        e4197044(4197044),
        e4197045(4197045),
        e4197046(4197046),
        e4197047(4197047),
        e4197048(4197048),
        e4197049(4197049),
        e4197050(4197050),
        e4197051(4197051),
        e4197052(4197052),
        e4197053(4197053),
        e4197054(4197054),
        e4197055(4197055),
        e4197056(4197056),
        e4197057(4197057),
        e4197058(4197058),
        e4197059(4197059),
        e4197060(4197060),
        e4197061(4197061),
        e4197062(4197062),
        e4197063(4197063),
        e4197064(4197064),
        e4197065(4197065),
        e4197066(4197066),
        e4197067(4197067),
        e4197068(4197068),
        e4197069(4197069),
        e4197070(4197070),
        e4197071(4197071),
        e4197072(4197072),
        e4197073(4197073),
        e4197074(4197074),
        e4197075(4197075),
        e4197076(4197076),
        e4197077(4197077),
        e4197078(4197078),
        e4197079(4197079),
        e4197080(4197080),
        e4197081(4197081),
        e4197082(4197082),
        e4197083(4197083),
        e4197084(4197084),
        e4197085(4197085),
        e4197086(4197086),
        e4197087(4197087),
        e4197088(4197088),
        e4197089(4197089),
        e4197090(4197090),
        e4197091(4197091),
        e4197092(4197092),
        e4197093(4197093),
        e4197094(4197094),
        e4197095(4197095),
        e4197096(4197096),
        e4197097(4197097),
        e4197098(4197098),
        e4197099(4197099),
        e4197100(4197100),
        e4197101(4197101),
        e4197102(4197102),
        e4197103(4197103),
        e4197104(4197104),
        e4197105(4197105),
        e4197106(4197106),
        e4197107(4197107),
        e4197108(4197108),
        e4197109(4197109),
        e4197110(4197110),
        e4197111(4197111),
        e4197112(4197112),
        e4197113(4197113),
        e4197114(4197114),
        e4197115(4197115),
        e4197116(4197116),
        e4197117(4197117),
        e4197118(4197118),
        e4197119(4197119),
        e4197120(4197120),
        e4197121(4197121),
        e4197122(4197122),
        e4197123(4197123),
        e4197124(4197124),
        e4197125(4197125),
        e4197126(4197126),
        e4197127(4197127),
        e4197128(4197128),
        e4197129(4197129),
        e4197130(4197130),
        e4197131(4197131),
        e4197132(4197132),
        e4197133(4197133),
        e4197134(4197134),
        e4197135(4197135),
        e4197136(4197136),
        e4197137(4197137),
        e4197138(4197138),
        e4197139(4197139),
        e4197140(4197140),
        e4197141(4197141),
        e4197142(4197142),
        e4197143(4197143),
        e4197144(4197144),
        e4197145(4197145),
        e4197146(4197146),
        e4197147(4197147),
        e4197148(4197148),
        e4197149(4197149),
        e4197150(4197150),
        e4197151(4197151),
        e4197152(4197152),
        e4197153(4197153),
        e4197154(4197154),
        e4197155(4197155),
        e4197156(4197156),
        e4197157(4197157),
        e4197158(4197158),
        e4197159(4197159),
        e4197160(4197160),
        e4197161(4197161),
        e4197162(4197162),
        e4197163(4197163),
        e4197164(4197164),
        e4197165(4197165),
        e4197166(4197166),
        e4197167(4197167),
        e4197168(4197168),
        e4197169(4197169),
        e4197170(4197170),
        e4197171(4197171),
        e4197172(4197172),
        e4197173(4197173),
        e4197174(4197174),
        e4197175(4197175),
        e4197176(4197176),
        e4197177(4197177),
        e4197178(4197178),
        e4197179(4197179),
        e4197180(4197180),
        e4197181(4197181),
        e4197182(4197182),
        e4197183(4197183),
        e4197184(4197184),
        e4197185(4197185),
        e4197186(4197186),
        e4197187(4197187),
        e4197188(4197188),
        e4197189(4197189),
        e4197190(4197190),
        e4197191(4197191),
        e4197192(4197192),
        e4197193(4197193),
        e4197194(4197194),
        e4197195(4197195),
        e4197196(4197196),
        e4197197(4197197),
        e4197198(4197198),
        e4197199(4197199),
        e4197200(4197200),
        e4197201(4197201),
        e4197202(4197202),
        e4197203(4197203),
        e4197204(4197204),
        e4197205(4197205),
        e4197206(4197206),
        e4197207(4197207),
        e4197208(4197208),
        e4197209(4197209),
        e4197210(4197210),
        e4197211(4197211),
        e4197212(4197212),
        e4197213(4197213),
        e4197214(4197214),
        e4197215(4197215),
        e4197216(4197216),
        e4197217(4197217),
        e4197218(4197218),
        e4197219(4197219),
        e4197220(4197220),
        e4197221(4197221),
        e4197222(4197222),
        e4197223(4197223),
        e4197224(4197224),
        e4197225(4197225),
        e4197226(4197226),
        e4197227(4197227),
        e4197228(4197228),
        e4197229(4197229),
        e4197230(4197230),
        e4197231(4197231),
        e4197232(4197232),
        e4197233(4197233),
        e4197234(4197234),
        e4197235(4197235),
        e4197236(4197236),
        e4197237(4197237),
        e4197238(4197238),
        e4197239(4197239),
        e4197240(4197240),
        e4197241(4197241),
        e4197242(4197242),
        e4197243(4197243),
        e4197244(4197244),
        e4197245(4197245),
        e4197246(4197246),
        e4197247(4197247),
        e4197248(4197248),
        e4197249(4197249),
        e4197250(4197250),
        e4197251(4197251),
        e4197252(4197252),
        e4197253(4197253),
        e4197254(4197254),
        e4197255(4197255),
        e4197256(4197256),
        e4197257(4197257),
        e4197258(4197258),
        e4197259(4197259),
        e4197260(4197260),
        e4197261(4197261),
        e4197262(4197262),
        e4197263(4197263),
        e4197264(4197264),
        e4197265(4197265),
        e4197266(4197266),
        e4197267(4197267),
        e4197268(4197268),
        e4197269(4197269),
        e4197270(4197270),
        e4197271(4197271),
        e4197272(4197272),
        e4197273(4197273),
        e4197274(4197274),
        e4197275(4197275),
        e4197276(4197276),
        e4197277(4197277),
        e4197278(4197278),
        e4197279(4197279),
        e4197280(4197280),
        e4197281(4197281),
        e4197282(4197282),
        e4197283(4197283),
        e4197284(4197284),
        e4197285(4197285),
        e4197286(4197286),
        e4197287(4197287),
        e4197288(4197288),
        e4197289(4197289),
        e4197290(4197290),
        e4197291(4197291),
        e4197292(4197292),
        e4197293(4197293),
        e4197294(4197294),
        e4197295(4197295),
        e4197296(4197296),
        e4197297(4197297),
        e4197298(4197298),
        e4197299(4197299),
        e4197300(4197300),
        e4197301(4197301),
        e4197302(4197302),
        e4197303(4197303),
        e4197304(4197304),
        e4197305(4197305),
        e4197306(4197306),
        e4197307(4197307),
        e4197308(4197308),
        e4197309(4197309),
        e4197310(4197310),
        e4197311(4197311),
        e4197312(4197312),
        e4197313(4197313),
        e4197314(4197314),
        e4197315(4197315),
        e4197316(4197316),
        e4197317(4197317),
        e4197318(4197318),
        e4197319(4197319),
        e4197320(4197320),
        e4197321(4197321),
        e4197322(4197322),
        e4197323(4197323),
        e4197324(4197324),
        e4197325(4197325),
        e4197326(4197326),
        e4197327(4197327),
        e4197328(4197328),
        e4197329(4197329),
        e4197330(4197330),
        e4197331(4197331),
        e4197332(4197332),
        e4197333(4197333),
        e4197334(4197334),
        e4197335(4197335),
        e4197336(4197336),
        e4197337(4197337),
        e4197338(4197338),
        e4197339(4197339),
        e4197340(4197340),
        e4197341(4197341),
        e4197342(4197342),
        e4197343(4197343),
        e4197344(4197344),
        e4197345(4197345),
        e4197346(4197346),
        e4197347(4197347),
        e4197348(4197348),
        e4197349(4197349),
        e4197350(4197350),
        e4197351(4197351),
        e4197352(4197352),
        e4197353(4197353),
        e4197354(4197354),
        e4197355(4197355),
        e4197356(4197356),
        e4197357(4197357),
        e4197358(4197358),
        e4197359(4197359),
        e4197360(4197360),
        e4197361(4197361),
        e4197362(4197362),
        e4197363(4197363),
        e4197364(4197364),
        e4197365(4197365),
        e4197366(4197366),
        e4197367(4197367),
        e4197368(4197368),
        e4197369(4197369),
        e4197370(4197370),
        e4197371(4197371),
        e4197422(4197422),
        e4197423(4197423),
        e4197424(4197424),
        e4197425(4197425),
        e4197426(4197426),
        e4197427(4197427),
        e4197428(4197428),
        e4197429(4197429),
        e4197430(4197430),
        e4197431(4197431),
        e4197432(4197432),
        e4197433(4197433),
        e4197434(4197434),
        e4197435(4197435),
        e4197436(4197436),
        e4197437(4197437),
        e4197438(4197438),
        e4197439(4197439),
        e4197440(4197440),
        e4197441(4197441),
        e4197442(4197442),
        e4197443(4197443),
        e4197444(4197444),
        e4197445(4197445),
        e4197446(4197446),
        e4197447(4197447),
        e4197448(4197448),
        e4197449(4197449),
        e4197450(4197450),
        e4197451(4197451),
        e4197452(4197452),
        e4197453(4197453),
        e4197454(4197454),
        e4197455(4197455),
        e4197456(4197456),
        e4197457(4197457),
        e4197458(4197458),
        e4197459(4197459),
        e4197460(4197460),
        e4197461(4197461),
        e4197462(4197462),
        e4197463(4197463),
        e4197464(4197464),
        e4197465(4197465),
        e4197466(4197466),
        e4197467(4197467),
        e4197468(4197468),
        e4197469(4197469),
        e4197470(4197470),
        e4197471(4197471),
        e4197472(4197472),
        e4197473(4197473),
        e4197474(4197474),
        e4197475(4197475),
        e4197476(4197476),
        e4197477(4197477),
        e4197478(4197478),
        e4197479(4197479),
        e4197480(4197480),
        e4197481(4197481),
        e4197482(4197482),
        e4197483(4197483),
        e4197484(4197484),
        e4197485(4197485),
        e4197486(4197486),
        e4197487(4197487),
        e4197488(4197488),
        e4197489(4197489),
        e4197490(4197490),
        e4197491(4197491),
        e4197492(4197492),
        e4197493(4197493),
        e4197494(4197494),
        e4197495(4197495),
        e4197496(4197496),
        e4197497(4197497),
        e4197498(4197498),
        e4197499(4197499),
        e4197500(4197500),
        e4197501(4197501),
        e4197502(4197502),
        e4197503(4197503),
        e4197504(4197504),
        e4197505(4197505),
        e4197506(4197506),
        e4197507(4197507),
        e4197508(4197508),
        e4197509(4197509),
        e4197510(4197510),
        e4197511(4197511),
        e4197512(4197512),
        e4197513(4197513),
        e4197514(4197514),
        e4197515(4197515),
        e4197516(4197516),
        e4197517(4197517),
        e4197518(4197518),
        e4197519(4197519),
        e4197520(4197520),
        e4197521(4197521),
        e4197522(4197522),
        e4197523(4197523),
        e4197524(4197524),
        e4197525(4197525),
        e4197526(4197526),
        e4197527(4197527),
        e4197528(4197528),
        e4197529(4197529),
        e4197530(4197530),
        e4197531(4197531),
        e4197532(4197532),
        e4197533(4197533),
        e4197534(4197534),
        e4197535(4197535),
        e4197536(4197536),
        e4197537(4197537),
        e4197538(4197538),
        e4197539(4197539),
        e4197540(4197540),
        e4197541(4197541),
        e4197542(4197542),
        e4197543(4197543),
        e4197544(4197544),
        e4197545(4197545),
        e4197546(4197546),
        e4197547(4197547),
        e4197548(4197548),
        e4197549(4197549),
        e4197550(4197550),
        e4197551(4197551),
        e4197552(4197552),
        e4197553(4197553),
        e4197554(4197554),
        e4197555(4197555),
        e4197556(4197556),
        e4197557(4197557),
        e4197558(4197558),
        e4197559(4197559),
        e4197560(4197560),
        e4197561(4197561),
        e4197562(4197562),
        e4197563(4197563),
        e4197564(4197564),
        e4197565(4197565),
        e4197566(4197566),
        e4197567(4197567),
        e4197568(4197568),
        e4197569(4197569),
        e4197570(4197570),
        e4197571(4197571),
        e4197572(4197572),
        e4197573(4197573),
        e4197574(4197574),
        e4197575(4197575),
        e4197576(4197576),
        e4197577(4197577),
        e4197578(4197578),
        e4197579(4197579),
        e4197580(4197580),
        e4197581(4197581),
        e4197582(4197582),
        e4197583(4197583),
        e4197584(4197584),
        e4197585(4197585),
        e4197586(4197586),
        e4197587(4197587),
        e4197588(4197588),
        e4197589(4197589),
        e4197590(4197590),
        e4197591(4197591),
        e4197592(4197592),
        e4197593(4197593),
        e4197594(4197594),
        e4197595(4197595),
        e4197596(4197596),
        e4197597(4197597),
        e4197598(4197598),
        e4197599(4197599),
        e4197600(4197600),
        e4197601(4197601),
        e4197602(4197602),
        e4197603(4197603),
        e4197604(4197604),
        e4197605(4197605),
        e4197606(4197606),
        e4197607(4197607),
        e4197608(4197608),
        e4197609(4197609),
        e4197610(4197610),
        e4197611(4197611),
        e4197612(4197612),
        e4197613(4197613),
        e4197614(4197614),
        e4197615(4197615),
        e4197616(4197616),
        e4197617(4197617),
        e4197618(4197618),
        e4197619(4197619),
        e4197620(4197620),
        e4197621(4197621),
        e4197622(4197622),
        e4197623(4197623),
        e4197624(4197624),
        e4197625(4197625),
        e4197626(4197626),
        e4197627(4197627),
        e4197628(4197628),
        e4197629(4197629),
        e4197630(4197630),
        e4197631(4197631),
        e4197632(4197632),
        e4197633(4197633),
        e4197634(4197634),
        e4197635(4197635),
        e4197636(4197636),
        e4197637(4197637),
        e4197638(4197638),
        e4197639(4197639),
        e4197640(4197640),
        e4197641(4197641),
        e4197642(4197642),
        e4197643(4197643),
        e4197644(4197644),
        e4197645(4197645),
        e4197646(4197646),
        e4197647(4197647),
        e4197648(4197648),
        e4197649(4197649),
        e4197650(4197650),
        e4197651(4197651),
        e4197652(4197652),
        e4197653(4197653),
        e4197654(4197654),
        e4197655(4197655),
        e4197656(4197656),
        e4197657(4197657),
        e4197658(4197658),
        e4197659(4197659),
        e4197660(4197660),
        e4197661(4197661),
        e4197662(4197662),
        e4197663(4197663),
        e4197664(4197664),
        e4197665(4197665),
        e4197666(4197666),
        e4197667(4197667),
        e4197668(4197668),
        e4197669(4197669),
        e4197670(4197670),
        e4197671(4197671),
        e4197672(4197672),
        e4197673(4197673),
        e4197674(4197674),
        e4197675(4197675),
        e4197676(4197676),
        e4197677(4197677),
        e4197678(4197678),
        e4197679(4197679),
        e4197680(4197680),
        e4197681(4197681),
        e4197682(4197682),
        e4197683(4197683),
        e4197684(4197684),
        e4197685(4197685),
        e4197686(4197686),
        e4197687(4197687),
        e4197688(4197688),
        e4197689(4197689),
        e4197690(4197690),
        e4197691(4197691),
        e4197692(4197692),
        e4197693(4197693),
        e4197694(4197694),
        e4197695(4197695),
        e4197696(4197696),
        e4197697(4197697),
        e4197698(4197698),
        e4197699(4197699),
        e4197700(4197700),
        e4197701(4197701),
        e4197702(4197702),
        e4197703(4197703),
        e4197704(4197704),
        e4197705(4197705),
        e4197706(4197706),
        e4197707(4197707),
        e4197708(4197708),
        e4197709(4197709),
        e4197710(4197710),
        e4197711(4197711),
        e4197712(4197712),
        e4197713(4197713),
        e4197714(4197714),
        e4197715(4197715),
        e4197716(4197716),
        e4197717(4197717),
        e4197718(4197718),
        e4197719(4197719),
        e4197720(4197720),
        e4197721(4197721),
        e4197722(4197722),
        e4197723(4197723),
        e4197724(4197724),
        e4197725(4197725),
        e4197726(4197726),
        e4197727(4197727),
        e4197728(4197728),
        e4197729(4197729),
        e4197730(4197730),
        e4197731(4197731),
        e4197732(4197732),
        e4197733(4197733),
        e4197734(4197734),
        e4197735(4197735),
        e4197736(4197736),
        e4197737(4197737),
        e4197738(4197738),
        e4197739(4197739),
        e4197740(4197740),
        e4197741(4197741),
        e4197742(4197742),
        e4197743(4197743),
        e4197744(4197744),
        e4197745(4197745),
        e4197746(4197746),
        e4197747(4197747),
        e4197748(4197748),
        e4197749(4197749),
        e4197750(4197750),
        e4197751(4197751),
        e4197752(4197752),
        e4197753(4197753),
        e4197754(4197754),
        e4197755(4197755),
        e4197756(4197756),
        e4197757(4197757),
        e4197758(4197758),
        e4197759(4197759),
        e4197760(4197760),
        e4197761(4197761),
        e4197762(4197762),
        e4197763(4197763),
        e4197764(4197764),
        e4197765(4197765),
        e4197766(4197766),
        e4197767(4197767),
        e4197768(4197768),
        e4197769(4197769),
        e4197770(4197770),
        e4197771(4197771),
        e4197772(4197772),
        e4197773(4197773),
        e4197774(4197774),
        e4197775(4197775),
        e4197776(4197776),
        e4197777(4197777),
        e4197778(4197778),
        e4197779(4197779),
        e4197780(4197780),
        e4197781(4197781),
        e4197782(4197782),
        e4197783(4197783),
        e4197784(4197784),
        e4197785(4197785),
        e4197786(4197786),
        e4197787(4197787),
        e4197788(4197788),
        e4197789(4197789),
        e4197790(4197790),
        e4197791(4197791),
        e4197792(4197792),
        e4197793(4197793),
        e4197794(4197794),
        e4197795(4197795),
        e4197796(4197796),
        e4197797(4197797),
        e4197798(4197798),
        e4197799(4197799),
        e4197800(4197800),
        e4197801(4197801),
        e4197802(4197802),
        e4197803(4197803),
        e4197804(4197804),
        e4197805(4197805),
        e4197806(4197806),
        e4197807(4197807),
        e4197808(4197808),
        e4197809(4197809),
        e4197810(4197810),
        e4197811(4197811),
        e4197812(4197812),
        e4197813(4197813),
        e4197814(4197814),
        e4197815(4197815),
        e4197816(4197816),
        e4197817(4197817),
        e4197818(4197818),
        e4197819(4197819),
        e4197820(4197820),
        e4197821(4197821),
        e4197822(4197822),
        e4197823(4197823),
        e4197824(4197824),
        e4197825(4197825),
        e4197826(4197826),
        e4197827(4197827),
        e4197828(4197828),
        e4197829(4197829),
        e4197830(4197830),
        e4197831(4197831),
        e4197832(4197832),
        e4197833(4197833),
        e4197834(4197834),
        e4197835(4197835),
        e4197836(4197836),
        e4197837(4197837),
        e4197838(4197838),
        e4197839(4197839),
        e4197840(4197840),
        e4197841(4197841),
        e4197842(4197842),
        e4197843(4197843),
        e4197844(4197844),
        e4197845(4197845),
        e4197846(4197846),
        e4197847(4197847),
        e4197848(4197848),
        e4197849(4197849),
        e4197850(4197850),
        e4197851(4197851),
        e4197852(4197852),
        e4197853(4197853),
        e4197854(4197854),
        e4197855(4197855),
        e4197856(4197856),
        e4197857(4197857),
        e4197858(4197858),
        e4197859(4197859),
        e4197860(4197860),
        e4197861(4197861),
        e4197862(4197862),
        e4197863(4197863),
        e4197864(4197864),
        e4197865(4197865),
        e4197866(4197866),
        e4197867(4197867),
        e4197868(4197868),
        e4197869(4197869),
        e4197870(4197870),
        e4197871(4197871),
        e4197872(4197872),
        e4197873(4197873),
        e4197874(4197874),
        e4197875(4197875),
        e4197876(4197876),
        e4197877(4197877),
        e4197878(4197878),
        e4197879(4197879),
        e4197880(4197880),
        e4197881(4197881),
        e4197882(4197882),
        e4197883(4197883),
        e4197884(4197884),
        e4197885(4197885),
        e4197886(4197886),
        e4197887(4197887),
        e4197888(4197888),
        e4197889(4197889),
        e4197890(4197890),
        e4197891(4197891),
        e4197892(4197892),
        e4197893(4197893),
        e4197894(4197894),
        e4197895(4197895),
        e4197896(4197896),
        e4197897(4197897),
        e4197898(4197898),
        e4197899(4197899),
        e4197900(4197900),
        e4197901(4197901),
        e4197902(4197902),
        e4197903(4197903),
        e4197904(4197904),
        e4197905(4197905),
        e4197906(4197906),
        e4197907(4197907),
        e4197908(4197908),
        e4197909(4197909),
        e4197910(4197910),
        e4197911(4197911),
        e4197912(4197912),
        e4197913(4197913),
        e4197914(4197914),
        e4197915(4197915),
        e4197916(4197916),
        e4197917(4197917),
        e4197918(4197918),
        e4197919(4197919),
        e4197920(4197920),
        e4197921(4197921),
        e4197922(4197922),
        e4197923(4197923),
        e4197924(4197924),
        e4197925(4197925),
        e4197926(4197926),
        e4197927(4197927),
        e4197928(4197928),
        e4197929(4197929),
        e4197930(4197930),
        e4197931(4197931),
        e4197932(4197932),
        e4197933(4197933),
        e4197934(4197934),
        e4197935(4197935),
        e4197936(4197936),
        e4197937(4197937),
        e4197938(4197938),
        e4197939(4197939),
        e4197940(4197940),
        e4197941(4197941),
        e4197942(4197942),
        e4197943(4197943),
        e4197944(4197944),
        e4197945(4197945),
        e4197946(4197946),
        e4197947(4197947),
        e4197948(4197948),
        e4197949(4197949),
        e4197950(4197950),
        e4197951(4197951),
        e4197952(4197952),
        e4197953(4197953),
        e4197954(4197954),
        e4197955(4197955),
        e4197956(4197956),
        e4197957(4197957),
        e4197958(4197958),
        e4197959(4197959),
        e4197960(4197960),
        e4197961(4197961),
        e4197962(4197962),
        e4197963(4197963),
        e4197964(4197964),
        e4197965(4197965),
        e4197966(4197966),
        e4197967(4197967),
        e4197968(4197968),
        e4197969(4197969),
        e4197970(4197970),
        e4197971(4197971),
        e4197972(4197972),
        e4197973(4197973),
        e4197974(4197974),
        e4197975(4197975),
        e4197976(4197976),
        e4197977(4197977),
        e4197978(4197978),
        e4197979(4197979),
        e4197980(4197980),
        e4197981(4197981),
        e4197982(4197982),
        e4197983(4197983),
        e4197984(4197984),
        e4197985(4197985),
        e4197986(4197986),
        e4197987(4197987),
        e4197988(4197988),
        e4197989(4197989),
        e4197990(4197990),
        e4197991(4197991),
        e4197992(4197992),
        e4197993(4197993),
        e4197994(4197994),
        e4197995(4197995),
        e4197996(4197996),
        e4197997(4197997),
        e4197998(4197998),
        e4197999(4197999),
        e4198000(4198000),
        e4198001(4198001),
        e4198002(4198002),
        e4198003(4198003),
        e4198004(4198004),
        e4198005(4198005),
        e4198006(4198006),
        e4198007(4198007),
        e4198008(4198008),
        e4198009(4198009),
        e4198010(4198010),
        e4198011(4198011),
        e4198012(4198012),
        e4198013(4198013),
        e4198014(4198014),
        e4198015(4198015),
        e4198016(4198016),
        e4198017(4198017),
        e4198018(4198018),
        e4198019(4198019),
        e4198020(4198020),
        e4198021(4198021),
        e4198022(4198022),
        e4198023(4198023),
        e4198024(4198024),
        e4198025(4198025),
        e4198026(4198026),
        e4198027(4198027),
        e4198028(4198028),
        e4198029(4198029),
        e4198030(4198030),
        e4198031(4198031),
        e4198032(4198032),
        e4198033(4198033),
        e4198034(4198034),
        e4198035(4198035),
        e4198036(4198036),
        e4198037(4198037),
        e4198038(4198038),
        e4198039(4198039),
        e4198040(4198040),
        e4198041(4198041),
        e4198042(4198042),
        e4198043(4198043),
        e4198044(4198044),
        e4198045(4198045),
        e4198046(4198046),
        e4198047(4198047),
        e4198048(4198048),
        e4198049(4198049),
        e4198050(4198050),
        e4198051(4198051),
        e4198052(4198052),
        e4198053(4198053),
        e4198054(4198054),
        e4198055(4198055),
        e4198056(4198056),
        e4198057(4198057),
        e4198058(4198058),
        e4198059(4198059),
        e4198060(4198060),
        e4198061(4198061),
        e4198062(4198062),
        e4198063(4198063),
        e4198064(4198064),
        e4198065(4198065),
        e4198066(4198066),
        e4198067(4198067),
        e4198068(4198068),
        e4198069(4198069),
        e4198070(4198070),
        e4198071(4198071),
        e4198072(4198072),
        e4198073(4198073),
        e4198074(4198074),
        e4198075(4198075),
        e4198076(4198076),
        e4198077(4198077),
        e4198078(4198078),
        e4198079(4198079),
        e4198080(4198080),
        e4198081(4198081),
        e4198082(4198082),
        e4198083(4198083),
        e4198084(4198084),
        e4198085(4198085),
        e4198086(4198086),
        e4198087(4198087),
        e4198088(4198088),
        e4198089(4198089),
        e4198090(4198090),
        e4198091(4198091),
        e4198092(4198092),
        e4198093(4198093),
        e4198094(4198094),
        e4198095(4198095),
        e4198096(4198096),
        e4198097(4198097),
        e4198098(4198098),
        e4198099(4198099),
        e4198100(4198100),
        e4198101(4198101),
        e4198102(4198102),
        e4198103(4198103),
        e4198104(4198104),
        e4198105(4198105),
        e4198106(4198106),
        e4198107(4198107),
        e4198108(4198108),
        e4198109(4198109),
        e4198110(4198110),
        e4198111(4198111),
        e4198112(4198112),
        e4198113(4198113),
        e4198114(4198114),
        e4198115(4198115),
        e4198116(4198116),
        e4198117(4198117),
        e4198118(4198118),
        e4198119(4198119),
        e4198120(4198120),
        e4198121(4198121),
        e4198122(4198122),
        e4198123(4198123),
        e4198124(4198124),
        e4198125(4198125),
        e4198126(4198126),
        e4198127(4198127),
        e4198128(4198128),
        e4198129(4198129),
        e4198130(4198130),
        e4198131(4198131),
        e4198132(4198132),
        e4198133(4198133),
        e4198134(4198134),
        e4198135(4198135),
        e4198136(4198136),
        e4198137(4198137),
        e4198138(4198138),
        e4198139(4198139),
        e4198140(4198140),
        e4198141(4198141),
        e4198142(4198142),
        e4198143(4198143),
        e4198144(4198144),
        e4198145(4198145),
        e4198146(4198146),
        e4198147(4198147),
        e4198148(4198148),
        e4198149(4198149),
        e4198150(4198150),
        e4198151(4198151),
        e4198152(4198152),
        e4198153(4198153),
        e4198154(4198154),
        e4198155(4198155),
        e4198156(4198156),
        e4198157(4198157),
        e4198158(4198158),
        e4198159(4198159),
        e4198160(4198160),
        e4198161(4198161),
        e4198162(4198162),
        e4198163(4198163),
        e4198164(4198164),
        e4198165(4198165),
        e4198166(4198166),
        e4198167(4198167),
        e4198168(4198168),
        e4198169(4198169),
        e4198170(4198170),
        e4198171(4198171),
        e4198172(4198172),
        e4198173(4198173),
        e4198174(4198174),
        e4198175(4198175),
        e4198176(4198176),
        e4198177(4198177),
        e4198178(4198178),
        e4198179(4198179),
        e4198180(4198180),
        e4198181(4198181),
        e4198182(4198182),
        e4198183(4198183),
        e4198184(4198184),
        e4198185(4198185),
        e4198186(4198186),
        e4198187(4198187),
        e4198188(4198188),
        e4198189(4198189),
        e4198190(4198190),
        e4198191(4198191),
        e4198192(4198192),
        e4198193(4198193),
        e4198194(4198194),
        e4198195(4198195),
        e4198196(4198196),
        e4198197(4198197),
        e4198198(4198198),
        e4198199(4198199),
        e4198200(4198200),
        e4198201(4198201),
        e4198202(4198202),
        e4198203(4198203),
        e4198204(4198204),
        e4198205(4198205),
        e4198206(4198206),
        e4198207(4198207),
        e4198208(4198208),
        e4198209(4198209),
        e4198210(4198210),
        e4198211(4198211),
        e4198212(4198212),
        e4198213(4198213),
        e4198214(4198214),
        e4198215(4198215),
        e4198216(4198216),
        e4198217(4198217),
        e4198218(4198218),
        e4198219(4198219),
        e4198220(4198220),
        e4198221(4198221),
        e4198222(4198222),
        e4198223(4198223),
        e4198224(4198224),
        e4198225(4198225),
        e4198226(4198226),
        e4198227(4198227),
        e4198228(4198228),
        e4198229(4198229),
        e4198230(4198230),
        e4198231(4198231),
        e4198232(4198232),
        e4198233(4198233),
        e4198234(4198234),
        e4198235(4198235),
        e4198236(4198236),
        e4198237(4198237),
        e4198238(4198238),
        e4198239(4198239),
        e4198240(4198240),
        e4198241(4198241),
        e4198242(4198242),
        e4198243(4198243),
        e4198244(4198244),
        e4198245(4198245),
        e4198246(4198246),
        e4198247(4198247),
        e4198248(4198248),
        e4198249(4198249),
        e4198250(4198250),
        e4198251(4198251),
        e4198252(4198252),
        e4198253(4198253),
        e4198254(4198254),
        e4198255(4198255),
        e4198256(4198256),
        e4198257(4198257),
        e4198258(4198258),
        e4198259(4198259),
        e4198260(4198260),
        e4198261(4198261),
        e4198262(4198262),
        e4198263(4198263),
        e4198264(4198264),
        e4198265(4198265),
        e4198266(4198266),
        e4198267(4198267),
        e4198268(4198268),
        e4198269(4198269),
        e4198270(4198270),
        e4198271(4198271),
        e4198272(4198272),
        e4198273(4198273),
        e4198274(4198274),
        e4198275(4198275),
        e4198276(4198276),
        e4198277(4198277),
        e4198278(4198278),
        e4198279(4198279),
        e4198280(4198280),
        e4198281(4198281),
        e4198282(4198282),
        e4198283(4198283),
        e4198284(4198284),
        e4198285(4198285),
        e4198286(4198286),
        e4198287(4198287),
        e4198288(4198288),
        e4198289(4198289),
        e4198290(4198290),
        e4198291(4198291),
        e4198292(4198292),
        e4198293(4198293),
        e4198294(4198294),
        e4198295(4198295),
        e4198296(4198296),
        e4198297(4198297),
        e4198298(4198298),
        e4198299(4198299),
        e4198300(4198300),
        e4198301(4198301),
        e4198302(4198302),
        e4198303(4198303),
        e4198304(4198304),
        e4198305(4198305),
        e4198306(4198306),
        e4198307(4198307),
        e4198308(4198308),
        e4198309(4198309),
        e4198310(4198310),
        e4198311(4198311),
        e4198312(4198312),
        e4198313(4198313),
        e4198314(4198314),
        e4198315(4198315),
        e4198316(4198316),
        e4198317(4198317),
        e4198318(4198318),
        e4198319(4198319),
        e4198320(4198320),
        e4198321(4198321),
        e4198322(4198322),
        e4198323(4198323),
        e4198324(4198324),
        e4198325(4198325),
        e4198326(4198326),
        e4198327(4198327),
        e4198328(4198328),
        e4198329(4198329),
        e4198330(4198330),
        e4198331(4198331),
        e4198332(4198332),
        e4198333(4198333),
        e4198334(4198334),
        e4198335(4198335),
        e4198336(4198336),
        e4198337(4198337),
        e4198338(4198338),
        e4198339(4198339),
        e4198340(4198340),
        e4198341(4198341),
        e4198342(4198342),
        e4198343(4198343),
        e4198344(4198344),
        e4198345(4198345),
        e4198346(4198346),
        e4198347(4198347),
        e4198348(4198348),
        e4198349(4198349),
        e4198350(4198350),
        e4198351(4198351),
        e4198352(4198352),
        e4198353(4198353),
        e4198354(4198354),
        e4198355(4198355),
        e4198356(4198356),
        e4198357(4198357),
        e4198358(4198358),
        e4198359(4198359),
        e4198360(4198360),
        e4198361(4198361),
        e4198362(4198362),
        e4198363(4198363),
        e4198364(4198364),
        e4198365(4198365),
        e4198366(4198366),
        e4198367(4198367),
        e4198368(4198368),
        e4198369(4198369),
        e4198370(4198370),
        e4198371(4198371),
        e4198372(4198372),
        e4198373(4198373),
        e4198374(4198374),
        e4198375(4198375),
        e4198376(4198376),
        e4198377(4198377),
        e4198378(4198378),
        e4198379(4198379),
        e4198380(4198380),
        e4198381(4198381),
        e4198382(4198382),
        e4198383(4198383),
        e4198384(4198384),
        e4198385(4198385),
        e4198386(4198386),
        e4198387(4198387),
        e4198388(4198388),
        e4198389(4198389),
        e4198390(4198390),
        e4198391(4198391),
        e4198392(4198392),
        e4198393(4198393),
        e4198394(4198394),
        e4198395(4198395),
        e4198396(4198396),
        e4198397(4198397),
        e4198398(4198398),
        e4198399(4198399),
        e4198400(4198400),
        e4198401(4198401),
        e4198402(4198402),
        e4198403(4198403),
        e4198404(4198404),
        e4198405(4198405),
        e4198406(4198406),
        e4198407(4198407),
        e4198408(4198408),
        e4198409(4198409),
        e4198410(4198410),
        e4198411(4198411),
        e4198412(4198412),
        e4198413(4198413),
        e4198414(4198414),
        e4198415(4198415),
        e4198416(4198416),
        e4198417(4198417),
        e4198418(4198418),
        e4198419(4198419),
        e4198420(4198420),
        e4198421(4198421),
        e4198422(4198422),
        e4198423(4198423),
        e4198424(4198424),
        e4198425(4198425),
        e4198426(4198426),
        e4198427(4198427),
        e4198428(4198428),
        e4198429(4198429),
        e4198430(4198430),
        e4198431(4198431),
        e4198432(4198432),
        e4198433(4198433),
        e4198434(4198434),
        e4198435(4198435),
        e4198436(4198436),
        e4198437(4198437),
        e4198438(4198438),
        e4198439(4198439),
        e4198440(4198440),
        e4198441(4198441),
        e4198442(4198442),
        e4198443(4198443),
        e4198444(4198444),
        e4198445(4198445),
        e4198446(4198446),
        e4198447(4198447),
        e4198448(4198448),
        e4198449(4198449),
        e4198450(4198450),
        e4198451(4198451),
        e4198452(4198452),
        e4198453(4198453),
        e4198454(4198454),
        e4198455(4198455),
        e4198456(4198456),
        e4198457(4198457),
        e4198458(4198458),
        e4198459(4198459),
        e4198460(4198460),
        e4198461(4198461),
        e4198462(4198462),
        e4198463(4198463),
        e4198464(4198464),
        e4198465(4198465),
        e4198466(4198466),
        e4198467(4198467),
        e4198468(4198468),
        e4198469(4198469),
        e4198470(4198470),
        e4198471(4198471),
        e4198472(4198472),
        e4198473(4198473),
        e4198474(4198474),
        e4198475(4198475),
        e4198476(4198476),
        e4198477(4198477),
        e4198478(4198478),
        e4198479(4198479),
        e4198480(4198480),
        e4198481(4198481),
        e4198482(4198482),
        e4198483(4198483),
        e4198484(4198484),
        e4198485(4198485),
        e4198486(4198486),
        e4198487(4198487),
        e4198488(4198488),
        e4198489(4198489),
        e4198490(4198490),
        e4198491(4198491),
        e4198492(4198492),
        e4198493(4198493),
        e4198494(4198494),
        e4198495(4198495),
        e4198496(4198496),
        e4198497(4198497),
        e4198498(4198498),
        e4198499(4198499),
        e4198500(4198500),
        e4198501(4198501),
        e4198502(4198502),
        e4198503(4198503),
        e4198504(4198504),
        e4198505(4198505),
        e4198506(4198506),
        e4198507(4198507),
        e4198508(4198508),
        e4198509(4198509),
        e4198510(4198510),
        e4198511(4198511),
        e4198512(4198512),
        e4198513(4198513),
        e4198514(4198514),
        e4198515(4198515),
        e4198516(4198516),
        e4198517(4198517),
        e4198518(4198518),
        e4198519(4198519),
        e4198520(4198520),
        e4198521(4198521),
        e4198522(4198522),
        e4198523(4198523),
        e4198524(4198524),
        e4198525(4198525),
        e4198526(4198526),
        e4198527(4198527),
        e4198528(4198528),
        e4198529(4198529),
        e4198530(4198530),
        e4198531(4198531),
        e4198532(4198532),
        e4198533(4198533),
        e4198534(4198534),
        e4198535(4198535),
        e4198536(4198536),
        e4198537(4198537),
        e4198538(4198538),
        e4198539(4198539),
        e4198540(4198540),
        e4198541(4198541),
        e4198542(4198542),
        e4198543(4198543),
        e4198544(4198544),
        e4198545(4198545),
        e4198546(4198546),
        e4198547(4198547),
        e4198548(4198548),
        e4198549(4198549),
        e4198550(4198550),
        e4198551(4198551),
        e4198552(4198552),
        e4198553(4198553),
        e4198554(4198554),
        e4198555(4198555),
        e4198556(4198556),
        e4198557(4198557),
        e4198558(4198558),
        e4198559(4198559),
        e4198560(4198560),
        e4198561(4198561),
        e4198562(4198562),
        e4198563(4198563),
        e4198564(4198564),
        e4198565(4198565),
        e4198566(4198566),
        e4198567(4198567),
        e4198568(4198568),
        e4198569(4198569),
        e4198570(4198570),
        e4198571(4198571),
        e4198572(4198572),
        e4198573(4198573),
        e4198574(4198574),
        e4198575(4198575),
        e4198576(4198576),
        e4198577(4198577),
        e4198578(4198578),
        e4198579(4198579),
        e4198580(4198580),
        e4198581(4198581),
        e4198582(4198582),
        e4198583(4198583),
        e4198584(4198584),
        e4198585(4198585),
        e4198586(4198586),
        e4198587(4198587),
        e4198588(4198588),
        e4198589(4198589),
        e4198590(4198590),
        e4198591(4198591),
        e4198592(4198592),
        e4198593(4198593),
        e4198594(4198594),
        e4198595(4198595),
        e4198596(4198596),
        e4198597(4198597),
        e4198598(4198598),
        e4198599(4198599),
        e4198600(4198600),
        e4198601(4198601),
        e4198602(4198602),
        e4198603(4198603),
        e4198604(4198604),
        e4198605(4198605),
        e4198606(4198606),
        e4198607(4198607),
        e4198608(4198608),
        e4198609(4198609),
        e4198610(4198610),
        e4198611(4198611),
        e4198612(4198612),
        e4198613(4198613),
        e4198614(4198614),
        e4198615(4198615),
        e4198616(4198616),
        e4198617(4198617),
        e4198618(4198618),
        e4198619(4198619),
        e4198620(4198620),
        e4198621(4198621),
        e4198622(4198622),
        e4198623(4198623),
        e4198624(4198624),
        e4198625(4198625),
        e4198626(4198626),
        e4198627(4198627),
        e4198628(4198628),
        e4198629(4198629),
        e4198630(4198630),
        e4198631(4198631),
        e4198632(4198632),
        e4198633(4198633),
        e4198634(4198634),
        e4198635(4198635),
        e4198636(4198636),
        e4198637(4198637),
        e4198638(4198638),
        e4198639(4198639),
        e4198640(4198640),
        e4198641(4198641),
        e4198642(4198642),
        e4198643(4198643),
        e4198644(4198644),
        e4198645(4198645),
        e4198646(4198646),
        e4198647(4198647),
        e4198648(4198648),
        e4198649(4198649),
        e4198650(4198650),
        e4198651(4198651),
        e4198652(4198652),
        e4198653(4198653),
        e4198654(4198654),
        e4198655(4198655),
        e4198656(4198656),
        e4198657(4198657),
        e4198658(4198658),
        e4198659(4198659),
        e4198660(4198660),
        e4198661(4198661),
        e4198662(4198662),
        e4198663(4198663),
        e4198664(4198664),
        e4198665(4198665),
        e4198666(4198666),
        e4198667(4198667),
        e4198668(4198668),
        e4198669(4198669),
        e4198670(4198670),
        e4198671(4198671),
        e4198672(4198672),
        e4198673(4198673),
        e4198674(4198674),
        e4198675(4198675),
        e4198676(4198676),
        e4198677(4198677),
        e4198678(4198678),
        e4198679(4198679),
        e4198680(4198680),
        e4198681(4198681),
        e4198682(4198682),
        e4198683(4198683),
        e4198684(4198684),
        e4198685(4198685),
        e4198686(4198686),
        e4198687(4198687),
        e4198688(4198688),
        e4198689(4198689),
        e4198690(4198690),
        e4198691(4198691),
        e4198692(4198692),
        e4198693(4198693),
        e4198694(4198694),
        e4198695(4198695),
        e4198696(4198696),
        e4198697(4198697),
        e4198698(4198698),
        e4198699(4198699),
        e4198700(4198700),
        e4198701(4198701),
        e4198702(4198702),
        e4198703(4198703),
        e4198704(4198704),
        e4198705(4198705),
        e4198706(4198706),
        e4198707(4198707),
        e4198708(4198708),
        e4198709(4198709),
        e4198710(4198710),
        e4198711(4198711),
        e4198712(4198712),
        e4198713(4198713),
        e4198714(4198714),
        e4198715(4198715),
        e4198716(4198716),
        e4198717(4198717),
        e4198718(4198718),
        e4198719(4198719),
        e4198720(4198720),
        e4198721(4198721),
        e4198722(4198722),
        e4198723(4198723),
        e4198724(4198724),
        e4198725(4198725),
        e4198726(4198726),
        e4198727(4198727),
        e4198728(4198728),
        e4198729(4198729),
        e4198730(4198730),
        e4198731(4198731),
        e4198732(4198732),
        e4198733(4198733),
        e4198734(4198734),
        e4198735(4198735),
        e4198736(4198736),
        e4198737(4198737),
        e4198738(4198738),
        e4198739(4198739),
        e4198740(4198740),
        e4198741(4198741),
        f4522530(4522530),
        f4522532(4522532),
        f4522544(4522544),
        f4522556(4522556),
        f4522561(4522561),
        f4522588(4522588),
        f4522603(4522603),
        f4525234(4525234),
        f4525239(4525239),
        f4525240(4525240),
        f4525241(4525241),
        f4525247(4525247),
        f4525248(4525248),
        f4525250(4525250),
        f4525251(4525251),
        f4525252(4525252),
        f4525253(4525253),
        f4525254(4525254),
        f4526517(4526517),
        f4526850(4526850),
        f4526851(4526851),
        f4526901(4526901),
        f4526902(4526902),
        f4527601(4527601),
        f4528207(4528207),
        f4528209(4528209),
        f4528211(4528211),
        f4528216(4528216),
        f4528218(4528218),
        f4528220(4528220),
        f4528223(4528223),
        f4528225(4528225),
        f4528227(4528227),
        f4528268(4528268),
        f4528270(4528270),
        f4528591(4528591),
        f4528596(4528596),
        f4528842(4528842),
        f4529444(4529444),
        f4529447(4529447),
        f4529495(4529495),
        f4529514(4529514),
        f4529517(4529517),
        f4529520(4529520),
        f4529522(4529522),
        f4529524(4529524),
        f4529533(4529533),
        f4529601(4529601),
        f4529604(4529604),
        f4529606(4529606),
        f4529615(4529615),
        f4529722(4529722),
        f4529725(4529725),
        f4529838(4529838),
        f4529847(4529847),
        f4529849(4529849),
        f4529971(4529971),
        f4529973(4529973),
        f4530046(4530046),
        f4530050(4530050),
        f4530080(4530080),
        f4530082(4530082),
        f4530083(4530083),
        f4530085(4530085),
        f4530092(4530092),
        f4530095(4530095),
        f4530097(4530097),
        f4530098(4530098),
        f4530100(4530100),
        f4530106(4530106),
        f4530109(4530109),
        f4530111(4530111),
        f4530112(4530112),
        f4530113(4530113),
        f4530114(4530114),
        f4530115(4530115),
        f4530117(4530117),
        f4530119(4530119),
        f4530121(4530121),
        f4530122(4530122),
        f4530123(4530123),
        f4530125(4530125),
        f4530127(4530127),
        f4530139(4530139),
        f4530143(4530143),
        f4530166(4530166),
        f4530204(4530204),
        f4530206(4530206),
        f4530389(4530389),
        f4530391(4530391),
        f4530407(4530407),
        f4530451(4530451),
        f4530727(4530727),
        f4531222(4531222),
        f4531275(4531275),
        f4531400(4531400),
        f4531404(4531404),
        f4531414(4531414),
        f4531419(4531419),
        f4531518(4531518),
        f4531578(4531578),
        f4531580(4531580),
        f4531707(4531707),
        f4531711(4531711),
        f4531714(4531714),
        f4531768(4531768),
        f4531770(4531770),
        f4531775(4531775),
        f4531796(4531796),
        f4531810(4531810),
        f4531828(4531828),
        f4531835(4531835),
        f4531839(4531839),
        f4531844(4531844),
        f4532089(4532089),
        f4532091(4532091),
        f4532099(4532099),
        f4532135(4532135),
        f4532137(4532137),
        f4532169(4532169),
        f4532171(4532171),
        f4532175(4532175),
        f4532236(4532236),
        f4532238(4532238),
        f4532685(4532685),
        f4532844(4532844),
        f4532850(4532850),
        f4532852(4532852),
        f4532854(4532854),
        f4532856(4532856),
        f4532859(4532859),
        f4532861(4532861),
        f4532863(4532863),
        f4532865(4532865),
        f4532871(4532871),
        f4532898(4532898),
        f4532900(4532900),
        f4532906(4532906),
        f4532915(4532915),
        f4532917(4532917),
        f4532919(4532919),
        f4532921(4532921),
        f4532925(4532925),
        f4532935(4532935),
        f4532954(4532954),
        f4532969(4532969),
        f4532988(4532988),
        f4533006(4533006),
        f4533008(4533008),
        f4533010(4533010),
        f4533059(4533059),
        f4533061(4533061),
        f4533226(4533226),
        f4533245(4533245),
        f4533247(4533247),
        f4534475(4534475),
        f4534477(4534477),
        f4534557(4534557),
        f4534797(4534797),
        f4534807(4534807),
        f4534811(4534811),
        f4534813(4534813),
        f4534826(4534826),
        f4534831(4534831),
        f4534833(4534833),
        f4535084(4535084),
        f4535086(4535086),
        f4535111(4535111),
        f4535173(4535173),
        f4535189(4535189),
        f4535450(4535450),
        f4535591(4535591),
        f4535844(4535844),
        f4536369(4536369),
        f4536436(4536436),
        f4536885(4536885),
        f4536887(4536887),
        f4536889(4536889),
        f4536891(4536891),
        f4536897(4536897),
        f4537109(4537109),
        f4537115(4537115),
        f10000005(10000005),
        f10000033(10000033),
        f10000034(10000034),
        f10000035(10000035),
        f10000190(10000190),
        f10000191(10000191),
        f10000192(10000192),
        f10000193(10000193),
        f10000194(10000194),
        f10000195(10000195),
        f10000196(10000196),
        f10000198(10000198),
        f10000200(10000200),
        f10000207(10000207),
        f10000208(10000208),
        f10000209(10000209),
        f10000210(10000210),
        f10000212(10000212),
        f10000241(10000241),
        f10000242(10000242),
        f10000261(10000261),
        f10000262(10000262),
        f10000263(10000263),
        f10000336(10000336),
        f10000337(10000337),
        f10000338(10000338),
        f10000339(10000339),
        f10000362(10000362),
        f10000363(10000363),
        f10000364(10000364),
        f10000365(10000365),
        f10000366(10000366),
        f10000367(10000367),
        f10000368(10000368),
        f10000369(10000369),
        f10000370(10000370),
        f10000372(10000372),
        f10000373(10000373),
        f10000374(10000374),
        f10000375(10000375),
        f10000376(10000376),
        f10000377(10000377),
        f10000378(10000378),
        f10000379(10000379),
        f10000388(10000388),
        f10000389(10000389),
        f10000390(10000390),
        f10000391(10000391),
        f10000392(10000392),
        f10000393(10000393),
        f10000394(10000394),
        f10000396(10000396),
        f10000397(10000397),
        f10000398(10000398),
        f10000399(10000399),
        f10000400(10000400),
        f10000401(10000401),
        f10000402(10000402),
        f10000403(10000403),
        f10000404(10000404),
        f10000405(10000405),
        f10000406(10000406),
        f10000407(10000407),
        f10000536(10000536),
        f10000557(10000557),
        f10000558(10000558),
        f10000571(10000571),
        f10000572(10000572),
        f10000573(10000573),
        f10000574(10000574),
        f10000575(10000575),
        f10000576(10000576),
        f10000591(10000591),
        f10000592(10000592),
        f10000593(10000593),
        f10000594(10000594),
        f10000595(10000595),
        f10000596(10000596),
        f10000597(10000597),
        f10000598(10000598),
        f10000616(10000616),
        f10000634(10000634),
        f10000644(10000644),
        f10000645(10000645),
        f10000656(10000656),
        f10000657(10000657),
        f10000658(10000658),
        f10000659(10000659),
        f10000660(10000660),
        f10000661(10000661),
        f10000662(10000662),
        f10000663(10000663),
        f10000689(10000689),
        f10000690(10000690),
        f10000750(10000750),
        f10000793(10000793),
        f10000794(10000794),
        f10000795(10000795),
        f10000796(10000796),
        f10000797(10000797),
        f10000798(10000798),
        f10000799(10000799),
        f10000800(10000800),
        f10000842(10000842),
        f10000843(10000843),
        f10000844(10000844),
        f10000845(10000845),
        f10000846(10000846),
        f10000878(10000878),
        f10000990(10000990),
        f10001023(10001023),
        f10001124(10001124),
        f10016392(10016392),
        f10016394(10016394),
        f10016395(10016395),
        f10016396(10016396),
        f10016397(10016397),
        f10016398(10016398),
        f10016399(10016399),
        f10016400(10016400),
        f10016411(10016411),
        f10016412(10016412),
        f10016415(10016415),
        f10016416(10016416),
        f10016421(10016421),
        f10016422(10016422),
        f10016424(10016424),
        f10016426(10016426),
        f10016427(10016427),
        f10016441(10016441),
        f10016442(10016442),
        f10016504(10016504),
        f10016510(10016510),
        f10016511(10016511),
        f10016512(10016512),
        f10016513(10016513),
        f10016515(10016515),
        f10016518(10016518),
        f10016532(10016532),
        f10016533(10016533),
        f10016534(10016534),
        f10016535(10016535),
        f10016536(10016536),
        f10016537(10016537),
        f10016538(10016538),
        f10016539(10016539),
        f10016540(10016540),
        f10016541(10016541),
        f10016542(10016542),
        f10016543(10016543),
        f10016544(10016544),
        f10016545(10016545),
        f10016546(10016546),
        f10016601(10016601),
        f10016602(10016602),
        f10016607(10016607),
        f10016608(10016608),
        f10016609(10016609),
        f10016623(10016623),
        f10016624(10016624),
        f10016639(10016639),
        f10016643(10016643),
        f10016725(10016725),
        f10016726(10016726),
        f10016727(10016727),
        f10016728(10016728),
        f10016729(10016729),
        f10016742(10016742),
        f10016743(10016743),
        f10016744(10016744),
        f10016745(10016745),
        f10016764(10016764),
        f10016769(10016769),
        f10016770(10016770),
        f10016771(10016771),
        f10016779(10016779),
        f10016793(10016793),
        f10016794(10016794),
        f10016800(10016800),
        f10016808(10016808),
        f10016998(10016998),
        f10017011(10017011),
        f10017032(10017032),
        f10017035(10017035),
        f10017151(10017151),
        f10017152(10017152),
        f10017164(10017164),
        f10017165(10017165),
        f10017166(10017166),
        f10017167(10017167),
        f10017259(10017259),
        f10017261(10017261),
        f10017312(10017312),
        f10017371(10017371),
        f10017372(10017372),
        f10017373(10017373),
        f10017420(10017420),
        f10017421(10017421),
        f10017422(10017422),
        f10017423(10017423),
        f10017424(10017424),
        f10017425(10017425),
        f10017426(10017426),
        f10017444(10017444),
        f10017451(10017451),
        f10017473(10017473),
        f10017474(10017474),
        f10017479(10017479),
        f10034971(10034971),
        f10034973(10034973),
        f10034974(10034974),
        f10034975(10034975),
        f10034979(10034979),
        f10034981(10034981),
        f10034982(10034982),
        f10034983(10034983),
        f10034987(10034987),
        f10034989(10034989),
        f10034990(10034990),
        f10034991(10034991),
        f10034995(10034995),
        f10034997(10034997),
        f10034998(10034998),
        f10034999(10034999),
        f10035003(10035003),
        f10035005(10035005),
        f10035006(10035006),
        f10035007(10035007),
        f10035011(10035011),
        f10035013(10035013),
        f10035014(10035014),
        f10035015(10035015),
        f10035019(10035019),
        f10035021(10035021),
        f10035022(10035022),
        f10035023(10035023),
        f10035027(10035027),
        f10035029(10035029),
        f10035030(10035030),
        f10035031(10035031),
        f10035037(10035037),
        f10035039(10035039),
        f10035040(10035040),
        f10035041(10035041),
        f10035045(10035045),
        f10035047(10035047),
        f10035048(10035048),
        f10035049(10035049),
        f10035053(10035053),
        f10035055(10035055),
        f10035056(10035056),
        f10035057(10035057),
        f10035063(10035063),
        f10035065(10035065),
        f10035066(10035066),
        f10035067(10035067),
        f10035071(10035071),
        f10035073(10035073),
        f10035079(10035079),
        f10035080(10035080),
        f10035084(10035084),
        f10035086(10035086),
        f10035087(10035087),
        f10035088(10035088),
        f10035094(10035094),
        f10035096(10035096),
        f10035097(10035097),
        f10035098(10035098),
        f10035105(10035105),
        f10035107(10035107),
        f10035108(10035108),
        f10035109(10035109),
        f10035113(10035113),
        f10035115(10035115),
        f10035116(10035116),
        f10035117(10035117),
        f10035121(10035121),
        f10035123(10035123),
        f10035124(10035124),
        f10035125(10035125),
        f10035131(10035131),
        f10035133(10035133),
        f10035134(10035134),
        f10035135(10035135),
        f10035141(10035141),
        f10035143(10035143),
        f10035144(10035144),
        f10035145(10035145),
        f10035151(10035151),
        f10035153(10035153),
        f10035154(10035154),
        f10035155(10035155),
        f10035161(10035161),
        f10035163(10035163),
        f10035164(10035164),
        f10035165(10035165),
        f10035166(10035166),
        f10035171(10035171),
        f10035173(10035173),
        f10035174(10035174),
        f10035175(10035175),
        f10035176(10035176),
        f10035181(10035181),
        f10035183(10035183),
        f10035184(10035184),
        f10035185(10035185),
        f10035186(10035186),
        f10035191(10035191),
        f10035193(10035193),
        f10035194(10035194),
        f10035195(10035195),
        f10035196(10035196),
        f10035216(10035216),
        f10035217(10035217),
        f10035218(10035218),
        f10035219(10035219),
        f10035226(10035226),
        f10035227(10035227),
        f10035228(10035228),
        f10035229(10035229),
        f10035236(10035236),
        f10035237(10035237),
        f10035238(10035238),
        f10035239(10035239),
        f10035246(10035246),
        f10035247(10035247),
        f10035248(10035248),
        f10035249(10035249),
        f10035256(10035256),
        f10035257(10035257),
        f10035258(10035258),
        f10035259(10035259),
        f10035266(10035266),
        f10035267(10035267),
        f10035268(10035268),
        f10035269(10035269),
        f10035279(10035279),
        f10035280(10035280),
        f10035281(10035281),
        f10035282(10035282),
        f10035289(10035289),
        f10035290(10035290),
        f10035291(10035291),
        f10035292(10035292),
        f10035299(10035299),
        f10035300(10035300),
        f10035301(10035301),
        f10035302(10035302),
        f10035309(10035309),
        f10035310(10035310),
        f10035311(10035311),
        f10035312(10035312),
        f10035319(10035319),
        f10035320(10035320),
        f10035321(10035321),
        f10035322(10035322),
        f10035329(10035329),
        f10035330(10035330),
        f10035331(10035331),
        f10035332(10035332),
        f10035342(10035342),
        f10035343(10035343),
        f10035344(10035344),
        f10035345(10035345),
        f10035352(10035352),
        f10035353(10035353),
        f10035354(10035354),
        f10035355(10035355),
        f10035362(10035362),
        f10035363(10035363),
        f10035364(10035364),
        f10035365(10035365),
        f10035372(10035372),
        f10035373(10035373),
        f10035374(10035374),
        f10035375(10035375),
        f10035382(10035382),
        f10035383(10035383),
        f10035384(10035384),
        f10035385(10035385),
        f10035392(10035392),
        f10035393(10035393),
        f10035394(10035394),
        f10035395(10035395),
        f10035402(10035402),
        f10035403(10035403),
        f10035404(10035404),
        f10035405(10035405),
        f10035419(10035419),
        f10035420(10035420),
        f10035421(10035421),
        f10035422(10035422),
        f10035429(10035429),
        f10035430(10035430),
        f10035431(10035431),
        f10035432(10035432),
        f10035439(10035439),
        f10035440(10035440),
        f10035441(10035441),
        f10035442(10035442),
        f10035449(10035449),
        f10035450(10035450),
        f10035451(10035451),
        f10035452(10035452),
        f10035459(10035459),
        f10035460(10035460),
        f10035461(10035461),
        f10035462(10035462),
        f10035472(10035472),
        f10035473(10035473),
        f10035474(10035474),
        f10035475(10035475),
        f10035482(10035482),
        f10035483(10035483),
        f10035484(10035484),
        f10035485(10035485),
        f10035492(10035492),
        f10035493(10035493),
        f10035494(10035494),
        f10035495(10035495),
        f10035505(10035505),
        f10035506(10035506),
        f10035507(10035507),
        f10035508(10035508),
        f10035515(10035515),
        f10035516(10035516),
        f10035517(10035517),
        f10035518(10035518),
        f10035525(10035525),
        f10035526(10035526),
        f10035527(10035527),
        f10035528(10035528),
        f10035537(10035537),
        f10035538(10035538),
        f10035539(10035539),
        f10035540(10035540),
        f10035547(10035547),
        f10035548(10035548),
        f10035549(10035549),
        f10035550(10035550),
        f10035557(10035557),
        f10035558(10035558),
        f10035559(10035559),
        f10035560(10035560),
        f10035567(10035567),
        f10035568(10035568),
        f10035569(10035569),
        f10035570(10035570),
        f10035579(10035579),
        f10035580(10035580),
        f10035581(10035581),
        f10035582(10035582),
        f10035589(10035589),
        f10035590(10035590),
        f10035591(10035591),
        f10035592(10035592),
        f10035599(10035599),
        f10035600(10035600),
        f10035601(10035601),
        f10035602(10035602),
        f10035609(10035609),
        f10035610(10035610),
        f10035611(10035611),
        f10035612(10035612),
        f10035619(10035619),
        f10035620(10035620),
        f10035621(10035621),
        f10035622(10035622),
        f10035629(10035629),
        f10035630(10035630),
        f10035631(10035631),
        f10035632(10035632),
        f10035639(10035639),
        f10035640(10035640),
        f10035641(10035641),
        f10035642(10035642),
        f10035649(10035649),
        f10035650(10035650),
        f10035651(10035651),
        f10035652(10035652),
        f10035664(10035664),
        f10035666(10035666),
        f10035667(10035667),
        f10035669(10035669),
        f10035678(10035678),
        f10035679(10035679),
        f10035680(10035680),
        f10035681(10035681),
        f10035691(10035691),
        f10035693(10035693),
        f10035694(10035694),
        f10035695(10035695),
        f10035703(10035703),
        f10035704(10035704),
        f10035705(10035705),
        f10035706(10035706),
        f10035713(10035713),
        f10035714(10035714),
        f10035715(10035715),
        f10035716(10035716),
        f10035725(10035725),
        f10035726(10035726),
        f10035727(10035727),
        f10035728(10035728),
        f10035737(10035737),
        f10035739(10035739),
        f10035740(10035740),
        f10035742(10035742),
        f10035759(10035759),
        f10035760(10035760),
        f10035761(10035761),
        f10035762(10035762),
        f10035769(10035769),
        f10035770(10035770),
        f10035771(10035771),
        f10035772(10035772),
        f10035779(10035779),
        f10035780(10035780),
        f10035781(10035781),
        f10035782(10035782),
        f10035789(10035789),
        f10035790(10035790),
        f10035791(10035791),
        f10035792(10035792),
        f10035802(10035802),
        f10035803(10035803),
        f10035804(10035804),
        f10035805(10035805),
        f10035812(10035812),
        f10035813(10035813),
        f10035814(10035814),
        f10035815(10035815),
        f10035822(10035822),
        f10035823(10035823),
        f10035824(10035824),
        f10035825(10035825),
        f10035832(10035832),
        f10035833(10035833),
        f10035834(10035834),
        f10035835(10035835),
        f10035845(10035845),
        f10035846(10035846),
        f10035847(10035847),
        f10035848(10035848),
        f10035855(10035855),
        f10035856(10035856),
        f10035857(10035857),
        f10035858(10035858),
        f10035865(10035865),
        f10035866(10035866),
        f10035867(10035867),
        f10035868(10035868),
        f10035878(10035878),
        f10035879(10035879),
        f10035880(10035880),
        f10035881(10035881),
        f10035888(10035888),
        f10035889(10035889),
        f10035890(10035890),
        f10035891(10035891),
        f10035898(10035898),
        f10035899(10035899),
        f10035900(10035900),
        f10035901(10035901),
        f10035908(10035908),
        f10035909(10035909),
        f10035910(10035910),
        f10035911(10035911),
        f10035918(10035918),
        f10035919(10035919),
        f10035920(10035920),
        f10035921(10035921),
        f10035931(10035931),
        f10035932(10035932),
        f10035933(10035933),
        f10035934(10035934),
        f10035941(10035941),
        f10035942(10035942),
        f10035943(10035943),
        f10035944(10035944),
        f10035951(10035951),
        f10035952(10035952),
        f10035953(10035953),
        f10035954(10035954),
        f10035961(10035961),
        f10035962(10035962),
        f10035963(10035963),
        f10035964(10035964),
        f10035974(10035974),
        f10035975(10035975),
        f10035976(10035976),
        f10035977(10035977),
        f10035984(10035984),
        f10035985(10035985),
        f10035986(10035986),
        f10035987(10035987),
        f10035994(10035994),
        f10035995(10035995),
        f10035996(10035996),
        f10035997(10035997),
        f10036004(10036004),
        f10036005(10036005),
        f10036006(10036006),
        f10036007(10036007),
        f10036018(10036018),
        f10036019(10036019),
        f10036020(10036020),
        f10036021(10036021),
        f10036028(10036028),
        f10036029(10036029),
        f10036030(10036030),
        f10036031(10036031),
        f10036038(10036038),
        f10036039(10036039),
        f10036040(10036040),
        f10036041(10036041),
        f10036048(10036048),
        f10036049(10036049),
        f10036050(10036050),
        f10036051(10036051),
        f10036062(10036062),
        f10036063(10036063),
        f10036064(10036064),
        f10036065(10036065),
        f10036072(10036072),
        f10036073(10036073),
        f10036074(10036074),
        f10036075(10036075),
        f10036082(10036082),
        f10036083(10036083),
        f10036084(10036084),
        f10036085(10036085),
        f10036092(10036092),
        f10036093(10036093),
        f10036094(10036094),
        f10036095(10036095),
        f10036105(10036105),
        f10036106(10036106),
        f10036107(10036107),
        f10036108(10036108),
        f10036115(10036115),
        f10036116(10036116),
        f10036117(10036117),
        f10036118(10036118),
        f10036125(10036125),
        f10036126(10036126),
        f10036127(10036127),
        f10036128(10036128),
        f10036135(10036135),
        f10036136(10036136),
        f10036137(10036137),
        f10036138(10036138),
        f10036145(10036145),
        f10036146(10036146),
        f10036147(10036147),
        f10036148(10036148),
        f10036158(10036158),
        f10036159(10036159),
        f10036160(10036160),
        f10036161(10036161),
        f10036168(10036168),
        f10036169(10036169),
        f10036170(10036170),
        f10036171(10036171),
        f10036178(10036178),
        f10036179(10036179),
        f10036180(10036180),
        f10036181(10036181),
        f10036188(10036188),
        f10036189(10036189),
        f10036190(10036190),
        f10036191(10036191),
        f10036201(10036201),
        f10036202(10036202),
        f10036203(10036203),
        f10036204(10036204),
        f10036211(10036211),
        f10036212(10036212),
        f10036213(10036213),
        f10036214(10036214),
        f10036221(10036221),
        f10036222(10036222),
        f10036223(10036223),
        f10036224(10036224),
        f10036231(10036231),
        f10036232(10036232),
        f10036233(10036233),
        f10036234(10036234),
        f10036244(10036244),
        f10036245(10036245),
        f10036246(10036246),
        f10036247(10036247),
        f10036254(10036254),
        f10036255(10036255),
        f10036256(10036256),
        f10036257(10036257),
        f10036264(10036264),
        f10036265(10036265),
        f10036266(10036266),
        f10036267(10036267),
        f10036274(10036274),
        f10036275(10036275),
        f10036276(10036276),
        f10036277(10036277),
        f10036286(10036286),
        f10036287(10036287),
        f10036288(10036288),
        f10036289(10036289),
        f10036296(10036296),
        f10036297(10036297),
        f10036298(10036298),
        f10036299(10036299),
        f10036306(10036306),
        f10036307(10036307),
        f10036308(10036308),
        f10036309(10036309),
        f10036316(10036316),
        f10036317(10036317),
        f10036318(10036318),
        f10036319(10036319),
        f10036326(10036326),
        f10036327(10036327),
        f10036328(10036328),
        f10036329(10036329),
        f10036336(10036336),
        f10036337(10036337),
        f10036338(10036338),
        f10036339(10036339),
        f10036346(10036346),
        f10036347(10036347),
        f10036348(10036348),
        f10036349(10036349),
        f10036356(10036356),
        f10036357(10036357),
        f10036358(10036358),
        f10036359(10036359),
        f10036368(10036368),
        f10036369(10036369),
        f10036370(10036370),
        f10036371(10036371),
        f10036378(10036378),
        f10036379(10036379),
        f10036380(10036380),
        f10036381(10036381),
        f10036388(10036388),
        f10036389(10036389),
        f10036390(10036390),
        f10036391(10036391),
        f10036398(10036398),
        f10036399(10036399),
        f10036400(10036400),
        f10036401(10036401),
        f10036411(10036411),
        f10036412(10036412),
        f10036413(10036413),
        f10036414(10036414),
        f10036421(10036421),
        f10036422(10036422),
        f10036423(10036423),
        f10036424(10036424),
        f10036431(10036431),
        f10036432(10036432),
        f10036433(10036433),
        f10036434(10036434),
        f10036441(10036441),
        f10036442(10036442),
        f10036443(10036443),
        f10036444(10036444),
        f10036451(10036451),
        f10036452(10036452),
        f10036453(10036453),
        f10036454(10036454),
        f10036461(10036461),
        f10036462(10036462),
        f10036463(10036463),
        f10036464(10036464),
        f10036471(10036471),
        f10036472(10036472),
        f10036473(10036473),
        f10036474(10036474),
        f10036481(10036481),
        f10036482(10036482),
        f10036483(10036483),
        f10036484(10036484),
        f10036493(10036493),
        f10036494(10036494),
        f10036495(10036495),
        f10036496(10036496),
        f10036503(10036503),
        f10036504(10036504),
        f10036505(10036505),
        f10036506(10036506),
        f10036513(10036513),
        f10036514(10036514),
        f10036515(10036515),
        f10036516(10036516),
        f10036523(10036523),
        f10036524(10036524),
        f10036525(10036525),
        f10036526(10036526),
        f10036535(10036535),
        f10036536(10036536),
        f10036537(10036537),
        f10036538(10036538),
        f10036545(10036545),
        f10036546(10036546),
        f10036547(10036547),
        f10036548(10036548),
        f10036555(10036555),
        f10036556(10036556),
        f10036557(10036557),
        f10036558(10036558),
        f10036565(10036565),
        f10036566(10036566),
        f10036567(10036567),
        f10036568(10036568),
        f10036575(10036575),
        f10036576(10036576),
        f10036577(10036577),
        f10036578(10036578),
        f10036585(10036585),
        f10036586(10036586),
        f10036587(10036587),
        f10036588(10036588),
        f10036595(10036595),
        f10036596(10036596),
        f10036597(10036597),
        f10036598(10036598),
        f10036605(10036605),
        f10036606(10036606),
        f10036607(10036607),
        f10036608(10036608),
        f10036615(10036615),
        f10036616(10036616),
        f10036617(10036617),
        f10036618(10036618),
        f10036625(10036625),
        f10036626(10036626),
        f10036627(10036627),
        f10036628(10036628),
        f10036637(10036637),
        f10036638(10036638),
        f10036639(10036639),
        f10036640(10036640),
        f10036647(10036647),
        f10036648(10036648),
        f10036649(10036649),
        f10036650(10036650),
        f10036657(10036657),
        f10036658(10036658),
        f10036659(10036659),
        f10036660(10036660),
        f10036667(10036667),
        f10036668(10036668),
        f10036669(10036669),
        f10036671(10036671),
        f10036679(10036679),
        f10036680(10036680),
        f10036681(10036681),
        f10036682(10036682),
        f10036690(10036690),
        f10036691(10036691),
        f10036692(10036692),
        f10036693(10036693),
        f10036702(10036702),
        f10036703(10036703),
        f10036704(10036704),
        f10036705(10036705),
        f10036712(10036712),
        f10036713(10036713),
        f10036714(10036714),
        f10036715(10036715),
        f10036723(10036723),
        f10036724(10036724),
        f10036725(10036725),
        f10036726(10036726),
        f10036734(10036734),
        f10036735(10036735),
        f10036736(10036736),
        f10036737(10036737),
        f10036745(10036745),
        f10036746(10036746),
        f10036747(10036747),
        f10036748(10036748),
        f10036756(10036756),
        f10036757(10036757),
        f10036758(10036758),
        f10036759(10036759),
        f10036770(10036770),
        f10036772(10036772),
        f10036773(10036773),
        f10036774(10036774),
        f10036782(10036782),
        f10036783(10036783),
        f10036784(10036784),
        f10036785(10036785),
        f10036794(10036794),
        f10036795(10036795),
        f10036796(10036796),
        f10036797(10036797),
        f10036805(10036805),
        f10036806(10036806),
        f10036807(10036807),
        f10036808(10036808),
        f10036816(10036816),
        f10036817(10036817),
        f10036818(10036818),
        f10036819(10036819),
        f10036826(10036826),
        f10036827(10036827),
        f10036828(10036828),
        f10036829(10036829),
        f10036836(10036836),
        f10036837(10036837),
        f10036838(10036838),
        f10036839(10036839),
        f10036846(10036846),
        f10036847(10036847),
        f10036848(10036848),
        f10036849(10036849),
        f10036856(10036856),
        f10036857(10036857),
        f10036858(10036858),
        f10036859(10036859),
        f10036868(10036868),
        f10036869(10036869),
        f10036870(10036870),
        f10036871(10036871),
        f10036878(10036878),
        f10036879(10036879),
        f10036880(10036880),
        f10036881(10036881),
        f10036888(10036888),
        f10036889(10036889),
        f10036890(10036890),
        f10036891(10036891),
        f10036898(10036898),
        f10036899(10036899),
        f10036900(10036900),
        f10036901(10036901),
        f10036908(10036908),
        f10036909(10036909),
        f10036910(10036910),
        f10036911(10036911),
        f10036919(10036919),
        f10036920(10036920),
        f10036921(10036921),
        f10036922(10036922),
        f10036929(10036929),
        f10036930(10036930),
        f10036931(10036931),
        f10036932(10036932),
        f10036939(10036939),
        f10036940(10036940),
        f10036941(10036941),
        f10036942(10036942),
        f10036951(10036951),
        f10036952(10036952),
        f10036953(10036953),
        f10036954(10036954),
        f10036961(10036961),
        f10036962(10036962),
        f10036963(10036963),
        f10036964(10036964),
        f10036971(10036971),
        f10036972(10036972),
        f10036973(10036973),
        f10036974(10036974),
        f10036983(10036983),
        f10036984(10036984),
        f10036985(10036985),
        f10036986(10036986),
        f10036993(10036993),
        f10036994(10036994),
        f10036995(10036995),
        f10036996(10036996),
        f10037003(10037003),
        f10037004(10037004),
        f10037005(10037005),
        f10037006(10037006),
        f10037013(10037013),
        f10037014(10037014),
        f10037015(10037015),
        f10037016(10037016),
        f10037023(10037023),
        f10037024(10037024),
        f10037025(10037025),
        f10037026(10037026),
        f10037033(10037033),
        f10037034(10037034),
        f10037035(10037035),
        f10037036(10037036),
        f10037043(10037043),
        f10037044(10037044),
        f10037045(10037045),
        f10037046(10037046),
        f10037053(10037053),
        f10037054(10037054),
        f10037055(10037055),
        f10037056(10037056),
        f10037063(10037063),
        f10037065(10037065),
        f10037066(10037066),
        f10037067(10037067),
        f10037071(10037071),
        f10037073(10037073),
        f10037074(10037074),
        f10037075(10037075),
        f10037081(10037081),
        f10037083(10037083),
        f10037084(10037084),
        f10037085(10037085),
        f10037089(10037089),
        f10037091(10037091),
        f10037092(10037092),
        f10037093(10037093),
        f10037099(10037099),
        f10037101(10037101),
        f10037102(10037102),
        f10037103(10037103),
        f10037107(10037107),
        f10037109(10037109),
        f10037110(10037110),
        f10037111(10037111),
        f10037115(10037115),
        f10037117(10037117),
        f10037118(10037118),
        f10037119(10037119),
        f10037123(10037123),
        f10037125(10037125),
        f10037126(10037126),
        f10037127(10037127),
        f10037131(10037131),
        f10037133(10037133),
        f10037134(10037134),
        f10037135(10037135),
        f10037139(10037139),
        f10037141(10037141),
        f10037142(10037142),
        f10037143(10037143),
        f10037151(10037151),
        f10037153(10037153),
        f10037154(10037154),
        f10037155(10037155),
        f10037159(10037159),
        f10037161(10037161),
        f10037162(10037162),
        f10037163(10037163),
        f10037167(10037167),
        f10037169(10037169),
        f10037170(10037170),
        f10037171(10037171),
        f10037178(10037178),
        f10037180(10037180),
        f10037181(10037181),
        f10037182(10037182),
        f10037186(10037186),
        f10037188(10037188),
        f10037189(10037189),
        f10037190(10037190),
        f10037194(10037194),
        f10037196(10037196),
        f10037197(10037197),
        f10037198(10037198),
        f10037205(10037205),
        f10037207(10037207),
        f10037208(10037208),
        f10037209(10037209),
        f10037215(10037215),
        f10037217(10037217),
        f10037218(10037218),
        f10037219(10037219),
        f10037225(10037225),
        f10037227(10037227),
        f10037228(10037228),
        f10037229(10037229),
        f10037233(10037233),
        f10037235(10037235),
        f10037236(10037236),
        f10037237(10037237),
        f10037242(10037242),
        f10037244(10037244),
        f10037245(10037245),
        f10037246(10037246),
        f10037252(10037252),
        f10037255(10037255),
        f10037256(10037256),
        f10037257(10037257),
        f10037262(10037262),
        f10037264(10037264),
        f10037265(10037265),
        f10037266(10037266),
        f10037275(10037275),
        f10037278(10037278),
        f10037279(10037279),
        f10037280(10037280),
        f10037284(10037284),
        f10037286(10037286),
        f10037287(10037287),
        f10037288(10037288),
        f10037292(10037292),
        f10037294(10037294),
        f10037295(10037295),
        f10037296(10037296),
        f10037300(10037300),
        f10037302(10037302),
        f10037303(10037303),
        f10037304(10037304),
        f10037310(10037310),
        f10037312(10037312),
        f10037313(10037313),
        f10037314(10037314),
        f10037318(10037318),
        f10037320(10037320),
        f10037321(10037321),
        f10037322(10037322),
        f10037326(10037326),
        f10037328(10037328),
        f10037329(10037329),
        f10037330(10037330),
        f10037337(10037337),
        f10037339(10037339),
        f10037340(10037340),
        f10037341(10037341),
        f10037345(10037345),
        f10037347(10037347),
        f10037348(10037348),
        f10037349(10037349),
        f10037353(10037353),
        f10037355(10037355),
        f10037356(10037356),
        f10037357(10037357),
        f10037361(10037361),
        f10037363(10037363),
        f10037364(10037364),
        f10037365(10037365),
        f10037369(10037369),
        f10037371(10037371),
        f10037372(10037372),
        f10037373(10037373),
        f10037377(10037377),
        f10037379(10037379),
        f10037380(10037380),
        f10037381(10037381),
        f10037387(10037387),
        f10037389(10037389),
        f10037390(10037390),
        f10037391(10037391),
        f10037395(10037395),
        f10037397(10037397),
        f10037398(10037398),
        f10037399(10037399),
        f10037406(10037406),
        f10037408(10037408),
        f10037409(10037409),
        f10037410(10037410),
        f10037416(10037416),
        f10037418(10037418),
        f10037419(10037419),
        f10037420(10037420),
        f10037430(10037430),
        f10037433(10037433),
        f10037434(10037434),
        f10037435(10037435),
        f10037439(10037439),
        f10037441(10037441),
        f10037442(10037442),
        f10037443(10037443),
        f10037449(10037449),
        f10037451(10037451),
        f10037452(10037452),
        f10037453(10037453),
        f10037454(10037454),
        f10037459(10037459),
        f10037461(10037461),
        f10037462(10037462),
        f10037463(10037463),
        f10037464(10037464),
        f10037469(10037469),
        f10037471(10037471),
        f10037472(10037472),
        f10037473(10037473),
        f10037474(10037474),
        f10037479(10037479),
        f10037481(10037481),
        f10037482(10037482),
        f10037483(10037483),
        f10037484(10037484),
        f10037489(10037489),
        f10037491(10037491),
        f10037492(10037492),
        f10037493(10037493),
        f10037494(10037494),
        f10037501(10037501),
        f10037503(10037503),
        f10037504(10037504),
        f10037505(10037505),
        f10037509(10037509),
        f10037511(10037511),
        f10037512(10037512),
        f10037513(10037513),
        f10037517(10037517),
        f10037519(10037519),
        f10037520(10037520),
        f10037521(10037521),
        f10037527(10037527),
        f10037529(10037529),
        f10037530(10037530),
        f10037531(10037531),
        f10037535(10037535),
        f10037537(10037537),
        f10037538(10037538),
        f10037539(10037539),
        f10037543(10037543),
        f10037545(10037545),
        f10037546(10037546),
        f10037547(10037547),
        f10037551(10037551),
        f10037553(10037553),
        f10037554(10037554),
        f10037555(10037555),
        f10037561(10037561),
        f10037563(10037563),
        f10037564(10037564),
        f10037565(10037565),
        f10037569(10037569),
        f10037571(10037571),
        f10037572(10037572),
        f10037573(10037573),
        f10037577(10037577),
        f10037579(10037579),
        f10037580(10037580),
        f10037581(10037581),
        f10037585(10037585),
        f10037587(10037587),
        f10037588(10037588),
        f10037589(10037589),
        f10037593(10037593),
        f10037595(10037595),
        f10037596(10037596),
        f10037597(10037597),
        f10037603(10037603),
        f10037605(10037605),
        f10037606(10037606),
        f10037607(10037607),
        f10037613(10037613),
        f10037615(10037615),
        f10037616(10037616),
        f10037617(10037617),
        f10037618(10037618),
        f10037623(10037623),
        f10037625(10037625),
        f10037626(10037626),
        f10037627(10037627),
        f10037628(10037628),
        f10037635(10037635),
        f10037637(10037637),
        f10037638(10037638),
        f10037639(10037639),
        f10037640(10037640),
        f10037645(10037645),
        f10037647(10037647),
        f10037648(10037648),
        f10037649(10037649),
        f10037650(10037650),
        f10037655(10037655),
        f10037657(10037657),
        f10037658(10037658),
        f10037659(10037659),
        f10037660(10037660),
        f10037665(10037665),
        f10037667(10037667),
        f10037668(10037668),
        f10037669(10037669),
        f10037670(10037670),
        f10037677(10037677),
        f10037679(10037679),
        f10037680(10037680),
        f10037681(10037681),
        f10037682(10037682),
        f10037687(10037687),
        f10037689(10037689),
        f10037690(10037690),
        f10037691(10037691),
        f10037692(10037692),
        f10037697(10037697),
        f10037699(10037699),
        f10037700(10037700),
        f10037701(10037701),
        f10037702(10037702),
        f10037709(10037709),
        f10037711(10037711),
        f10037712(10037712),
        f10037713(10037713),
        f10037714(10037714),
        f10037719(10037719),
        f10037721(10037721),
        f10037722(10037722),
        f10037723(10037723),
        f10037724(10037724),
        f10037729(10037729),
        f10037731(10037731),
        f10037732(10037732),
        f10037733(10037733),
        f10037734(10037734),
        f10037739(10037739),
        f10037741(10037741),
        f10037742(10037742),
        f10037743(10037743),
        f10037744(10037744),
        f10039392(10039392),
        f10039393(10039393),
        f10039394(10039394),
        f10039395(10039395),
        f10039402(10039402),
        f10039403(10039403),
        f10039404(10039404),
        f10039405(10039405),
        f10039412(10039412),
        f10039413(10039413),
        f10039414(10039414),
        f10039415(10039415),
        f10039422(10039422),
        f10039423(10039423),
        f10039424(10039424),
        f10039425(10039425),
        f10039432(10039432),
        f10039433(10039433),
        f10039434(10039434),
        f10039435(10039435),
        f10039442(10039442),
        f10039443(10039443),
        f10039444(10039444),
        f10039445(10039445),
        f10039452(10039452),
        f10039453(10039453),
        f10039454(10039454),
        f10039455(10039455),
        f10039462(10039462),
        f10039463(10039463),
        f10039464(10039464),
        f10039465(10039465),
        f10039474(10039474),
        f10039475(10039475),
        f10039476(10039476),
        f10039477(10039477),
        f10039484(10039484),
        f10039485(10039485),
        f10039486(10039486),
        f10039487(10039487),
        f10039494(10039494),
        f10039495(10039495),
        f10039496(10039496),
        f10039497(10039497),
        f10039504(10039504),
        f10039505(10039505),
        f10039506(10039506),
        f10039507(10039507),
        f10039514(10039514),
        f10039515(10039515),
        f10039516(10039516),
        f10039517(10039517),
        f10039524(10039524),
        f10039525(10039525),
        f10039526(10039526),
        f10039527(10039527),
        f10039534(10039534),
        f10039535(10039535),
        f10039536(10039536),
        f10039537(10039537),
        f10039544(10039544),
        f10039545(10039545),
        f10039546(10039546),
        f10039547(10039547),
        f10041574(10041574),
        f10041576(10041576),
        f10041577(10041577),
        f10041578(10041578),
        f10041582(10041582),
        f10041584(10041584),
        f10041585(10041585),
        f10041586(10041586),
        f10041592(10041592),
        f10041594(10041594),
        f10041595(10041595),
        f10041596(10041596),
        f10041600(10041600),
        f10041602(10041602),
        f10041603(10041603),
        f10041604(10041604),
        f10041608(10041608),
        f10041610(10041610),
        f10041611(10041611),
        f10041612(10041612),
        f10041616(10041616),
        f10041618(10041618),
        f10041619(10041619),
        f10041620(10041620),
        f10041624(10041624),
        f10041626(10041626),
        f10041627(10041627),
        f10041628(10041628),
        f10041632(10041632),
        f10041634(10041634),
        f10041635(10041635),
        f10041636(10041636),
        f10041640(10041640),
        f10041642(10041642),
        f10041643(10041643),
        f10041644(10041644),
        f10043209(10043209),
        f10043211(10043211),
        f10043212(10043212),
        f10043213(10043213),
        f10043217(10043217),
        f10043219(10043219),
        f10043220(10043220),
        f10043221(10043221),
        f10043225(10043225),
        f10043227(10043227),
        f10043228(10043228),
        f10043229(10043229),
        f10043233(10043233),
        f10043235(10043235),
        f10043236(10043236),
        f10043237(10043237),
        f10043714(10043714),
        f10043716(10043716),
        f10043717(10043717),
        f10043718(10043718),
        f10043722(10043722),
        f10043724(10043724),
        f10043725(10043725),
        f10043726(10043726),
        f10043730(10043730),
        f10043732(10043732),
        f10043733(10043733),
        f10043734(10043734),
        f10043738(10043738),
        f10043740(10043740),
        f10043741(10043741),
        f10043742(10043742),
        f10043746(10043746),
        f10043748(10043748),
        f10043749(10043749),
        f10043750(10043750),
        f10044023(10044023),
        f10044025(10044025),
        f10044026(10044026),
        f10044027(10044027),
        f10044031(10044031),
        f10044033(10044033),
        f10044034(10044034),
        f10044035(10044035),
        f10044041(10044041),
        f10044043(10044043),
        f10044044(10044044),
        f10044045(10044045),
        f10044049(10044049),
        f10044051(10044051),
        f10044052(10044052),
        f10044053(10044053),
        f10044059(10044059),
        f10044061(10044061),
        f10044062(10044062),
        f10044063(10044063),
        f10044067(10044067),
        f10044069(10044069),
        f10044070(10044070),
        f10044071(10044071),
        f10044075(10044075),
        f10044077(10044077),
        f10044078(10044078),
        f10044079(10044079),
        f10044083(10044083),
        f10044085(10044085),
        f10044086(10044086),
        f10044087(10044087),
        f10077832(10077832),
        f10077834(10077834),
        f10077835(10077835),
        f10077836(10077836),
        f10077837(10077837),
        f10077838(10077838),
        f10077839(10077839),
        f10077840(10077840),
        f10077851(10077851),
        f10077852(10077852),
        f10077855(10077855),
        f10077856(10077856),
        f10077861(10077861),
        f10077862(10077862),
        f10077864(10077864),
        f10077866(10077866),
        f10077867(10077867),
        f10077881(10077881),
        f10077882(10077882),
        f10077944(10077944),
        f10077950(10077950),
        f10077951(10077951),
        f10077952(10077952),
        f10077953(10077953),
        f10077955(10077955),
        f10077958(10077958),
        f10077972(10077972),
        f10077973(10077973),
        f10077974(10077974),
        f10077975(10077975),
        f10077976(10077976),
        f10077977(10077977),
        f10077978(10077978),
        f10077979(10077979),
        f10077980(10077980),
        f10077981(10077981),
        f10077982(10077982),
        f10077983(10077983),
        f10077984(10077984),
        f10077985(10077985),
        f10077986(10077986),
        f10078041(10078041),
        f10078042(10078042),
        f10078047(10078047),
        f10078048(10078048),
        f10078049(10078049),
        f10078063(10078063),
        f10078064(10078064),
        f10078079(10078079),
        f10078083(10078083),
        f10078165(10078165),
        f10078166(10078166),
        f10078167(10078167),
        f10078168(10078168),
        f10078169(10078169),
        f10078182(10078182),
        f10078183(10078183),
        f10078184(10078184),
        f10078185(10078185),
        f10078204(10078204),
        f10078209(10078209),
        f10078210(10078210),
        f10078211(10078211),
        f10078219(10078219),
        f10078233(10078233),
        f10078234(10078234),
        f10078240(10078240),
        f10078248(10078248),
        f10078438(10078438),
        f10078451(10078451),
        f10078472(10078472),
        f10078475(10078475),
        f10078591(10078591),
        f10078592(10078592),
        f10078604(10078604),
        f10078605(10078605),
        f10078606(10078606),
        f10078607(10078607),
        f10078699(10078699),
        f10078701(10078701),
        f10078752(10078752),
        f10078811(10078811),
        f10078812(10078812),
        f10078813(10078813),
        f10078860(10078860),
        f10078861(10078861),
        f10078862(10078862),
        f10078863(10078863),
        f10078864(10078864),
        f10078865(10078865),
        f10078866(10078866),
        f10078884(10078884),
        f10078891(10078891),
        f10078913(10078913),
        f10078914(10078914),
        f10078919(10078919),
        f10999432(10999432),
        f10999434(10999434),
        f10999435(10999435),
        f10999436(10999436),
        f10999437(10999437),
        f10999438(10999438),
        f10999439(10999439),
        f10999440(10999440),
        f10999451(10999451),
        f10999452(10999452),
        f10999455(10999455),
        f10999456(10999456),
        f10999461(10999461),
        f10999462(10999462),
        f10999464(10999464),
        f10999466(10999466),
        f10999467(10999467),
        f10999481(10999481),
        f10999482(10999482),
        f10999544(10999544),
        f10999550(10999550),
        f10999551(10999551),
        f10999552(10999552),
        f10999553(10999553),
        f10999555(10999555),
        f10999558(10999558),
        f10999572(10999572),
        f10999573(10999573),
        f10999574(10999574),
        f10999575(10999575),
        f10999576(10999576),
        f10999577(10999577),
        f10999578(10999578),
        f10999579(10999579),
        f10999580(10999580),
        f10999581(10999581),
        f10999582(10999582),
        f10999583(10999583),
        f10999584(10999584),
        f10999585(10999585),
        f10999586(10999586),
        f10999641(10999641),
        f10999642(10999642),
        f10999647(10999647),
        f10999648(10999648),
        f10999649(10999649),
        f10999663(10999663),
        f10999664(10999664),
        f10999679(10999679),
        f10999683(10999683),
        f10999765(10999765),
        f10999766(10999766),
        f10999767(10999767),
        f10999768(10999768),
        f10999769(10999769),
        f10999782(10999782),
        f10999783(10999783),
        f10999784(10999784),
        f10999785(10999785),
        f10999804(10999804),
        f10999809(10999809),
        f10999810(10999810),
        f10999811(10999811),
        f10999819(10999819),
        f10999833(10999833),
        f10999834(10999834),
        f10999840(10999840),
        f10999848(10999848),
        f11000038(11000038),
        f11000051(11000051),
        f11000072(11000072),
        f11000075(11000075),
        f11000191(11000191),
        f11000192(11000192),
        f11000204(11000204),
        f11000205(11000205),
        f11000206(11000206),
        f11000207(11000207),
        f11000299(11000299),
        f11000301(11000301),
        f11000352(11000352),
        f11000411(11000411),
        f11000412(11000412),
        f11000413(11000413),
        f11000460(11000460),
        f11000461(11000461),
        f11000462(11000462),
        f11000463(11000463),
        f11000464(11000464),
        f11000465(11000465),
        f11000466(11000466),
        f11000484(11000484),
        f11000491(11000491),
        f11000513(11000513),
        f11000514(11000514),
        f11000519(11000519),
        e14194305(14194305),
        e14194309(14194309),
        e14194310(14194310),
        e14194311(14194311),
        e14194312(14194312),
        e14194313(14194313),
        e14194314(14194314),
        e14194315(14194315),
        e14194316(14194316),
        e14194317(14194317),
        e14194318(14194318),
        e14194319(14194319),
        e14194320(14194320),
        e14194321(14194321),
        e14194326(14194326),
        e14194327(14194327),
        e14194328(14194328),
        e14194329(14194329),
        e14194330(14194330),
        e14194331(14194331),
        e14194332(14194332),
        e14194333(14194333),
        e14194334(14194334),
        e14194335(14194335),
        e14194336(14194336),
        e14194337(14194337),
        e14194338(14194338),
        e14194339(14194339),
        e14194340(14194340),
        e14194341(14194341),
        e14194342(14194342),
        e14194343(14194343),
        e14194344(14194344),
        e14194345(14194345),
        e14194346(14194346),
        e14194347(14194347),
        e14194348(14194348),
        e14194349(14194349),
        e14194350(14194350),
        e14194351(14194351),
        e14194352(14194352),
        e14194353(14194353),
        e14194354(14194354),
        e14194355(14194355),
        e14194356(14194356),
        e14194357(14194357),
        e14194358(14194358),
        e14194359(14194359),
        e14194360(14194360),
        e14194361(14194361),
        e14194362(14194362),
        e14194363(14194363),
        e14194364(14194364),
        e14194365(14194365),
        e14194366(14194366),
        e14194367(14194367),
        e14194368(14194368),
        e14194369(14194369),
        e14194370(14194370),
        e14194371(14194371),
        e14194372(14194372),
        e14194373(14194373),
        e14194374(14194374),
        e14194380(14194380),
        e14194381(14194381),
        e14194382(14194382),
        e14194383(14194383),
        e14194384(14194384),
        e14194385(14194385),
        e14194386(14194386),
        e14194387(14194387),
        e14194388(14194388),
        e14194389(14194389),
        e14194390(14194390),
        e14194391(14194391),
        e14194392(14194392),
        e14194393(14194393),
        e14194394(14194394),
        e14194395(14194395),
        e14194396(14194396),
        e14194397(14194397),
        e14194398(14194398),
        e14194399(14194399),
        e14194400(14194400),
        e14194401(14194401),
        e14194402(14194402),
        e14194403(14194403),
        e14194404(14194404),
        e14194405(14194405),
        e14194406(14194406),
        e14194407(14194407),
        e14194408(14194408),
        e14194409(14194409),
        e14194410(14194410),
        e14194411(14194411),
        e14194412(14194412),
        e14194414(14194414),
        e14194415(14194415),
        e14194417(14194417),
        e14194418(14194418),
        e14194420(14194420),
        e14194421(14194421),
        e14194422(14194422),
        e14194423(14194423),
        e14194424(14194424),
        e14194425(14194425),
        e14194426(14194426),
        e14194427(14194427),
        e14194428(14194428),
        e14194429(14194429),
        e14194430(14194430),
        e14194431(14194431),
        e14194432(14194432),
        e14194445(14194445),
        e14194446(14194446),
        e14194447(14194447),
        e14194448(14194448),
        e14194449(14194449),
        e14194450(14194450),
        e14194451(14194451),
        e14194452(14194452),
        e14194453(14194453),
        e14194454(14194454),
        e14194455(14194455),
        e14194456(14194456),
        e14194457(14194457),
        e14194458(14194458),
        e14194459(14194459),
        e14194463(14194463),
        e14194464(14194464),
        e14194465(14194465),
        e14194466(14194466),
        e14194467(14194467),
        e14194468(14194468),
        e14194469(14194469),
        e14194473(14194473),
        e14194474(14194474),
        e14194475(14194475),
        e14194476(14194476),
        e14194477(14194477),
        e14194478(14194478),
        e14194479(14194479),
        e14194480(14194480),
        e14194481(14194481),
        e14194482(14194482),
        e14194483(14194483),
        e14194493(14194493),
        e14194495(14194495),
        e14194496(14194496),
        e14194497(14194497),
        e14194501(14194501),
        e14194502(14194502),
        e14194503(14194503),
        e14194504(14194504),
        e14194505(14194505),
        e14194506(14194506),
        e14194507(14194507),
        e14194508(14194508),
        e14194509(14194509),
        e14194510(14194510),
        e14194511(14194511),
        e14194512(14194512),
        e14194513(14194513),
        e14194516(14194516),
        e14194517(14194517),
        e14194518(14194518),
        e14194519(14194519),
        e14194520(14194520),
        e14194522(14194522),
        e14194523(14194523),
        e14194524(14194524),
        e14194525(14194525),
        e14194526(14194526),
        e14194527(14194527),
        e14194528(14194528),
        e14194529(14194529),
        e14194530(14194530),
        e14194531(14194531),
        e14194532(14194532),
        e14194533(14194533),
        e14194534(14194534),
        e14194535(14194535),
        e14194536(14194536),
        e14194537(14194537),
        e14194538(14194538),
        e14194539(14194539),
        e14194540(14194540),
        e14194541(14194541),
        e14194542(14194542),
        e14194543(14194543),
        e14194544(14194544),
        e14194545(14194545),
        e14194546(14194546),
        e14194547(14194547),
        e14194548(14194548),
        e14194549(14194549),
        e14194550(14194550),
        e14194551(14194551),
        e14194552(14194552),
        e14194553(14194553),
        e14194554(14194554),
        e14194555(14194555),
        e14194556(14194556),
        e14194557(14194557),
        e14194558(14194558),
        e14194559(14194559),
        e14194560(14194560),
        e14194561(14194561),
        e14194562(14194562),
        e14194563(14194563),
        e14194564(14194564),
        e14194565(14194565),
        e14194566(14194566),
        e14194567(14194567),
        e14194568(14194568),
        e14194569(14194569),
        e14194570(14194570),
        e14194571(14194571),
        e14194572(14194572),
        e14194573(14194573),
        e14194574(14194574),
        e14194575(14194575),
        e14194576(14194576),
        e14194577(14194577),
        e14194578(14194578),
        e14194579(14194579),
        e14194580(14194580),
        e14194581(14194581),
        e14194582(14194582),
        e14194583(14194583),
        e14194584(14194584),
        e14194585(14194585),
        e14194586(14194586),
        e14194587(14194587),
        e14194588(14194588),
        e14194589(14194589),
        e14194590(14194590),
        e14194591(14194591),
        e14194592(14194592),
        e14194597(14194597),
        e14194598(14194598),
        e14194599(14194599),
        e14194600(14194600),
        e14194601(14194601),
        e14194602(14194602),
        e14194603(14194603),
        e14194604(14194604),
        e14194605(14194605),
        e14194606(14194606),
        e14194607(14194607),
        e14194608(14194608),
        e14194609(14194609),
        e14194610(14194610),
        e14194611(14194611),
        e14194612(14194612),
        e14194613(14194613),
        e14194614(14194614),
        e14194615(14194615),
        e14194616(14194616),
        e14194617(14194617),
        e14194618(14194618),
        e14194619(14194619),
        e14194620(14194620),
        e14194621(14194621),
        e14194622(14194622),
        e14194623(14194623),
        e14194624(14194624),
        e14194625(14194625),
        e14194626(14194626),
        e14194627(14194627),
        e14194628(14194628),
        e14194629(14194629),
        e14194630(14194630),
        e14194631(14194631),
        e14194632(14194632),
        e14194633(14194633),
        e14194634(14194634),
        e14194635(14194635),
        e14194636(14194636),
        e14194637(14194637),
        e14194638(14194638),
        e14194639(14194639),
        e14194640(14194640),
        e14194641(14194641),
        e14194642(14194642),
        e14194643(14194643),
        e14194644(14194644),
        e14194645(14194645),
        e14194646(14194646),
        e14194647(14194647),
        e14194648(14194648),
        e14194649(14194649),
        e14194650(14194650),
        e14194651(14194651),
        e14194652(14194652),
        e14194653(14194653),
        e14194654(14194654),
        e14194655(14194655),
        e14194656(14194656),
        e14194657(14194657),
        e14194658(14194658),
        e14194659(14194659),
        e14194660(14194660),
        e14194661(14194661),
        e14194662(14194662),
        e14194663(14194663),
        e14194664(14194664),
        e14194665(14194665),
        e14194666(14194666),
        e14194667(14194667),
        e14194668(14194668),
        e14194669(14194669),
        e14194677(14194677),
        e14194678(14194678),
        e14194679(14194679),
        e14194680(14194680),
        e14194681(14194681),
        e14194682(14194682),
        e14194683(14194683),
        e14194684(14194684),
        e14194685(14194685),
        e14194686(14194686),
        e14194687(14194687),
        e14194688(14194688),
        e14194689(14194689),
        e14194690(14194690),
        e14194691(14194691),
        e14194692(14194692),
        e14194693(14194693),
        e14194694(14194694),
        e14194696(14194696),
        e14194697(14194697),
        e14194698(14194698),
        e14194699(14194699),
        e14194700(14194700),
        e14194701(14194701),
        e14194702(14194702),
        e14194703(14194703),
        e14194704(14194704),
        e14194705(14194705),
        e14194706(14194706),
        e14194707(14194707),
        e14194708(14194708),
        e14194709(14194709),
        e14194710(14194710),
        e14194711(14194711),
        e14194713(14194713),
        e14194715(14194715),
        e14194716(14194716),
        e14194717(14194717),
        e14194718(14194718),
        e14194719(14194719),
        e14194720(14194720),
        e14194721(14194721),
        e14194722(14194722),
        e14194723(14194723),
        e14194724(14194724),
        e14194725(14194725),
        e14194726(14194726),
        e14194727(14194727),
        e14194728(14194728),
        e14194729(14194729),
        e14194730(14194730),
        e14194731(14194731),
        e14194732(14194732),
        e14194733(14194733),
        e14194734(14194734),
        e14194735(14194735),
        e14194736(14194736),
        e14194737(14194737),
        e14194738(14194738),
        e14194739(14194739),
        e14194740(14194740),
        e14194741(14194741),
        e14194742(14194742),
        e14194743(14194743),
        e14194744(14194744),
        e14194745(14194745),
        e14194746(14194746),
        e14194747(14194747),
        e14194748(14194748),
        e14194749(14194749),
        e14194750(14194750),
        e14194751(14194751),
        e14194752(14194752),
        e14194753(14194753),
        e14194754(14194754),
        e14194755(14194755),
        e14194756(14194756),
        e14194757(14194757),
        e14194758(14194758),
        e14194759(14194759),
        e14194760(14194760),
        e14194761(14194761),
        e14194762(14194762),
        e14194763(14194763),
        e14194764(14194764),
        e14194765(14194765),
        e14194766(14194766),
        e14194767(14194767),
        e14194768(14194768),
        e14194769(14194769),
        e14194770(14194770),
        e14194771(14194771),
        e14194772(14194772),
        e14194773(14194773),
        e14194777(14194777),
        e14194778(14194778),
        e14194779(14194779),
        e14194780(14194780),
        e14194781(14194781),
        e14194782(14194782),
        e14194783(14194783),
        e14194784(14194784),
        e14194785(14194785),
        e14194786(14194786),
        e14194787(14194787),
        e14194788(14194788),
        e14194789(14194789),
        e14194790(14194790),
        e14194856(14194856),
        e14194857(14194857),
        e14194858(14194858),
        e14194859(14194859),
        e14194860(14194860),
        e14194861(14194861),
        e14194862(14194862),
        e14194863(14194863),
        e14194864(14194864),
        e14194865(14194865),
        e14194866(14194866),
        e14194867(14194867),
        e14194868(14194868),
        e14194869(14194869),
        e14194870(14194870),
        e14194871(14194871),
        e14194872(14194872),
        e14194873(14194873),
        e14194874(14194874),
        e14194875(14194875),
        e14194876(14194876),
        e14194877(14194877),
        e14194878(14194878),
        e14194879(14194879),
        e14194880(14194880),
        e14194881(14194881),
        e14194882(14194882),
        e14194883(14194883),
        e14194884(14194884),
        e14194885(14194885),
        e14194886(14194886),
        e14194887(14194887),
        e14194888(14194888),
        e14194889(14194889),
        e14194890(14194890),
        e14194891(14194891),
        e14194892(14194892),
        e14194893(14194893),
        e14194894(14194894),
        e14194895(14194895),
        e14194896(14194896),
        e14194897(14194897),
        e14194898(14194898),
        e14194899(14194899),
        e14194900(14194900),
        e14194901(14194901),
        e14194902(14194902),
        e14194903(14194903),
        e14194904(14194904),
        e14194905(14194905),
        e14194906(14194906),
        e14194907(14194907),
        e14194908(14194908),
        e14194909(14194909),
        e14194910(14194910),
        e14194911(14194911),
        e14194912(14194912),
        e14194913(14194913),
        e14194914(14194914),
        e14194915(14194915),
        e14194916(14194916),
        e14194917(14194917),
        e14194918(14194918),
        e14194919(14194919),
        e14194920(14194920),
        e14194921(14194921),
        e14194922(14194922),
        e14194923(14194923),
        e14194924(14194924),
        e14194925(14194925),
        e14194926(14194926),
        e14194927(14194927),
        e14194928(14194928),
        e14194929(14194929),
        e14194936(14194936),
        e14194937(14194937),
        e14194938(14194938),
        e14194939(14194939),
        e14194940(14194940),
        e14194941(14194941),
        e14194942(14194942),
        e14194943(14194943),
        e14194944(14194944),
        e14194945(14194945),
        e14194946(14194946),
        e14194947(14194947),
        e14194948(14194948),
        e14194949(14194949),
        e14194950(14194950),
        e14194951(14194951),
        e14194952(14194952),
        e14194953(14194953),
        e14194954(14194954),
        e14194955(14194955),
        e14194956(14194956),
        e14194957(14194957),
        e14194960(14194960),
        e14194961(14194961),
        e14194962(14194962),
        e14194963(14194963),
        e14194964(14194964),
        e14194965(14194965),
        e14194966(14194966),
        e14194967(14194967),
        e14194968(14194968),
        e14194969(14194969),
        e14194970(14194970),
        e14194971(14194971),
        e14194972(14194972),
        e14194973(14194973),
        e14194974(14194974),
        e14194975(14194975),
        e14194976(14194976),
        e14194986(14194986),
        e14194987(14194987),
        e14194988(14194988),
        e14194989(14194989),
        e14194990(14194990),
        e14194991(14194991),
        e14194992(14194992),
        e14194993(14194993),
        e14194994(14194994),
        e14194995(14194995),
        e14194996(14194996),
        e14194997(14194997),
        e14194998(14194998),
        e14194999(14194999),
        e14195000(14195000),
        e14195001(14195001),
        e14195002(14195002),
        e14195003(14195003),
        e14195004(14195004),
        e14195005(14195005),
        e14195006(14195006),
        e14195007(14195007),
        e14195008(14195008),
        e14195009(14195009),
        e14195010(14195010),
        e14195011(14195011),
        e14195012(14195012),
        e14195013(14195013),
        e14195014(14195014),
        e14195021(14195021),
        e14195022(14195022),
        e14195023(14195023),
        e14195024(14195024),
        e14195025(14195025),
        e14195026(14195026),
        e14195027(14195027),
        e14195028(14195028),
        e14195029(14195029),
        e14195030(14195030),
        e14195031(14195031),
        e14195032(14195032),
        e14195033(14195033),
        e14195034(14195034),
        e14195035(14195035),
        e14195036(14195036),
        e14195037(14195037),
        e14195038(14195038),
        e14195039(14195039),
        e14195040(14195040),
        e14195041(14195041),
        e14195042(14195042),
        e14195043(14195043),
        e14195044(14195044),
        e14195045(14195045),
        e14195046(14195046),
        e14195047(14195047),
        e14195048(14195048),
        e14195049(14195049),
        e14195050(14195050),
        e14195051(14195051),
        e14195052(14195052),
        e14195053(14195053),
        e14195054(14195054),
        e14195055(14195055),
        e14195056(14195056),
        e14195057(14195057),
        e14195058(14195058),
        e14195059(14195059),
        e14195060(14195060),
        e14195061(14195061),
        e14195062(14195062),
        e14195063(14195063),
        e14195067(14195067),
        e14195068(14195068),
        e14195069(14195069),
        e14195070(14195070),
        e14195071(14195071),
        e14195072(14195072),
        e14195073(14195073),
        e14195074(14195074),
        e14195075(14195075),
        e14195076(14195076),
        e14195077(14195077),
        e14195078(14195078),
        e14195079(14195079),
        e14195080(14195080),
        e14195081(14195081),
        e14195082(14195082),
        e14195083(14195083),
        e14195084(14195084),
        e14195085(14195085),
        e14195086(14195086),
        e14195087(14195087),
        e14195088(14195088),
        e14195089(14195089),
        e14195090(14195090),
        e14195091(14195091),
        e14195092(14195092),
        e14195093(14195093),
        e14195094(14195094),
        e14195095(14195095),
        e14195096(14195096),
        e14195097(14195097),
        e14195098(14195098),
        e14195099(14195099),
        e14195100(14195100),
        e14195101(14195101),
        e14195102(14195102),
        e14195103(14195103),
        e14195104(14195104),
        e14195105(14195105),
        e14195106(14195106),
        e14195107(14195107),
        e14195108(14195108),
        e14195109(14195109),
        e14195110(14195110),
        e14195111(14195111),
        e14195112(14195112),
        e14195113(14195113),
        e14195114(14195114),
        e14195115(14195115),
        e14195116(14195116),
        e14195117(14195117),
        e14195118(14195118),
        e14195119(14195119),
        e14195120(14195120),
        e14195121(14195121),
        e14195122(14195122),
        e14195123(14195123),
        e14195124(14195124),
        e14195125(14195125),
        e14195126(14195126),
        e14195127(14195127),
        e14195128(14195128),
        e14195129(14195129),
        e14195130(14195130),
        e14195131(14195131),
        e14195132(14195132),
        e14195133(14195133),
        e14195134(14195134),
        e14195135(14195135),
        e14195136(14195136),
        e14195137(14195137),
        e14195138(14195138),
        e14195139(14195139),
        e14195140(14195140),
        e14195141(14195141),
        e14195142(14195142),
        e14195143(14195143),
        e14195144(14195144),
        e14195145(14195145),
        e14195146(14195146),
        e14195147(14195147),
        e14195148(14195148),
        e14195149(14195149),
        e14195150(14195150),
        e14195151(14195151),
        e14195152(14195152),
        e14195153(14195153),
        e14195154(14195154),
        e14195155(14195155),
        e14195156(14195156),
        e14195157(14195157),
        e14195158(14195158),
        e14195159(14195159),
        e14195160(14195160),
        e14195161(14195161),
        e14195162(14195162),
        e14195164(14195164),
        e14195165(14195165),
        e14195166(14195166),
        e14195167(14195167),
        e14195168(14195168),
        e14195169(14195169),
        e14195170(14195170),
        e14195171(14195171),
        e14195172(14195172),
        e14195173(14195173),
        e14195174(14195174),
        e14195175(14195175),
        e14195176(14195176),
        e14195177(14195177),
        e14195178(14195178),
        e14195179(14195179),
        e14195180(14195180),
        e14195181(14195181),
        e14195182(14195182),
        e14195183(14195183),
        e14195184(14195184),
        e14195185(14195185),
        e14195186(14195186),
        e14195187(14195187),
        e14195188(14195188),
        e14195189(14195189),
        e14195190(14195190),
        e14195191(14195191),
        e14195192(14195192),
        e14195193(14195193),
        e14195194(14195194),
        e14195195(14195195),
        e14195196(14195196),
        e14195197(14195197),
        e14195198(14195198),
        e14195199(14195199),
        e14195200(14195200),
        e14195201(14195201),
        e14195202(14195202),
        e14195203(14195203),
        e14195204(14195204),
        e14195205(14195205),
        e14195206(14195206),
        e14195207(14195207),
        e14195208(14195208),
        e14195209(14195209),
        e14195210(14195210),
        e14195211(14195211),
        e14195212(14195212),
        e14195213(14195213),
        e14195214(14195214),
        e14195215(14195215),
        e14195216(14195216),
        e14195217(14195217),
        e14195218(14195218),
        e14195219(14195219),
        e14195220(14195220),
        e14195221(14195221),
        e14195222(14195222),
        e14195223(14195223),
        e14195224(14195224),
        e14195225(14195225),
        e14195226(14195226),
        e14195227(14195227),
        e14195228(14195228),
        e14195229(14195229),
        e14195230(14195230),
        e14195231(14195231),
        e14195232(14195232),
        e14195233(14195233),
        e14195234(14195234),
        e14195235(14195235),
        e14195236(14195236),
        e14195237(14195237),
        e14195238(14195238),
        e14195239(14195239),
        e14195240(14195240),
        e14195241(14195241),
        e14195242(14195242),
        e14195243(14195243),
        e14195244(14195244),
        e14195245(14195245),
        e14195246(14195246),
        e14195247(14195247),
        e14195248(14195248),
        e14195249(14195249),
        e14195250(14195250),
        e14195251(14195251),
        e14195252(14195252),
        e14195253(14195253),
        e14195254(14195254),
        e14195255(14195255),
        e14195256(14195256),
        e14195257(14195257),
        e14195258(14195258),
        e14195259(14195259),
        e14195260(14195260),
        e14195261(14195261),
        e14195262(14195262),
        e14195263(14195263),
        e14195264(14195264),
        e14195265(14195265),
        e14195266(14195266),
        e14195267(14195267),
        e14195268(14195268),
        e14195269(14195269),
        e14195270(14195270),
        e14195271(14195271),
        e14195272(14195272),
        e14195273(14195273),
        e14195274(14195274),
        e14195275(14195275),
        e14195276(14195276),
        e14195277(14195277),
        e14195278(14195278),
        e14195279(14195279),
        e14195280(14195280),
        e14195281(14195281),
        e14195282(14195282),
        e14195283(14195283),
        e14195284(14195284),
        e14195285(14195285),
        e14195286(14195286),
        e14195287(14195287),
        e14195288(14195288),
        e14195289(14195289),
        e14195290(14195290),
        e14195291(14195291),
        e14195292(14195292),
        e14195293(14195293),
        e14195294(14195294),
        e14195295(14195295),
        e14195296(14195296),
        e14195297(14195297),
        e14195298(14195298),
        e14195299(14195299),
        e14195300(14195300),
        e14195301(14195301),
        e14195302(14195302),
        e14195303(14195303),
        e14195304(14195304),
        e14195305(14195305),
        e14195306(14195306),
        e14195307(14195307),
        e14195308(14195308),
        e14195309(14195309),
        e14195310(14195310),
        e14195311(14195311),
        e14195312(14195312),
        e14195313(14195313),
        e14195314(14195314),
        e14195315(14195315),
        e14195316(14195316),
        e14195317(14195317),
        e14195318(14195318),
        e14195319(14195319),
        e14195320(14195320),
        e14195321(14195321),
        e14195322(14195322),
        e14195323(14195323),
        e14195324(14195324),
        e14195325(14195325),
        e14195326(14195326),
        e14195327(14195327),
        e14195328(14195328),
        e14195329(14195329),
        e14195330(14195330),
        e14195331(14195331),
        e14195332(14195332),
        e14195333(14195333),
        e14195334(14195334),
        e14195335(14195335),
        e14195336(14195336),
        e14195337(14195337),
        e14195338(14195338),
        e14195339(14195339),
        e14195340(14195340),
        e14195341(14195341),
        e14195342(14195342),
        e14195343(14195343),
        e14195344(14195344),
        e14195345(14195345),
        e14195346(14195346),
        e14195347(14195347),
        e14195348(14195348),
        e14195349(14195349),
        e14195350(14195350),
        e14195351(14195351),
        e14195352(14195352),
        e14195353(14195353),
        e14195355(14195355),
        e14195356(14195356),
        e14195357(14195357),
        e14195358(14195358),
        e14195359(14195359),
        e14195360(14195360),
        e14195361(14195361),
        e14195362(14195362),
        e14195363(14195363),
        e14195364(14195364),
        e14195365(14195365),
        e14195369(14195369),
        e14195370(14195370),
        e14195371(14195371),
        e14195372(14195372),
        e14195373(14195373),
        e14195374(14195374),
        e14195375(14195375),
        e14195376(14195376),
        e14195377(14195377),
        e14195378(14195378),
        e14195379(14195379),
        e14195380(14195380),
        e14195381(14195381),
        e14195382(14195382),
        e14195383(14195383),
        e14195384(14195384),
        e14195385(14195385),
        e14195386(14195386),
        e14195387(14195387),
        e14195388(14195388),
        e14195389(14195389),
        e14195390(14195390),
        e14195391(14195391),
        e14195392(14195392),
        e14195393(14195393),
        e14195394(14195394),
        e14195395(14195395),
        e14195396(14195396),
        e14195397(14195397),
        e14195398(14195398),
        e14195399(14195399),
        e14195400(14195400),
        e14195401(14195401),
        e14195402(14195402),
        e14195403(14195403),
        e14195404(14195404),
        e14195405(14195405),
        e14195406(14195406),
        e14195407(14195407),
        e14195408(14195408),
        e14195409(14195409),
        e14195410(14195410),
        e14195411(14195411),
        e14195412(14195412),
        e14195413(14195413),
        e14195414(14195414),
        e14195415(14195415),
        e14195416(14195416),
        e14195417(14195417),
        e14195418(14195418),
        e14195419(14195419),
        e14195420(14195420),
        e14195421(14195421),
        e14195422(14195422),
        e14195423(14195423),
        e14195424(14195424),
        e14195425(14195425),
        e14195426(14195426),
        e14195427(14195427),
        e14195428(14195428),
        e14195429(14195429),
        e14195430(14195430),
        e14195431(14195431),
        e14195432(14195432),
        e14195433(14195433),
        e14195434(14195434),
        e14195435(14195435),
        e14195436(14195436),
        e14195437(14195437),
        e14195438(14195438),
        e14195439(14195439),
        e14195440(14195440),
        e14195441(14195441),
        e14195442(14195442),
        e14195443(14195443),
        e14195444(14195444),
        e14195445(14195445),
        e14195446(14195446),
        e14195447(14195447),
        e14195448(14195448),
        e14195449(14195449),
        e14195450(14195450),
        e14195451(14195451),
        e14195452(14195452),
        e14195453(14195453),
        e14195454(14195454),
        e14195455(14195455),
        e14195456(14195456),
        e14195457(14195457),
        e14195458(14195458),
        e14195459(14195459),
        e14195460(14195460),
        e14195461(14195461),
        e14195462(14195462),
        e14195463(14195463),
        e14195464(14195464),
        e14195465(14195465),
        e14195466(14195466),
        e14195467(14195467),
        e14195468(14195468),
        e14195469(14195469),
        e14195470(14195470),
        e14195471(14195471),
        e14195472(14195472),
        e14195473(14195473),
        e14195474(14195474),
        e14195475(14195475),
        e14195476(14195476),
        e14195477(14195477),
        e14195478(14195478),
        e14195479(14195479),
        e14195480(14195480),
        e14195481(14195481),
        e14195482(14195482),
        e14195483(14195483),
        e14195484(14195484),
        e14195485(14195485),
        e14195486(14195486),
        e14195487(14195487),
        e14195488(14195488),
        e14195489(14195489),
        e14195490(14195490),
        e14195491(14195491),
        e14195492(14195492),
        e14195493(14195493),
        e14195494(14195494),
        e14195495(14195495),
        e14195496(14195496),
        e14195497(14195497),
        e14195498(14195498),
        e14195499(14195499),
        e14195500(14195500),
        e14195501(14195501),
        e14195502(14195502),
        e14195503(14195503),
        e14195504(14195504),
        e14195505(14195505),
        e14195506(14195506),
        e14195507(14195507),
        e14195508(14195508),
        e14195509(14195509),
        e14195510(14195510),
        e14195511(14195511),
        e14195512(14195512),
        e14195513(14195513),
        e14195514(14195514),
        e14195515(14195515),
        e14195516(14195516),
        e14195517(14195517),
        e14195518(14195518),
        e14195519(14195519),
        e14195520(14195520),
        e14195521(14195521),
        e14195522(14195522),
        e14195523(14195523),
        e14195524(14195524),
        e14195525(14195525),
        e14195526(14195526),
        e14195546(14195546),
        e14195547(14195547),
        e14195548(14195548),
        e14195550(14195550),
        e14195551(14195551),
        e14195552(14195552),
        e14195553(14195553),
        e14195563(14195563),
        e14195564(14195564),
        e14195565(14195565),
        e14195566(14195566),
        e14195567(14195567),
        e14195568(14195568),
        e14195569(14195569),
        e14195570(14195570),
        e14195571(14195571),
        e14195572(14195572),
        e14195573(14195573),
        e14195574(14195574),
        e14195575(14195575),
        e14195586(14195586),
        e14195587(14195587),
        e14195588(14195588),
        e14195589(14195589),
        e14195591(14195591),
        e14195592(14195592),
        e14195593(14195593),
        e14195594(14195594),
        e14195595(14195595),
        e14195596(14195596),
        e14195597(14195597),
        e14195598(14195598),
        e14195599(14195599),
        e14195600(14195600),
        e14195601(14195601),
        e14195602(14195602),
        e14195603(14195603),
        e14195623(14195623),
        e14195624(14195624),
        e14195625(14195625),
        e14195635(14195635),
        e14195636(14195636),
        e14195643(14195643),
        e14195644(14195644),
        e14195645(14195645),
        e14195646(14195646),
        e14195647(14195647),
        e14195648(14195648),
        e14195663(14195663),
        e14195664(14195664),
        e14195665(14195665),
        e14195666(14195666),
        e14195667(14195667),
        e14195668(14195668),
        e14195669(14195669),
        e14195670(14195670),
        e14195671(14195671),
        e14195672(14195672),
        e14195673(14195673),
        e14195674(14195674),
        e14195675(14195675),
        e14195676(14195676),
        e14195677(14195677),
        e14195678(14195678),
        e14195679(14195679),
        e14195680(14195680),
        e14195681(14195681),
        e14195682(14195682),
        e14195683(14195683),
        e14195684(14195684),
        e14195685(14195685),
        e14195686(14195686),
        e14195687(14195687),
        e14195688(14195688),
        e14195689(14195689),
        e14195690(14195690),
        e14195691(14195691),
        e14195692(14195692),
        e14195693(14195693),
        e14195694(14195694),
        e14195695(14195695),
        e14195696(14195696),
        e14195697(14195697),
        e14195698(14195698),
        e14195699(14195699),
        e14195700(14195700),
        e14195701(14195701),
        e14195702(14195702),
        e14195703(14195703),
        e14195704(14195704),
        e14195705(14195705),
        e14195706(14195706),
        e14195707(14195707),
        e14195708(14195708),
        e14195709(14195709),
        e14195710(14195710),
        e14195711(14195711),
        e14195712(14195712),
        e14195713(14195713),
        e14195714(14195714),
        e14195715(14195715),
        e14195716(14195716),
        e14195717(14195717),
        e14195718(14195718),
        e14195719(14195719),
        e14195723(14195723),
        e14195727(14195727),
        e14195731(14195731),
        e14195735(14195735),
        e14195739(14195739),
        e14195740(14195740),
        e14195741(14195741),
        e14195742(14195742),
        e14195743(14195743),
        e14195744(14195744),
        e14195745(14195745),
        e14195746(14195746),
        e14195747(14195747),
        e14195748(14195748),
        e14195749(14195749),
        e14195750(14195750),
        e14195751(14195751),
        e14195752(14195752),
        e14195753(14195753),
        e14195754(14195754),
        e14195755(14195755),
        e14195756(14195756),
        e14195757(14195757),
        e14195758(14195758),
        e14195759(14195759),
        e14195760(14195760),
        e14195761(14195761),
        e14195762(14195762),
        e14195763(14195763),
        e14195764(14195764),
        e14195765(14195765),
        e14195766(14195766),
        e14195767(14195767),
        e14195768(14195768),
        e14195769(14195769),
        e14195770(14195770),
        e14195771(14195771),
        e14195772(14195772),
        e14195773(14195773),
        e14195774(14195774),
        e14195775(14195775),
        e14195776(14195776),
        e14195777(14195777),
        e14195778(14195778),
        e14195779(14195779),
        e14195787(14195787),
        e14195818(14195818),
        e14195824(14195824),
        e14195827(14195827),
        e14195830(14195830),
        e14195832(14195832),
        e14195835(14195835),
        e14195841(14195841),
        e14195842(14195842),
        e14195843(14195843),
        e14195844(14195844),
        e14195845(14195845),
        e14195846(14195846),
        e14195847(14195847),
        e14195848(14195848),
        e14195849(14195849),
        e14195850(14195850),
        e14195851(14195851),
        e14195852(14195852),
        e14195853(14195853),
        e14195854(14195854),
        e14195855(14195855),
        e14195856(14195856),
        e14195857(14195857),
        e14195858(14195858),
        e14195859(14195859),
        e14195860(14195860),
        e14195861(14195861),
        e14195862(14195862),
        e14195863(14195863),
        e14195882(14195882),
        e14195883(14195883),
        e14195884(14195884),
        e14195885(14195885),
        e14195886(14195886),
        e14195887(14195887),
        e14195888(14195888),
        e14195889(14195889),
        e14195890(14195890),
        e14195891(14195891),
        e14195892(14195892),
        e14195893(14195893),
        e14195894(14195894),
        e14195895(14195895),
        e14195896(14195896),
        e14195897(14195897),
        e14195898(14195898),
        e14195899(14195899),
        e14195900(14195900),
        e14195901(14195901),
        e14195902(14195902),
        e14195903(14195903),
        e14195904(14195904),
        e14195905(14195905),
        e14195906(14195906),
        e14195907(14195907),
        e14195908(14195908),
        e14195909(14195909),
        e14195910(14195910),
        e14195911(14195911),
        e14195912(14195912),
        e14195913(14195913),
        e14195914(14195914),
        e14195915(14195915),
        e14195931(14195931),
        e14195932(14195932),
        e14195933(14195933),
        e14195934(14195934),
        e14195935(14195935),
        e14195936(14195936),
        e14195937(14195937),
        e14195938(14195938),
        e14195939(14195939),
        e14195940(14195940),
        e14195941(14195941),
        e14195942(14195942),
        e14195943(14195943),
        e14195944(14195944),
        e14195945(14195945),
        e14195946(14195946),
        e14195947(14195947),
        e14195948(14195948),
        e14195949(14195949),
        e14195950(14195950),
        e14195951(14195951),
        e14195952(14195952),
        e14195953(14195953),
        e14195954(14195954),
        e14195955(14195955),
        e14195956(14195956),
        e14195957(14195957),
        e14195958(14195958),
        e14195959(14195959),
        e14195960(14195960),
        e14195961(14195961),
        e14195962(14195962),
        e14195963(14195963),
        e14195964(14195964),
        e14195965(14195965),
        e14195966(14195966),
        e14195967(14195967),
        e14195968(14195968),
        e14195969(14195969),
        e14195970(14195970),
        e14195971(14195971),
        e14195972(14195972),
        e14195973(14195973),
        e14195974(14195974),
        e14195975(14195975),
        e14195976(14195976),
        e14195977(14195977),
        e14195978(14195978),
        e14195979(14195979),
        e14195980(14195980),
        e14195981(14195981),
        e14195982(14195982),
        e14195983(14195983),
        e14195984(14195984),
        e14195985(14195985),
        e14195986(14195986),
        e14195987(14195987),
        e14195988(14195988),
        e14195989(14195989),
        e14195990(14195990),
        e14195991(14195991),
        e14195992(14195992),
        e14195993(14195993),
        e14195994(14195994),
        e14195995(14195995),
        e14195996(14195996),
        e14195997(14195997),
        e14195998(14195998),
        e14195999(14195999),
        e14196000(14196000),
        e14196001(14196001),
        e14196002(14196002),
        e14196003(14196003),
        e14196004(14196004),
        e14196005(14196005),
        e14196006(14196006),
        e14196007(14196007),
        e14196008(14196008),
        e14196009(14196009),
        e14196010(14196010),
        e14196011(14196011),
        e14196012(14196012),
        e14196013(14196013),
        e14196014(14196014),
        e14196015(14196015),
        e14196016(14196016),
        e14196017(14196017),
        e14196018(14196018),
        e14196019(14196019),
        e14196020(14196020),
        e14196021(14196021),
        e14196022(14196022),
        e14196023(14196023),
        e14196024(14196024),
        e14196025(14196025),
        e14196026(14196026),
        e14196027(14196027),
        e14196028(14196028),
        e14196029(14196029),
        e14196030(14196030),
        e14196031(14196031),
        e14196032(14196032),
        e14196033(14196033),
        e14196034(14196034),
        e14196035(14196035),
        e14196036(14196036),
        e14196037(14196037),
        e14196038(14196038),
        e14196039(14196039),
        e14196040(14196040),
        e14196041(14196041),
        e14196042(14196042),
        e14196043(14196043),
        e14196044(14196044),
        e14196045(14196045),
        e14196046(14196046),
        e14196047(14196047),
        e14196048(14196048),
        e14196049(14196049),
        e14196050(14196050),
        e14196051(14196051),
        e14196052(14196052),
        e14196053(14196053),
        e14196054(14196054),
        e14196055(14196055),
        e14196056(14196056),
        e14196057(14196057),
        e14196058(14196058),
        e14196059(14196059),
        e14196060(14196060),
        e14196081(14196081),
        e14196082(14196082),
        e14196083(14196083),
        e14196084(14196084),
        e14196085(14196085),
        e14196086(14196086),
        e14196087(14196087),
        e14196088(14196088),
        e14196089(14196089),
        e14196090(14196090),
        e14196091(14196091),
        e14196092(14196092),
        e14196093(14196093),
        e14196094(14196094),
        e14196095(14196095),
        e14196096(14196096),
        e14196097(14196097),
        e14196098(14196098),
        e14196099(14196099),
        e14196100(14196100),
        e14196101(14196101),
        e14196102(14196102),
        e14196103(14196103),
        e14196104(14196104),
        e14196105(14196105),
        e14196106(14196106),
        e14196107(14196107),
        e14196108(14196108),
        e14196109(14196109),
        e14196110(14196110),
        e14196111(14196111),
        e14196112(14196112),
        e14196113(14196113),
        e14196114(14196114),
        e14196115(14196115),
        e14196116(14196116),
        e14196117(14196117),
        e14196118(14196118),
        e14196119(14196119),
        e14196120(14196120),
        e14196121(14196121),
        e14196122(14196122),
        e14196123(14196123),
        e14196124(14196124),
        e14196125(14196125),
        e14196126(14196126),
        e14196127(14196127),
        e14196128(14196128),
        e14196129(14196129),
        e14196130(14196130),
        e14196131(14196131),
        e14196132(14196132),
        e14196133(14196133),
        e14196134(14196134),
        e14196135(14196135),
        e14196136(14196136),
        e14196137(14196137),
        e14196138(14196138),
        e14196139(14196139),
        e14196140(14196140),
        e14196141(14196141),
        e14196142(14196142),
        e14196143(14196143),
        e14196144(14196144),
        e14196145(14196145),
        e14196146(14196146),
        e14196147(14196147),
        e14196148(14196148),
        e14196149(14196149),
        e14196150(14196150),
        e14196151(14196151),
        e14196152(14196152),
        e14196153(14196153),
        e14196154(14196154),
        e14196155(14196155),
        e14196156(14196156),
        e14196157(14196157),
        e14196158(14196158),
        e14196159(14196159),
        e14196160(14196160),
        e14196161(14196161),
        e14196162(14196162),
        e14196163(14196163),
        e14196164(14196164),
        e14196165(14196165),
        e14196166(14196166),
        e14196167(14196167),
        e14196168(14196168),
        e14196169(14196169),
        e14196170(14196170),
        e14196171(14196171),
        e14196172(14196172),
        e14196173(14196173),
        e14196174(14196174),
        e14196175(14196175),
        e14196176(14196176),
        e14196177(14196177),
        e14196178(14196178),
        e14196179(14196179),
        e14196180(14196180),
        e14196181(14196181),
        e14196182(14196182),
        e14196183(14196183),
        e14196184(14196184),
        e14196185(14196185),
        e14196186(14196186),
        e14196187(14196187),
        e14196188(14196188),
        e14196189(14196189),
        e14196190(14196190),
        e14196191(14196191),
        e14196192(14196192),
        e14196193(14196193),
        e14196194(14196194),
        e14196195(14196195),
        e14196196(14196196),
        e14196197(14196197),
        e14196198(14196198),
        e14196199(14196199),
        e14196200(14196200),
        e14196201(14196201),
        e14196202(14196202),
        e14196203(14196203),
        e14196204(14196204),
        e14196205(14196205),
        e14196206(14196206),
        e14196207(14196207),
        e14196208(14196208),
        e14196209(14196209),
        e14196210(14196210),
        e14196211(14196211),
        e14196212(14196212),
        e14196213(14196213),
        e14196214(14196214),
        e14196215(14196215),
        e14196216(14196216),
        e14196217(14196217),
        e14196218(14196218),
        e14196219(14196219),
        e14196220(14196220),
        e14196221(14196221),
        e14196222(14196222),
        e14196223(14196223),
        e14196224(14196224),
        e14196225(14196225),
        e14196226(14196226),
        e14196227(14196227),
        e14196228(14196228),
        e14196229(14196229),
        e14196230(14196230),
        e14196231(14196231),
        e14196232(14196232),
        e14196233(14196233),
        e14196234(14196234),
        e14196235(14196235),
        e14196236(14196236),
        e14196237(14196237),
        e14196238(14196238),
        e14196239(14196239),
        e14196240(14196240),
        e14196241(14196241),
        e14196242(14196242),
        e14196244(14196244),
        e14196245(14196245),
        e14196246(14196246),
        e14196247(14196247),
        e14196248(14196248),
        e14196249(14196249),
        e14196250(14196250),
        e14196251(14196251),
        e14196252(14196252),
        e14196253(14196253),
        e14196254(14196254),
        e14196255(14196255),
        e14196256(14196256),
        e14196257(14196257),
        e14196258(14196258),
        e14196259(14196259),
        e14196260(14196260),
        e14196261(14196261),
        e14196262(14196262),
        e14196263(14196263),
        e14196264(14196264),
        e14196265(14196265),
        e14196266(14196266),
        e14196267(14196267),
        e14196268(14196268),
        e14196269(14196269),
        e14196270(14196270),
        e14196271(14196271),
        e14196272(14196272),
        e14196273(14196273),
        e14196274(14196274),
        e14196275(14196275),
        e14196276(14196276),
        e14196277(14196277),
        e14196278(14196278),
        e14196279(14196279),
        e14196280(14196280),
        e14196281(14196281),
        e14196282(14196282),
        e14196283(14196283),
        e14196284(14196284),
        e14196285(14196285),
        e14196286(14196286),
        e14196287(14196287),
        e14196288(14196288),
        e14196289(14196289),
        e14196290(14196290),
        e14196291(14196291),
        e14196292(14196292),
        e14196293(14196293),
        e14196294(14196294),
        e14196295(14196295),
        e14196296(14196296),
        e14196297(14196297),
        e14196298(14196298),
        e14196299(14196299),
        e14196300(14196300),
        e14196301(14196301),
        e14196302(14196302),
        e14196303(14196303),
        e14196304(14196304),
        e14196305(14196305),
        e14196306(14196306),
        e14196307(14196307),
        e14196308(14196308),
        e14196309(14196309),
        e14196310(14196310),
        e14196311(14196311),
        e14196312(14196312),
        e14196313(14196313),
        e14196314(14196314),
        e14196315(14196315),
        e14196316(14196316),
        e14196317(14196317),
        e14196318(14196318),
        e14196319(14196319),
        e14196320(14196320),
        e14196321(14196321),
        e14196322(14196322),
        e14196323(14196323),
        e14196324(14196324),
        e14196325(14196325),
        e14196326(14196326),
        e14196327(14196327),
        e14196328(14196328),
        e14196329(14196329),
        e14196335(14196335),
        e14196336(14196336),
        e14196337(14196337),
        e14196338(14196338),
        e14196339(14196339),
        e14196340(14196340),
        e14196341(14196341),
        e14196342(14196342),
        e14196343(14196343),
        e14196344(14196344),
        e14196345(14196345),
        e14196346(14196346),
        e14196347(14196347),
        e14196348(14196348),
        e14196349(14196349),
        e14196350(14196350),
        e14196351(14196351),
        e14196352(14196352),
        e14196353(14196353),
        e14196354(14196354),
        e14196355(14196355),
        e14196356(14196356),
        e14196361(14196361),
        e14196362(14196362),
        e14196363(14196363),
        e14196364(14196364),
        e14196365(14196365),
        e14196366(14196366),
        e14196367(14196367),
        e14196368(14196368),
        e14196369(14196369),
        e14196370(14196370),
        e14196371(14196371),
        e14196372(14196372),
        e14196373(14196373),
        e14196374(14196374),
        e14196375(14196375),
        e14196376(14196376),
        e14196377(14196377),
        e14196378(14196378),
        e14196379(14196379),
        e14196380(14196380),
        e14196381(14196381),
        e14196382(14196382),
        e14196383(14196383),
        e14196384(14196384),
        e14196385(14196385),
        e14196386(14196386),
        e14196387(14196387),
        e14196388(14196388),
        e14196389(14196389),
        e14196390(14196390),
        e14196391(14196391),
        e14196392(14196392),
        e14196393(14196393),
        e14196394(14196394),
        e14196395(14196395),
        e14196396(14196396),
        e14196397(14196397),
        e14196398(14196398),
        e14196399(14196399),
        e14196400(14196400),
        e14196401(14196401),
        e14196402(14196402),
        e14196403(14196403),
        e14196404(14196404),
        e14196405(14196405),
        e14196406(14196406),
        e14196407(14196407),
        e14196408(14196408),
        e14196409(14196409),
        e14196410(14196410),
        e14196411(14196411),
        e14196412(14196412),
        e14196413(14196413),
        e14196414(14196414),
        e14196415(14196415),
        e14196416(14196416),
        e14196417(14196417),
        e14196418(14196418),
        e14196419(14196419),
        e14196420(14196420),
        e14196421(14196421),
        e14196422(14196422),
        e14196423(14196423),
        e14196424(14196424),
        e14196425(14196425),
        e14196426(14196426),
        e14196427(14196427),
        e14196428(14196428),
        e14196429(14196429),
        e14196430(14196430),
        e14196431(14196431),
        e14196432(14196432),
        e14196433(14196433),
        e14196434(14196434),
        e14196435(14196435),
        e14196436(14196436),
        e14196437(14196437),
        e14196438(14196438),
        e14196439(14196439),
        e14196440(14196440),
        e14196441(14196441),
        e14196442(14196442),
        e14196443(14196443),
        e14196444(14196444),
        e14196445(14196445),
        e14196446(14196446),
        e14196447(14196447),
        e14196448(14196448),
        e14196449(14196449),
        e14196450(14196450),
        e14196451(14196451),
        e14196452(14196452),
        e14196453(14196453),
        e14196454(14196454),
        e14196455(14196455),
        e14196456(14196456),
        e14196457(14196457),
        e14196458(14196458),
        e14196459(14196459),
        e14196460(14196460),
        e14196461(14196461),
        e14196462(14196462),
        e14196463(14196463),
        e14196464(14196464),
        e14196465(14196465),
        e14196470(14196470),
        e14196471(14196471),
        e14196472(14196472),
        f14522386(14522386),
        f14523652(14523652),
        f14523659(14523659),
        f14523660(14523660),
        f14523661(14523661),
        f14527296(14527296),
        f14527302(14527302),
        f14527312(14527312),
        f14527340(14527340),
        f14527344(14527344),
        f14527352(14527352),
        f14527357(14527357),
        f14527365(14527365),
        f14527367(14527367),
        f14527371(14527371),
        f14527380(14527380),
        f14527403(14527403),
        f14527405(14527405),
        f14527407(14527407),
        f14527409(14527409),
        f14527413(14527413),
        f14527415(14527415),
        f14527419(14527419),
        f14527420(14527420),
        f14527424(14527424),
        f14527440(14527440),
        f14527449(14527449),
        f14527457(14527457),
        f14527462(14527462),
        f14527474(14527474),
        f14527476(14527476),
        f14527481(14527481),
        f14527486(14527486),
        f14527500(14527500),
        f14527503(14527503),
        f14527518(14527518),
        f14527575(14527575),
        f14527577(14527577),
        f14527758(14527758),
        f14527787(14527787),
        f14527789(14527789),
        f14527797(14527797),
        f14527799(14527799),
        f14527802(14527802),
        f14527804(14527804),
        f14527806(14527806),
        f14527808(14527808),
        f14527810(14527810),
        f14527812(14527812),
        f14527975(14527975),
        f14528057(14528057),
        f14528819(14528819),
        f14528854(14528854),
        f14528856(14528856),
        f14528883(14528883),
        f14528888(14528888),
        f14528893(14528893),
        f14528897(14528897),
        f14529259(14529259),
        f14529310(14529310),
        f14529318(14529318),
        f14529327(14529327),
        f14529445(14529445),
        f14529459(14529459),
        f14529479(14529479),
        f14529671(14529671),
        f14530011(14530011),
        f14530050(14530050),
        f14530090(14530090),
        f14530445(14530445),
        f14530467(14530467),
        f14530919(14530919),
        f14530921(14530921),
        f14531402(14531402),
        f14531414(14531414),
        f14531419(14531419),
        f14531448(14531448),
        f14531455(14531455),
        f14531519(14531519),
        f14531529(14531529),
        f14531541(14531541),
        f14531560(14531560),
        f14532517(14532517),
        f14532527(14532527),
        f14532531(14532531),
        f14532533(14532533),
        f14532550(14532550),
        f14532563(14532563),
        f14532565(14532565),
        f14533159(14533159),
        f14533161(14533161),
        f14533342(14533342),
        f14533344(14533344),
        f14533349(14533349),
        f14533371(14533371),
        f14533374(14533374),
        f14533376(14533376),
        f14533378(14533378),
        f14533380(14533380),
        f14533382(14533382),
        f14533589(14533589)
    }

CucsConditionLifecycle ::= TEXTUAL-CONVENTION
    STATUS        current
    DESCRIPTION
        ""
    SYNTAX        BITS
    {
        flapping(0),
        soakingClear(1),
        soakingRaise(2),
        suppressed(3),
        pinned(4)
    }

CucsConditionRemoteInvRslt ::= TEXTUAL-CONVENTION
    STATUS        current
    DESCRIPTION
        ""
    SYNTAX        BITS
    {
        failure(0),
        unidentifiedFail(1),
        internalError(2),
        timeout(3),
        endPointUnavailable(4),
        endPointFailed(5),
        endPointProtocolError(6),
        swDefect(7),
        fwDefect(8),
        hwDefect(9),
        resourceUnavailable(10),
        resourceCapacityExceeded(11),
        resourceDependency(12),
        capabilityNotImplementedIgnore(13),
        capabilityNotImplementedFailure(14),
        capabilityNotSupported(15),
        capabilityUnavailable(16),
        serviceNotImplementedIgnore(17),
        serviceNotImplementedFail(18),
        serviceNotSupported(19),
        serviceUnavailable(20),
        serviceProtocolError(21),
        fruIdentityIndeterminate(22),
        fruInfoMalformed(23),
        illegalFru(24),
        fruStateIndeterminate(25),
        fruNotReady(26),
        extendTimeout(27),
        taskReset(28),
        fruNotSupported(29),
        intermittentError(30)
    }

CucsConditionRule ::= TEXTUAL-CONVENTION
    STATUS        current
    DESCRIPTION
        ""
    SYNTAX        INTEGER
    {
        generic(0),
        sysdebugCoreCoreFile(5),
        mgmtImportItemImportxmlerror(33),
        fabricComputeSlotEpMisplacedInChassisSlot(156),
        fabricComputeSlotEpServerIdentificationProblem(157),
        vnicEtherConfigFailed(169),
        vnicFcConfigFailed(170),
        processorUnitInoperable(174),
        processorUnitThermalNonCritical(175),
        processorUnitThermalThresholdCritical(176),
        processorUnitThermalThresholdNonRecoverable(177),
        processorUnitVoltageThresholdNonCritical(178),
        processorUnitVoltageThresholdCritical(179),
        processorUnitVoltageThresholdNonRecoverable(180),
        storageLocalDiskInoperable(181),
        storageItemCapacityExceeded(182),
        storageItemCapacityWarning(183),
        memoryUnitDegraded(184),
        memoryUnitInoperable(185),
        memoryUnitThermalThresholdNonCritical(186),
        memoryUnitThermalThresholdCritical(187),
        memoryUnitThermalThresholdNonRecoverable(188),
        memoryArrayVoltageThresholdNonCritical(189),
        memoryArrayVoltageThresholdCritical(190),
        memoryArrayVoltageThresholdNonRecoverable(191),
        extpolRegistryServiceRegistryVersionMismatch(193),
        extpolProviderProviderVersionMismatch(194),
        extpolControllerControllerVersionMismatch(195),
        extpolClientClientVersionMismatch(196),
        adaptorUnitUnidentifiableFru(200),
        adaptorUnitMissing(203),
        adaptorUnitAdaptorReachability(206),
        adaptorHostIfLinkDown(207),
        identpoolElementDuplicatedAssigned(208),
        identpoolElementDuplicatedDefined(209),
        firmwareSourceRemoteDownloadFailure(241),
        firmwareDownloadPolicyError(242),
        computeGroupMembershipGroupMembershipStateFault(261),
        computeGroupMembershipGroupMembershipGroupFault(262),
        orgDomainGroupPolicyUcsGroupingPolicyFault(263),
        portPioLinkDown(276),
        portPioFailed(277),
        portPioHardwareFailure(278),
        portPioSfpNotPresent(279),
        fabricExternalPcDown(282),
        dcxVcDown(283),
        networkElementInoperable(291),
        mgmtEntityDegraded(293),
        mgmtEntityDown(294),
        dcxNsFailed(304),
        computePhysicalInsufficientlyEquipped(305),
        computePhysicalIdentityUnestablishable(306),
        computeBoardPowerError(310),
        computePhysicalPowerProblem(311),
        computePhysicalThermalProblem(312),
        computePhysicalBiosPostTimeout(313),
        computePhysicalDiscoveryFailed(314),
        computePhysicalAssociationFailed(315),
        computePhysicalInoperable(317),
        computePhysicalUnassignedMissing(318),
        computePhysicalAssignedMissing(319),
        computePhysicalUnidentified(320),
        computePhysicalUnassignedInaccessible(321),
        computePhysicalAssignedInaccessible(322),
        lsServerFailed(324),
        lsServerDiscoveryFailed(326),
        lsServerConfigFailure(327),
        lsServerMaintenanceFailed(329),
        lsServerRemoved(330),
        lsServerInaccessible(331),
        lsServerAssociationFailed(332),
        lsServerUnassociated(334),
        storageItemSpeedLowsd(336),
        storageItemSpeedDegradedsd(337),
        storageItemSpeedWarningsd(338),
        etherSwitchIntfioSatelliteConnectionAbsent(367),
        etherSwitchIntfioSatelliteWiringProblem(368),
        equipmentPsuPowerSupplyProblem(369),
        equipmentFanDegraded(371),
        equipmentFanInoperable(373),
        equipmentPsuInoperable(374),
        equipmentIocardRemoved(376),
        equipmentFanModuleMissing(377),
        equipmentPsuMissing(378),
        equipmentIocardThermalProblem(379),
        equipmentFanModuleThermalThresholdNonCritical(380),
        equipmentPsuThermalThresholdNonCritical(381),
        equipmentFanModuleThermalThresholdCritical(382),
        equipmentPsuThermalThresholdCritical(383),
        equipmentFanModuleThermalThresholdNonRecoverable(384),
        equipmentPsuThermalThresholdNonRecoverable(385),
        equipmentPsuVoltageThresholdNonCritical(387),
        vnicFcIfVsanUnresolvable(388),
        equipmentPsuVoltageThresholdCritical(389),
        vnicEtherIfVlanSyncFault(391),
        vnicFcIfVsanSyncFault(392),
        vnicEtherUnassociatedVnicIfFault(393),
        vnicFcUnassociatedVnicIfFault(394),
        equipmentFanPerfThresholdNonCritical(395),
        lsSpmetaUngroupedDomain(396),
        equipmentFanPerfThresholdNonRecoverable(397),
        equipmentIocardFirmwareUpgrade(398),
        equipmentChassisUnsupportedConnectivity(399),
        equipmentChassisUnacknowledged(400),
        equipmentIocardUnsupportedConnectivity(401),
        equipmentIocardUnacknowledged(402),
        equipmentIocardPeerDisconnected(403),
        equipmentChassisIdentity(404),
        equipmentIocardIdentity(405),
        equipmentFanModuleIdentity(406),
        equipmentPsuIdentity(407),
        equipmentChassisPowerProblem(408),
        equipmentChassisThermalThresholdCritical(409),
        equipmentChassisThermalThresholdNonCritical(410),
        equipmentChassisThermalThresholdNonRecoverable(411),
        computeBoardCmosVoltageThresholdCritical(424),
        computeBoardCmosVoltageThresholdNonRecoverable(425),
        mgmtEntityElectionFailure(428),
        mgmtEntityHaNotReady(429),
        mgmtEntityVersionIncompatible(430),
        equipmentFanMissing(434),
        equipmentIocardAutoUpgradingFirmware(435),
        firmwarePackItemImageMissing(436),
        etherSwitchIntfioSatelliteWiringNumbersUnexpected(440),
        mgmtEntityManagementServicesFailure(451),
        mgmtEntityManagementServicesUnresponsive(452),
        mgmtEntityDevice1SharedStorageError(453),
        mgmtEntityDevice2SharedStorageError(454),
        mgmtEntityDevice3SharedStorageError(455),
        equipmentChassisInoperable(456),
        etherServerIntfioHardwareFailure(458),
        dcxVcMgmtVifDown(459),
        sysdebugMepLogMEpLogLog(460),
        sysdebugMepLogMEpLogVeryLow(461),
        sysdebugMepLogMEpLogFull(462),
        computePoolEmpty(463),
        uuidpoolPoolEmpty(464),
        ippoolPoolEmpty(465),
        macpoolPoolEmpty(466),
        firmwareUpdatableImageUnusable(470),
        firmwareBootUnitCantBoot(471),
        fcpoolInitiatorsEmpty(476),
        equipmentIocardInaccessible(478),
        dcxVifLinkState(479),
        equipmentFanModuleDegraded(480),
        equipmentIocardPostFailure(481),
        equipmentFanPerfThresholdLowerNonRecoverable(484),
        memoryUnitIdentityUnestablishable(502),
        computePhysicalPostFailure(517),
        equipmentPsuOffline(528),
        sysdebugMepLogTransferError(530),
        configDbConfigStatsDbError(536),
        computeAoperationRemoteOperationFail(558),
        storageRaidBatteryInoperable(560),
        computeRtcBatteryInoperable(561),
        lsIssuesConfigFailure(571),
        vnicFaultVlanSyncFault(572),
        vnicMgmtIfVlanUnresolvable(573),
        vnicMgmtIfVlanAccessFault(574),
        vnicMgmtIfVlanSyncFault(575),
        vnicMgmtUnassociatedVnicIfFault(576),
        memoryBufferUnitThermalThresholdNonCritical(577),
        memoryBufferUnitThermalThresholdCritical(578),
        memoryBufferUnitThermalThresholdNonRecoverable(579),
        computeIohubThermalNonCritical(582),
        computeIohubThermalThresholdCritical(583),
        computeIohubThermalThresholdNonRecoverable(584),
        equipmentChassisIdentityUnestablishable(587),
        licenseInstanceGracePeriodWarning1(591),
        licenseInstanceGracePeriodWarning2(592),
        queryUsageContextTimeout(593),
        queryUsageContextFailed(594),
        queryDependencyContextTimeout(595),
        queryDependencyContextFailed(596),
        queryImportContextTimeout(597),
        queryImportContextFailed(598),
        licenseFileFileNotDeleted(599),
        configBackupUngroupedDomain(616),
        fabricLanPinGroupEmpty(621),
        fabricSanPinGroupEmpty(622),
        adaptorExtEthIfMisConnect(625),
        computeRemoteOpStatusRemoteOpFailed(634),
        swVlanPortNsResourceStatus(635),
        extpolClientClientNotReachable(644),
        mgmtExportPolicyNoSchedulerExists(645),
        fabricVlanPrimaryVlanMissingIsolated(646),
        mgmtIfMisConnect(654),
        storageMetaGlobalArrayStorageArrayNotOpted(656),
        storageMetaDomainGroupMissing(657),
        storageMetaMissingArrayAutoConfigRef(658),
        storageMetaStorageBladeNotInDiscoveryMode(659),
        storageMetaMissingArrayAutoConfigPolicy(660),
        storageMetaMissingQualifier(661),
        storageMetaMatchingQualifierError(662),
        storageMetaStorageBladeAlreadyInUse(663),
        equipmentFexPostFailure(669),
        equipmentFexIdentity(670),
        powerBudgetPowerBudgetCmcProblem(688),
        lsComputeBindingAssignmentRequirementsNotMet(689),
        powerBudgetPowerBudgetBmcProblem(690),
        powerBudgetPowerBudgetDiscFail(693),
        powerGroupPowerGroupInsufficientBudget(695),
        powerGroupPowerGroupBudgetIncorrect(696),
        adaptorHostEthIfMissing(708),
        portPioInvalidSfp(710),
        mgmtIfMissing(714),
        fabricEthLanPcEpDown(727),
        fabricFcSanPcEpDown(728),
        equipmentIocardThermalThresholdNonCritical(729),
        equipmentIocardThermalThresholdCritical(730),
        equipmentIocardThermalThresholdNonRecoverable(731),
        equipmentChassisSeepromInoperable(733),
        fabricFcSanPcEpIncompatibleSpeed(734),
        fabricFcSanPcIncompatibleSpeed(735),
        extmgmtIfMgmtifdown(736),
        powerChassisMemberPowerGroupCapInsufficient(740),
        powerChassisMemberChassisFirmwareProblem(741),
        powerChassisMemberChassisPsuInsufficient(742),
        powerChassisMemberChassisPsuRedundanceFailure(743),
        powerBudgetPowerCapReachedCommit(744),
        sysdebugAutoCoreFileExportTargetAutoCoreTransferFailure(747),
        smartlicenseEntitlementEnforcementModeFault(750),
        fabricMonSpanConfigFail(757),
        powerBudgetChassisPsuInsufficient(764),
        powerBudgetTstateTransition(765),
        powerPolicyPowerPolicyApplicationFail(766),
        mgmtIfNew(772),
        adaptorExtEthIfMissing(775),
        storageLocalDiskSlotEpUnusable(776),
        fabricEthEstcPcEpDown(777),
        equipmentFexIdentityUnestablishable(778),
        mgmtEntityDevice1SeepromError(791),
        mgmtEntityDevice2SeepromError(792),
        vnicEtherIfPrimaryVlanMissingForIsolated(793),
        vnicEtherIfPrimaryVlanMissingForCommunity(794),
        vnicMgmtIfPrimaryVlanMissingForIsolated(795),
        vnicMgmtIfPrimaryVlanMissingForCommunity(796),
        vnicEtherIfPrimaryVlanAccessFaultForIsolated(797),
        vnicEtherIfPrimaryVlanAccessFaultForCommunity(798),
        vnicMgmtIfPrimaryVlanAccessFaultIsolated(799),
        vnicMgmtIfPrimaryVlanAccessFaultForCommunity(800),
        processorUnitIdentityUnestablishable(801),
        firmwareBootUnitActivateStatusFailed(807),
        fabricDceSwSrvPcEpDown(826),
        fabricInternalPcDown(829),
        fabricEpMgrEpTransModeFail(837),
        mgmtPmonEntryUcsmProcessFailure(846),
        processorUnitDisabled(855),
        computeABoardThermalProblem(857),
        equipmentPsuPowerSupplyShutdown(859),
        iqnpoolPoolEmpty(861),
        fabricVlanMisconfigured(862),
        swEthLanEpMissingPrimaryVlan(865),
        swEthLanPcMissingPrimaryVlan(866),
        memoryUnitDisabled(867),
        computeAboardThermalProblem(869),
        vmVifLinkState(872),
        mgmtEntityHaSshKeysMismatched(874),
        vnicEtherPinningMismatch(875),
        vnicEtherPinningMisconfig(876),
        storageLocalLunInoperable(877),
        equipmentPsuPowerThreshold(878),
        equipmentPsuInputError(879),
        fabricPioEpErrorMisconfigured(880),
        networkElementInventoryFailed(885),
        computeBoardPowerFail(887),
        equipmentSwitchCardPowerOff(890),
        adaptorUnitExtnUnidentifiableFru(900),
        adaptorUnitExtnMissing(901),
        equipmentFexFexUnsupported(902),
        vnicIscsiConfigFailed(903),
        pkiKeyRingStatus(909),
        pkiTpStatus(910),
        computePhysicalDisassociationFailed(915),
        computePhysicalNetworkMisconfigured(916),
        vnicProfileProfileConfigIncorrect(917),
        computeAboardMotherBoardVoltageThresholdUpperNonRecoverable(918),
        computeAboardMotherBoardVoltageThresholdLowerNonRecoverable(919),
        computeAboardMotherBoardVoltageUpperThresholdCritical(920),
        computeAboardMotherBoardVoltageLowerThresholdCritical(921),
        networkElementThermalThresholdCritical(928),
        aaaProviderGroupProvidergroup(943),
        aaaConfigServergroup(944),
        aaaRoleRoleNotDeployed(945),
        aaaLocaleLocaleNotDeployed(946),
        aaaUserRoleUserRoleNotDeployed(947),
        aaaUserLocaleUserLocaleNotDeployed(948),
        pkiKeyRingKeyRingNotDeployed(949),
        commSnmpSyscontactEmpty(950),
        commDateTimeCommTimeZoneInvalid(951),
        aaaUserLocalUserNotDeployed(952),
        commSnmpUserSnmpUserNotDeployed(953),
        commSvcEpCommSvcNotDeployed(954),
        mgmtConnectionDisabled(957),
        mgmtConnectionUnused(958),
        mgmtConnectionUnsupportedConnectivity(959),
        capabilityCatalogueLoadErrors(967),
        storageLocalDiskDegraded(968),
        storageRaidBatteryDegraded(969),
        storageRaidBatteryRelearnAborted(970),
        storageRaidBatteryRelearnFailed(971),
        storageAdefConfigurationError(972),
        storageInitiatorConfigurationError(973),
        storageVsanRefVsanUnresolvable(974),
        storageControllerPatrolReadFailed(975),
        storageControllerInoperable(976),
        storageLocalDiskRebuildFailed(977),
        storageLocalDiskCopybackFailed(978),
        storageVirtualDriveInoperable(979),
        storageVirtualDriveDegraded(980),
        storageVirtualDriveReconstructionFailed(981),
        storageVirtualDriveConsistencyCheckFailed(982),
        extpolClientClientLostConnectivity(1010),
        policyControlEpSuspendModeActive(1017),
        lsIdentityInfoForward990(1023),
        extmgmtArpTargetsArpTargetsNotValid(1037),
        computeAboardPowerUsageProblem(1040),
        fabricFcoeSanPcEpDown(1046),
        fabricFcoeSanEpDown(1047),
        fabricFcoeSanEpUnsupported(1048),
        fabricFcoeSanPcDown(1049),
        fabricFcoeSanPcUnsupported(1050),
        fabricFcoeEstcEpDown(1051),
        fabricPinTargetDown(1052),
        fabricExternalEpFcZoningEnable(1053),
        fabricEthLanEpOverlappingVlan(1054),
        fabricEthLanPcOverlappingVlan(1055),
        fabricFcEstcEpFcStoragePortInvalid(1056),
        fabricFcoeEstcEpFcoeStoragePortInvalid(1057),
        fabricFcSanPcFcPortchannelMembersInvalid(1058),
        computeABoardPowerUsageProblem(1097),
        vnicEtherIfVlanAccessFault(1101),
        vnicEtherIfVlanUnresolvable(1102),
        vnicEtherIfInvalidVlan(1103),
        fabricVlanVlanConflictPermit(1104),
        fabricVlanReqVlanPermitUnresolved(1105),
        fabricVlanGroupReqVlanGroupPermitUnresolved(1106),
        policyConfigErrorPolicyConfigError(1124),
        swVlanPortNsVlancompNotSupport(1202),
        fabricVlanMisconfiguredMcastPolicy(1204),
        fabricVsanMembershipDown(1206),
        callhomeEpNoSnmpPolicyForCallhome(1207),
        aaaOrgLocaleOrgNotPresent(1209),
        vnicFcPinningMisconfig(1216),
        equipmentHealthLedCriticalError(1219),
        equipmentHealthLedMinorError(1220),
        networkOperLevelExtraprimaryvlans(1221),
        pkiKeyRingModulus(1222),
        extpolClientGracePeriodWarning2(1223),
        extpolClientGracePeriodWarning3(1224),
        extpolClientGracePeriodWarning4(1225),
        extpolClientGracePeriodWarning5(1226),
        extpolClientGracePeriodWarning6(1227),
        extpolClientGracePeriodWarning7(1228),
        extpolClientGracePeriodWarning1(1229),
        storageInitiatorDuplicateFcZone(1232),
        storageIniGroupSwitchModeDisabled(1233),
        storageItemFilesystemIssues(1237),
        aaaProviderGroupProvidergroupsize(1258),
        firmwareAutoSyncPolicyDefaultHostPackageMissing(1280),
        firmwareAutoSyncPolicyDefaultHostPackageMissingVersions(1281),
        fabricNetflowMonSessionFlowMonConfigFail(1284),
        fabricNetflowMonSessionNetflowSessionConfigFail(1285),
        fabricPooledVlanNamedVlanUnresolved(1286),
        vnicEtherIfRemoteVlanUnresolvable(1306),
        vnicFcIfRemoteVsanUnresolvable(1307),
        vnicEtherVirtualizationConflict(1308),
        lsIssuesIscsiConfigFailed(1309),
        firmwareBootUnitPowerCycleRequired(1317),
        mgmtControllerUnsupportedDimmBlacklisting(1324),
        mgmtInterfaceInbandVlanFailure(1325),
        extmgmtNdiscTargetsNdiscTargetsNotValid(1327),
        storageLocalDiskMissing(1330),
        storageFlexFlashControllerInoperable(1331),
        storageFlexFlashCardInoperable(1332),
        storageFlexFlashCardMissing(1333),
        storageFlexFlashVirtualDriveDegraded(1334),
        storageFlexFlashVirtualDriveInoperable(1335),
        storageFlexFlashControllerUnhealthy(1336),
        extvmmVmndrefVmNetworkReferenceIncorrect(1337),
        mgmtInterfaceInbandCapIsNotAvailable(1356),
        mgmtInterfaceUnsupportedFirmwareVersion(1357),
        fabricEthLanEpUdldLinkDown(1358),
        fabricEthLanPcEpUdldLinkDown(1359),
        fabricFcoeSanEpUdldLinkDown(1360),
        fabricFcoeSanPcEpUdldLinkDown(1361),
        cimcvmediaActualMountEntryVmediaMountFailed(1366),
        firmwareStatusCimcFirmwareMismatch(1367),
        firmwareStatusPldFirmwareMismatch(1368),
        vnicEtherVirtualizationNetflowConflict(1380),
        storageMezzFlashLifeInoperable(1382),
        lsIssuesKvmPolicyUnsupported(1383),
        fabricVlanPrimaryVlanMissingForIsolated(1385),
        fabricVlanPrimaryVlanMissingForCommunity(1386),
        fabricVlanErrorAssocPrimary(1388),
        fabricVlanMismatchA(1389),
        fabricVlanMismatchB(1390),
        mgmtBackupPolicyConfigConfigurationBackupOutdated(1391),
        lsServerSvnicNotPresent(1396),
        networkOperLevelExtrasecondaryvlans(1397),
        swVlanExtrasecondaryvlansperprimary(1398),
        sysdebugLogExportStatusLogExportFailure(1402),
        mgmtInterfaceNamedInbandVlanUnresolved(1419),
        mgmtInterfaceInbandUnsupportedServer(1420),
        mgmtInterfaceInbandUnsupportedFirmware(1421),
        storageMezzFlashLifeConfigurationError(1428),
        storageMezzFlashLifeDegraded(1429),
        storageFlexFlashControllerMismatch(1430),
        storageFlexFlashDriveUnhealthy(1431),
        storageFlexFlashCardUnhealthy(1432),
        poolElementDuplicatedAssigned(1433),
        computePhysicalAdapterMismatch(1434),
        equipmentTpmSlaveTpm(1437),
        swVlanPortNsResourceStatusWarning(1438),
        networkElementMemoryerror(1439),
        memoryNvDimmControllerInoperable(1472),
        memoryNvDimmControllerDegraded(1473),
        memoryNvDimmBatteryThermalIssueCritical(1474),
        memoryNvDimmBatteryThermalIssueNonRecoverable(1475),
        memoryNvDimmBatteryInsufficientCharge(1476),
        memoryNvDimmBatteryHealthDegraded(1477),
        memoryNvDimmBatteryHealthInoperable(1478),
        lstorageArrayAssociationFailed(1480),
        lstorageArrayControllerProfileCount(1481),
        lstorageProcessorConfigFailure(1482),
        lstorageBackstorePoolEmpty(1483),
        networkElementRemoved(1493),
        powerBudgetChassisPsuMixedMode(1498),
        powerBudgetPowerBudgetUnavailable(1499),
        storageVolumeSmallVolumeSpace(1501),
        storageVolumeNoVolumeSpace(1502),
        storageEnclosureDrawerOpen(1503),
        storageDiskGroupOffline(1504),
        storageDiskGroupDegraded(1505),
        storageDiskGroupRebuilding(1506),
        storageDiskGroupBad(1507),
        storageScsiLunInstRefOffline(1508),
        storageProcessorComputeInoperable(1509),
        storageProcessorComputeDegraded(1510),
        storageProcessorCimcBackupTriggerNotEnabled(1511),
        storageProcessorCimcHeartbeatTimedOut(1512),
        storageProcessorMgmtInaccessible(1513),
        storageProcessorStorageNotReady(1514),
        storageProcessorElectionFailure(1515),
        storageProcessorHaDegraded(1516),
        storageDiskEnvStatsDiskWearNonCriticalThreshold(1517),
        storageDiskEnvStatsDiskWearCriticalThreshold(1518),
        storageLocalDiskInaccessible(1519),
        storageScsiLunDeploymentFailure(1520),
        storageLunReplicaDeploymentFailure(1521),
        storageLunSnapshotDeploymentFailure(1522),
        storageLunMaskGroupDeploymentFailure(1523),
        equipmentChassisInvalidFru(1558),
        equipmentSwitchiocardRemoved(1559),
        equipmentSwitchiocardThermalProblem(1560),
        equipmentSwitchiocardThermalThresholdNonCritical(1561),
        equipmentSwitchiocardThermalThresholdCritical(1562),
        equipmentSwitchiocardThermalThresholdNonRecoverable(1563),
        equipmentSwitchiocardPeerDisconnected(1564),
        equipmentSwitchiocardIdentity(1565),
        equipmentSwitchiocardCpuThermalThresholdCritical(1566),
        storageLocalDiskThermalIssueCritical(1604),
        storageLocalDiskThermalIssueNonRecoverable(1605),
        storageLocalDiskNotSupported(1606),
        fabricComputemslotEpMisplacedInChassisSlot(1616),
        fabricComputemslotEpServerIdentificationProblem(1617),
        fabricCartridgeSlotEpMisplacedInChassisSlot(1618),
        storageControllerNotSupported(1620),
        storageVirtualDriveDeploymentFailure(1621),
        storageVirtualDriveMissing(1622),
        storageVirtualDriveMismatch(1623),
        storageVdmemberEpMismatch(1624),
        firmwareBootUnitFirmwareBootFailed(1627),
        equipmentChassisMajorError(1634),
        equipmentFexMajorError(1635),
        computeRackUnitMajorError(1654),
        aaaDefaultAuthDefaultAuthNotDeployed(1668),
        aaaDomainDomainNotDeployed(1669),
        lsServerFault(1671),
        mgmtBackupLocalInternalBackupFailed(1672),
        lsIssuesForward327(1675),
        lsIdentityInfoForward1671(1676),
        vnicEtherCdnConfigNotApplied(1680),
        computePhysicalConnectivityDown(1681),
        storageSasExpanderInoperable(1685),
        storageSasExpanderAccessibilityProblem(1686),
        storageSasExpanderDegraded(1687),
        storageLocalDiskLinkDegraded(1688),
        fabricFcSanNumOfVsanExceedLimit(1694),
        swVlanPortNsCompressedSetsExhaustedWarning(1700),
        networkElementKernelMemCricitalThreshold(1701),
        flowctrlItemFlowctrlconfig(1702),
        networkElementSystemshutdown(1703),
        mgmtHealthStatusHealthWarningIssue(1704),
        mgmtHealthStatusHealthMinorIssue(1705),
        mgmtHealthStatusHealthMajorIssue(1706),
        mgmtHealthStatusHealthCriticalIssue(1707),
        computePhysicalDeprecated(1708),
        computePhysicalAdapterFirmwareNeedsUpdate(1709),
        computePhysicalIdentityUnestablishableOrDeprecated(1710),
        equipmentIocardDeprecated(1713),
        fabricSwChPhEpUncleanConfiguration(1719),
        fabricComputeSlotEpNotSupportedInChassisSlot(1720),
        fabricDceSwSrvEpDown(1721),
        storageLocalDiskThermalIssueNonCritical(1731),
        storageLocalDiskFailed(1732),
        equipmentSystemiocontrollerRemoved(1744),
        computeRackUnitFanSpeedConfigurationFailed(1745),
        fabricEthLanNumOfvlancompGrpExceedLimit(1748),
        fabricMulticastPolicySameOrEmptyPeerQuerierIp(1749),
        adaptorUnitDeprecated(1753),
        mgmtInterfaceInbandPinningInvalid(1754),
        etherPioInvalidSfp(1755),
        networkOperLevelExtravif(1756),
        networkElementDeprecated(1757),
        fabricNetGroupNativeVlanNotFound(1758),
        equipmentChassisChassislimitExceeded(1761),
        swSystemStatsForward1701(1764),
        mgmtEntityDevice1SharedStorageConnectError(1766),
        mgmtEntityDevice2SharedStorageConnectError(1767),
        mgmtEntityDevice3SharedStorageConnectError(1768),
        mgmtMgmtDbStateMgmtDbCorruptionDetected(1769),
        swEthLanBorderVlanLimitExceeded(1778),
        mgmtEntityMgmtDbVersionMismatch(1781),
        equipmentTpmTpmMismatch(1784),
        equipmentSharediomoduleInaccessible(1792),
        equipmentChassisInaccessibleB(1793),
        equipmentChassisInaccessibleA(1794),
        equipmentSystemiocontrollerThermalProblem(1795),
        equipmentSystemiocontrollerUnacknowledged(1796),
        equipmentIocardBackPlanePortProblem(1797),
        equipmentSwitchiocardBackPlanePortProblem(1798),
        equipmentFexBackPlanePortProblem(1799),
        fabricFcZoneProfileSwitchModeDisabled(1825),
        fabricFcUserZoneConfigFailure(1826),
        storageEnclosureThermalIssueNonCritical(1831),
        storageEnclosureThermalIssueCritical(1832),
        storageEnclosureThermalIssueNonRecoverable(1833),
        storageControllerDegraded(1834),
        storageSasExpanderLinkMisconnect(1835),
        storageSasExpanderLinkDegraded(1836),
        storageEnclosureMissing(1837),
        storageEnclosureFruEmpty(1838),
        storageEnclosureDiskSlotEpMissing(1839),
        storageEnclosureDiskSlotEpEquipmentInoperable(1840),
        storageEnclosureDiskSlotEpChassisSpare(1841),
        storageEnclosureDiskSlotEpHotspareUnsupported(1842),
        storageEnclosureDiskSlotEpSharingUnsupported(1843),
        storageEnclosureDiskSlotEpIoeOwnershipUnassigned(1844),
        storageEnclosureDiskSlotEpHddslotServer2OwnershipUnassigned(1845),
        equipmentChassisProfileFailed(1846),
        equipmentChassisProfileDiscoveryFailed(1847),
        equipmentChassisProfileConfigFailure(1848),
        equipmentChassisProfileRemoved(1849),
        equipmentChassisProfileInaccessible(1850),
        equipmentChassisProfileAssociationFailed(1851),
        equipmentChassisProfileUnassociated(1852),
        equipmentChassisIssuesForward1848(1864),
        fabricNetGroupRefNetSanGroupUnresolvable(1873),
        etherPioUnknownServerDevice(1889),
        etherPioMisconfigureForServerDevice(1890),
        etherPioInterfaceMismatch(1891),
        adaptorUnitPciConfigIssue(1892),
        networkElementEvacuationon(1893),
        networkLimitUnicastMac(1894),
        networkLimitMulticastMac(1895),
        networkLimitPvlifvlanmbr(1896),
        networkLimitPvsystem(1897),
        networkLimitIgmpgroup(1898),
        mgmtDbStateDbCorruptionDetected(1899),
        mgmtDbStateHighDbCorruptionDetected(1900),
        equipmentInventoryStatusHardwareMismatch(1901),
        equipmentChassisPhysicalSecurity(1902),
        equipmentComputeConnConfigProblem(1903),
        vnicEtherPrimaryVlanMissing(1907),
        vnicEtherNetSanGroupMisconfigured(1908),
        computePhysicalKmipFault(1912),
        computePhysicalHardwareInventoryMismatch(1913),
        computePhysicalPciConfigMismatch(1914),
        storageEnclosureDiskSlotEpSecondControllerAbsent(1915),
        computePhysicalExtensionForward1913(1916),
        computePhysicalExtensionForward1914(1917),
        adaptorUnitUnConnectedAdaptorReachability(1926),
        mgmtHealthStatusHealthInfoIssue(1927),
        computeRackUnitPhysicalSecurity(1932),
        biosUnitFd0FailedSecurityVerification(1933),
        computeBoardFailedSecureFuseValidation(1934),
        computeRackUnitUnsupportedConfig(1949),
        computeRackUnitConfigMismatch(1950),
        adaptorExtEthIfUnsupportedConection(1951),
        fabricVsanReserved(1953),
        fabricVlanReserved(1954),
        storageControllerNonOptimal(1959),
        storageFlexFlashCardIoerrors(1960),
        storageNvmeSwitchDegraded(1961),
        storageLocalDiskUnhealthy(1962),
        vnicFcUnsupported(1965),
        equipmentSystemiocontrollerInoperable(1966),
        networkLimitIftmcpv(1967),
        networkLimitDvif(1968),
        mgmtKvmCertificateCertificateUnsupported(1969),
        mgmtKvmCertificateCertificateEmptyParams(1970),
        pciSwitchPciSwitch(1974),
        storageControllerNonOptimalSevere(1975),
        etherServerIntfioErrorDisabled(1979),
        equipmentIocardSlowDrainRecoveryFail(1980),
        cloudDeviceConnectorEpIntersightNotClaimed(1981),
        computePhysicalPersistentMemoryDetected(1994),
        memoryPersistentMemoryUnitDegraded(1998),
        memoryPersistentMemoryUnitIdentityUnestablishable(1999),
        memoryPersistentMemoryUnitInoperable(2000),
        memoryPersistentMemoryUnitDisabled(2001),
        memoryPersistentMemoryUnitThermalThresholdNonCritical(2002),
        memoryPersistentMemoryUnitThermalThresholdCritical(2003),
        memoryPersistentMemoryUnitThermalThresholdNonRecoverable(2004),
        memoryPersistentMemoryConfigurationNotMatching(2005),
        memoryPersistentMemoryConfigurationNsNotMatching(2006),
        memoryPersistentMemoryConfigResultConfigError(2007),
        memoryPersistentMemoryNamespaceConfigResultConfigError(2008),
        memoryPersistentMemoryNamespaceNotMatching(2009),
        computePhysicalExtensionForward1994(2010),
        computeBoardCpuTypeUnestablished(2013),
        equipmentPsuUnsupported(2014),
        pciEquipSlotUnsecure(2015),
        storageItemFilesystemcleanwitherrors(2016),
        firmwareSecurefpgaUnsecuredfpga(2023),
        pciEquipSlotSpdmFault(2042),
        lsIssuesSpdmCertificatePolicyUnsupported(2045),
        storageControllerSpdmFault(2046),
        equipmentIocardFabricPortCountExceed(2056),
        adaptorHostEthIfAdaptorRingSizeValue(2057),
        memoryUnitPeerDimmDisabled(2058),
        memoryUnitDimmDisabled(2059),
        portPioUplinkPortStpMisConfigured(2060),
        etherServerIntfioInvalidSfp(2061),
        storageLocalDiskSelftestfailed(2062),
        equipmentIocardThermalNonCritical(2063),
        equipmentIocardThermalCritical(2064),
        equipmentIocardThermalNonRecoverable(2065),
        equipmentSwitchiocardThermalNonCritical(2066),
        equipmentSwitchiocardThermalCritical(2067),
        equipmentSwitchiocardThermalNonRecoverable(2068),
        fabricEthLanPcUplinkPortChannelStpMisConfigured(2069),
        cloudDeviceConnectorEpDisabledOrUnclaimedDevice(2079),
        equipmentCrossFabricModuleRemoved(2080),
        equipmentCrossFabricModuleIdentity(2081),
        equipmentCrossFabricModuleDeprecated(2082),
        adaptorUnitPcieUnstableLink(2083),
        adaptorUnitAsicFatalErr(2084),
        adaptorUnitFcpuErr(2085),
        networkLimitUnicastMacThreshold(2086),
        aaaUserEpPasswordEncryptionKeyNotSet(2087),
        graphicsCardGpuMissing(2091),
        computeBladeThermalThresholdNonRecoverable(2096),
        computeBladeGpuNodePresence(2097),
        computeBladeGpuNodeAbsent(2098),
        dcxVifStaticMacLimitReached(2099),
        equipmentPcieNodeRiser1Absentcpu1Present(2100),
        equipmentPcieNodeRiserMismatch(2101),
        equipmentPcieNodeRiser2Presentcpu2Absent(2102),
        equipmentPcieNodePcieLinkConfigIssue(2103),
        equipmentPcieNodePowerFault(2104),
        equipmentPcieNodeRiser1PowerFault(2105),
        equipmentPcieNodeRiser2PowerFault(2106),
        equipmentPcieNodeUnsupportedpcieNodePresent(2107),
        equipmentPcieNodeUnknownpcieNodePresent(2108),
        equipmentPcieNodeUnsupportedpcieCardPresentOnRiser1(2109),
        equipmentPcieNodeUnsupportedpcieCardPresentOnRiser2(2110),
        equipmentPcieNodeUnknownpcieCardPresentOnRiser1(2111),
        equipmentPcieNodeUnknownpcieCardPresentOnRiser2(2112),
        equipmentPcieNodePcieNodePresentxfm1Absent(2113),
        equipmentPcieNodeRetimerVersionMismatch(2114),
        equipmentPcieNodeRemoved(2115),
        equipmentChassisIssuesFirmwareUpdateNotUnsupported(2116),
        etherMacSecSessionMacsecSessionStateChange(2117),
        etherMacSecSessionMacsecFallbackSession(2118),
        fabricMonSpanOperFail(2127),
        fabricMonOriginsviErspanConfigFail(2128),
        adaptorUnitAdapterCommunicationErrors(2130),
        adaptorUnitAdapterCounterfeit(2131),
        adaptorUnitAdapterSecureBootFail(2132),
        adaptorUnitAdapterBackupImage(2133),
        adaptorUnitAdapterfwvalidationFailed(2134),
        adaptorUnitAdapterAltImage(2135),
        adaptorUnitAdapterDiagImage(2136),
        adaptorUnitAdapterNotRelKeySigned(2137),
        adaptorUnitAdapterLowUpgradesRemaining(2138),
        adaptorUnitAdapterNoUpgradesRemaining(2139),
        qosclassItemCosConflict(2140),
        storageControllerUnsupportedController(2141),
        storageLocalDiskUnsupportedDisk(2142),
        mgmtHybridSlotConfigurationError(2143),
        adaptorUnitLowMemory(2153),
        adaptorUnitAdapterUpgradableCountLow(2154),
        adaptorUnitAdapterUpgradableCountZero(2155),
        commSnmpTrapSnmpTrapWithNoauthPrivilege(2156),
        aaaUserWeakPasswordHashingAlgorithm(2163),
        aaaLoginProfileBlockInvalidLogin(2164),
        storageControllerUnsupportedDrive(2165),
        mgmtKmipStatus(2166),
        swVlanTrafficMonInvalidSourceVlanIntf(2167),
        fsmSamDmeSysdebugLogControlEpPersistence(16392),
        fsmSamDmeMgmtRegistryInfoConfigure(16394),
        fsmSamDmeOrgOrgConfigure(16395),
        fsmSamDmeTopSystemHostName(16400),
        fsmSamDmeEquipmentiocardFePresence(16405),
        fsmSamDmeEquipmentiocardFeConn(16406),
        fsmSamDmeEquipmentChassisRemoveChassis(16407),
        fsmSetLocatorLed(16408),
        fsmSamDmeMgmtDataExporterExportData(16415),
        fsmSamDmeMgmtDataImporterImportData(16416),
        fsmUpdateElement(16424),
        fsmSamDmeTestingServiceProfileResolvePolicyFsm(16441),
        fsmSamDmeTestingServiceProfileResolveManyPolicyFsm(16442),
        fsmSamDmeCertRepairEpRepairCert(16504),
        fsmResolveResourceFsm(16511),
        fsmResolvevmfsm(16512),
        fsmResolveControllerFsm(16513),
        fsmSamDmeMgmtControllerExtMgmtIfConfig(16518),
        fsmSamDmeFabricComputeSlotEpIdentify(16519),
        fsmSamDmeComputeBladeDiscover(16520),
        fsmReleasePolicyFsm(16532),
        fsmSamDmeEquipmentChassisPsuPolicyConfig(16533),
        fsmSamDmeAdaptorHostFcIfResetFcPersBinding(16534),
        fsmSamDmeComputeBladeDiag(16535),
        fsmResolveManyOperationFsm(16536),
        fsmResolveManyStorageFsm(16537),
        fsmReleaseManyPolicyFsm(16538),
        fsmSwitchMode(16539),
        fsmReleaseManyStorageFsm(16540),
        fsmResolveAllPolicyFsm(16541),
        fsmResolveAllOperationFsm(16542),
        fsmResolveAllStorageFsm(16543),
        fsmReleaseAllPolicyFsm(16544),
        fsmReleaseAllOperationFsm(16545),
        fsmReleaseAllStorageFsm(16546),
        fsmSamDmeVnicProfileSetDeploy(16550),
        fsmUpdateSvcEp(16576),
        fsmSamDmeCommSvcEpRestartWebSvc(16577),
        fsmUpdateEp(16579),
        fsmUpdateRealm(16580),
        fsmUpdateUserEp(16581),
        fsmSamDmePkiEpUpdateEp(16582),
        fsmSingle(16600),
        fsmSamDmeSysfileMutationGlobal(16601),
        fsmSamDmeConfigBackupDelete(16602),
        fsmSamDmeSysdebugManualCoreFileExportTargetExport(16604),
        fsmSamDmeSysdebugAutoCoreFileExportTargetConfigure(16605),
        fsmSamDmeSysdebugLogControlEpLogControlPersist(16606),
        fsmSamDmeConsumerInstRenameCfgDir(16607),
        fsmSamDmeNfsClientDefAddConfig(16608),
        fsmSamDmeNfsClientDefDeleteConfig(16609),
        fsmSamDmeSwAccessDomainDeploy(16634),
        fsmSamDmeSwEthLanBorderDeploy(16635),
        fsmSamDmeSwFcSanBorderDeploy(16636),
        fsmSamDmeSwUtilityDomainDeploy(16637),
        fsmSamDmeComputeSystemRegister(16639),
        fsmSamDmeSyntheticFsObjCreate(16641),
        fsmUpdateContextFsm(16643),
        fsmSamDmeFirmwareDownloaderDownload(16650),
        fsmSamDmeFirmwareImageDelete(16651),
        fsmUpdateSwitch(16653),
        fsmUpdateiom(16654),
        fsmSamDmeMgmtControllerActivateiom(16655),
        fsmUpdatebmc(16656),
        fsmSamDmeMgmtControllerActivatebmc(16657),
        fsmSamDmeCallhomeEpConfigCallhome(16670),
        fsmSwMgmtOobIfConfig(16673),
        fsmSwMgmtInbandIfConfig(16674),
        fsmVirtualIfConfig(16679),
        fsmSamDmeMgmtIfEnableVip(16680),
        fsmSamDmeMgmtIfDisableVip(16681),
        fsmSamDmeMgmtIfEnableha(16682),
        fsmSamDmeMgmtBackupBackup(16683),
        fsmSamDmeMgmtImporterImport(16684),
        fsmSamDmeOrgOrgConfigurePeer(16728),
        fsmSamDmeTopSystemPeerHostName(16729),
        fsmSamDmeStatsCollectionPolicyUpdateEp(16742),
        fsmSamDmeQosclassDefinitionConfigGlobalQos(16745),
        fsmSamDmeEpqosDefinitionDeploy(16749),
        fsmSamDmeEpqosDefinitionDelTaskRemove(16750),
        fsmSamDmeControllerEpQuiesce(16764),
        fsmSamDmeConfigConsumerCatalogueCreate(16769),
        fsmSamDmeNfsExportDefImageSync(16770),
        fsmSamDmeNfsExportDefAddRepo(16771),
        fsmUpdateIdent(16793),
        fsmSync(16794),
        fsmSyncVnetEpucs(16800),
        fsmSamDmeEquipmentiocardResetCmc(16803),
        fsmSyncChangeucs(16808),
        fsmUpdateucsmanager(16815),
        fsmSysConfig(16823),
        fsmSamDmeAdaptorExtEthIfPathReset(16852),
        fsmSamDmeAdaptorHostEthIfCircuitReset(16857),
        fsmSamDmeAdaptorHostFcIfCircuitReset(16858),
        fsmSamDmeExtvmmProviderConfig(16879),
        fsmSamDmeExtvmmKeyStoreCertInstall(16880),
        fsmSamDmeExtvmmSwitchDelTaskRemoveProvider(16881),
        fsmSamDmeExtvmmMasterExtKeyConfig(16898),
        fsmUpdater(16904),
        fsmSamDmeFirmwareDistributableDelete(16906),
        fsmDiscover(16920),
        fsmAssociate(16921),
        fsmDisassociate(16922),
        fsmDecommission(16924),
        fsmSoftShutdown(16925),
        fsmHardShutdown(16926),
        fsmTurnup(16927),
        fsmPowercycle(16928),
        fsmHardreset(16929),
        fsmSoftreset(16930),
        fsmSwConnUpd(16931),
        fsmBiosRecovery(16932),
        fsmCmosReset(16934),
        fsmResetBmc(16935),
        fsmUpdateExtUsers(16938),
        fsmUpdateAdaptor(16939),
        fsmActivateAdaptor(16940),
        fsmConfigSol(16941),
        fsmUnconfigSol(16942),
        fsmSetFeLocatorLed(16943),
        fsmSamDmeEquipmentChassisPowerCap(16944),
        fsmSamDmeEquipmentiocardMuxOffline(16945),
        fsmPowerCap(16950),
        fsmUpdateBoardController(16964),
        fsmDeployCatalogue(16965),
        fsmSamDmeComputePhysicalAssociate(16973),
        fsmSamDmeComputePhysicalDisassociate(16974),
        fsmSamDmeComputePhysicalPowerCap(16975),
        fsmSamDmeComputePhysicalDecommission(16976),
        fsmSamDmeComputePhysicalSoftShutdown(16977),
        fsmSamDmeComputePhysicalHardShutdown(16978),
        fsmSamDmeComputePhysicalTurnup(16979),
        fsmSamDmeComputePhysicalPowercycle(16980),
        fsmSamDmeComputePhysicalHardreset(16981),
        fsmSamDmeComputePhysicalSoftreset(16982),
        fsmSamDmeComputePhysicalSwConnUpd(16983),
        fsmSamDmeComputePhysicalBiosRecovery(16984),
        fsmSamDmeComputePhysicalCmosReset(16986),
        fsmSamDmeComputePhysicalResetBmc(16987),
        fsmSamDmeEquipmentiocardResetIom(16988),
        fsmInstall(16991),
        fsmClear(16992),
        fsmUpdateFlexlm(16993),
        fsmSamDmeComputeRackUnitDiscover(16994),
        fsmSamDmeLsServerConfigure(16995),
        fsmSamDmeSwEthMonDeploy(17000),
        fsmSamDmeSwFcMonDeploy(17001),
        fsmSamDmeFabricSanCloudSwitchMode(17002),
        fsmRemoveFex(17007),
        fsmSamDmeComputePhysicalUpdateExtUsers(17008),
        fsmSamDmeSysdebugTechSupportInitiate(17012),
        fsmSamDmeSysdebugTechSupportDeleteTechSupFile(17013),
        fsmSamDmeSysdebugTechSupportDownload(17014),
        fsmActivateCatalog(17017),
        fsmActivateMgmtExt(17018),
        fsmSamDmeDupeChangeTrackerEpConfigure(17032),
        fsmTrigger(17035),
        fsmSamDmeComputePhysicalUpdateAdaptor(17043),
        fsmSamDmeComputePhysicalActivateAdaptor(17044),
        fsmSamDmeCapabilityCatalogueActivateCatalog(17045),
        fsmSamDmeCapabilityMgmtExtensionActivateMgmtExt(17046),
        fsmSamDmeLicenseDownloaderDownload(17050),
        fsmSamDmeLicenseFileInstall(17051),
        fsmSamDmeLicenseFileClear(17052),
        fsmSamDmeLicenseInstanceUpdateFlexlm(17053),
        fsmConfigure(17060),
        fsmMuxOffline(17061),
        fsmSamDmeComputePhysicalConfigSol(17083),
        fsmSamDmeComputePhysicalUnconfigSol(17084),
        fsmSamDmePortpioInCompatSfpPresence(17089),
        fsmSamDmeComputePhysicalDiagnosticInterrupt(17116),
        fsmSamDmeSysdebugCoreDownload(17133),
        fsmSamDmeEquipmentChassisDynamicReallocation(17134),
        fsmSamDmeCallhomeHolderConfigure(17151),
        fsmSamDmeCallhomeHolderInventory(17152),
        fsmSamDmeComputePhysicalResetKvm(17163),
        fsmSamDmeSmartlicenseAgentConfigure(17164),
        fsmSamDmeSmartlicenseTestConfigure(17165),
        fsmSamDmeSmartlicenseEntitlementEpConfigure(17166),
        fsmSamDmeSmartlicenseHolderConfigure(17167),
        fsmSamDmeMgmtControllerOnline(17169),
        fsmSamDmeComputeRackUnitOffline(17170),
        fsmSamDmeEquipmentLocatorLedSetFiLocatorLed(17187),
        fsmConfPhysical(17190),
        fsmClusterRole(17192),
        fsmIlluminate(17195),
        fsmSetFiLocatorLed(17196),
        fsmDeployAlias(17207),
        fsmSamDmeFabricEpMgrConfigure(17214),
        fsmSamDmeVnicProfileSetDeployAlias(17223),
        fsmSamDmeSwPhysConfPhysical(17239),
        fsmSamDmeExtvmmEpClusterRole(17254),
        fsmSamDmeVmLifeCyclePolicyConfig(17259),
        fsmUpdateState(17261),
        fsmSamDmeEquipmentBeaconLedIlluminate(17262),
        fsmSamDmeEtherServerIntfioConfigSpeed(17271),
        fsmUpdatebios(17281),
        fsmSamDmeComputePhysicalActivatebios(17282),
        fsmSamDmeCommDateTimeTimezone(17312),
        fsmSamDmeFirmwareSystemDeploy(17325),
        fsmSamDmeFirmwareSystemApplyCatalogPack(17326),
        fsmSamDmeMgmtExportPolicyReportConfigCopy(17339),
        fsmSamDmeMgmtImporterReportConfigImport(17340),
        fsmSamDmeNfsMountInstMount(17348),
        fsmSamDmeNfsMountInstUnmount(17349),
        fsmSamDmeNfsMountDefReportNfsMountSuspend(17350),
        fsmSamDmeStorageSystemSync(17367),
        fsmSamDmePolicyControlEpOpRemoteDomainReg(17371),
        fsmSamDmePolicyControlEpOpRemoteDomainUnReg(17372),
        fsmSamDmeEquipmentChassisProfileConfigure(17373),
        fsmSamDmeSwFcSanBorderActivateZoneSet(17381),
        fsmSamDmeExtpolEpRegisterFsm(17382),
        fsmSamDmeExtpolRegistryCrossDomainConfig(17383),
        fsmSamDmeExtpolRegistryCrossDomainDelete(17384),
        fsmSamDmeExtpolEpRepairCert(17399),
        fsmSamDmePolicyControlEpOperate(17400),
        fsmSamDmePolicyPolicyScopeReleasePolicyFsm(17402),
        fsmSamDmePolicyPolicyScopeReleaseOperationFsm(17403),
        fsmSamDmePolicyPolicyScopeReleaseStorageFsm(17404),
        fsmSamDmePolicyPolicyScopeResolveManyPolicyFsm(17405),
        fsmSamDmePolicyPolicyScopeResolveManyOperationFsm(17406),
        fsmSamDmePolicyPolicyScopeResolveManyStorageFsm(17407),
        fsmSamDmePolicyPolicyScopeReleaseManyPolicyFsm(17408),
        fsmSamDmePolicyPolicyScopeReleaseManyOperationFsm(17409),
        fsmSamDmePolicyPolicyScopeReleaseManyStorageFsm(17410),
        fsmSamDmePolicyPolicyScopeResolveAllPolicyFsm(17411),
        fsmSamDmePolicyPolicyScopeResolveAllOperationFsm(17412),
        fsmSamDmePolicyPolicyScopeResolveAllStorageFsm(17413),
        fsmSamDmePolicyPolicyScopeReleaseAllPolicyFsm(17414),
        fsmSamDmePolicyPolicyScopeReleaseAllOperationFsm(17415),
        fsmSamDmePolicyPolicyScopeReleaseAllStorageFsm(17416),
        fsmSamDmeIdentIdentRequestUpdateIdent(17418),
        fsmSamDmeIdentMetaSystemSync(17419),
        fsmSamDmeMgmtControllerRegistryConfig(17420),
        fsmSamDmeGlRequestEvaluate(17421),
        fsmSamDmeGlRequestCreateGlobalIdPool(17422),
        fsmSamDmeGlRequestCreateGlobalPolicy(17423),
        fsmSamDmeGlRequestGlobalize(17424),
        fsmSamDmeObserveObservedResolvePolicyFsm(17425),
        fsmSamDmeObserveObservedResolveResourceFsm(17426),
        fsmSamDmeObserveObservedResolvevmfsm(17427),
        fsmSamDmeObserveObservedResolveControllerFsm(17428),
        fsmSamDmeDiagSrvCtrlOperationConfigure(17444),
        fsmSamDmePortpioInCompatSfpReplaced(17445),
        fsmSamDmeFdPhysicalConfigure(17451),
        fsmSamDmeVnicOutbandMgmtEpConfigureOutband(17473),
        fsmSamDmeDomainProfileConfigure(17474),
        fsmSamDmeComputePhysicalResetIpmi(17476),
        fsmSamDmeComputePhysicalFwUpgrade(17477),
        fsmSamDmeComputeRackUnitAdapterReset(17478),
        fsmSamDmeFabricFcZoneProfileConfigure(17479),
        fsmSamDmeComputeServerDiscPolicyResolveScrubPolicy(17483),
        fsmSamDmeExtpolProviderReportConfigImport(17485),
        fsmSamDmeFabricVnetEpSyncEpPushVnetEpDeletion(17599),
        fsmSamDmeGmetaHolderInventory(17601),
        fsmSamDmeComputePhysicalCimcSessionDelete(17602),
        fsmSamDmePolicyControlledTypeOperate(17612),
        fsmSamDmeMgmtControllerExtMgmtInterfaceConfig(17660),
        fsmSamDmeComputeRackUnitCreateDhcpEntry(17661),
        fsmSamDmeComputePhysicalServiceInfraDeploy(17662),
        fsmSamDmeComputePhysicalServiceInfraWithdraw(17663),
        fsmSamDmeComputePhysicalUpdateBoardController(17667),
        fsmSamDmeComputePhysicalConfigBoard(17702),
        fsmSamDmeComputePhysicalResetMemoryErrors(17703),
        fsmSamDmeMgmtipv6IfAddrSwMgmtOobIpv6IfConfig(17707),
        fsmSamDmeSwEthLanFlowMonDeploy(17713),
        fsmSamDmeExtvmmNetworkSetsDeploy(17733),
        fsmSamDmeComputePhysicalFlashController(17762),
        fsmSamDmeSysdebugLogExportPolicyConfigure(17788),
        fsmSamDmeStorageFlexFlashControllermopsReset(17791),
        fsmSamDmeStorageFlexFlashControllermopsFormat(17792),
        fsmSamDmeStorageFlexFlashControllermopsPair(17793),
        fsmSamDmeComputePhysicalEnableCimcSecureBoot(17806),
        fsmSamDmeIdentMetaSystemUcscUnivSync(17824),
        fsmSamDmeStoragePartitionDeployStorage(17921),
        fsmSamDmeStorageProcessorDiscoverSystem(17922),
        fsmSamDmeStorageProcessorEnterMaintenance(17923),
        fsmSamDmeStorageProcessorExitMaintenance(17924),
        fsmSamDmeStorageProcessorDeploySystem(17925),
        fsmSamDmeStorageProcessorUndeploySystem(17926),
        fsmSamDmeStorageProcessorHaTakeOver(17927),
        fsmSamDmeStoragePartitionScrubraidgroup(17928),
        fsmSamDmeMgmtControllerLockConfig(17933),
        fsmSamDmeMgmtControllerPowerBudgetReclaimConfig(17934),
        fsmSamDmeComputePhysicalOobStorageAdminConfig(17935),
        fsmSamDmeEquipmentiocardBaseFePresence(17940),
        fsmSamDmeEquipmentiocardBaseFeConn(17941),
        fsmSamDmeEquipmentLocatorLedSetDiskLocatorLed(17954),
        fsmSamDmeLstorageProcessorConfigure(17978),
        fsmSamDmeOsControllerDeployos(17984),
        fsmSamDmeEquipmentPsuUpdatepsu(17987),
        fsmSamDmeMgmtControllerUpdatecmc(18012),
        fsmSamDmeMgmtControllerActivatecmc(18013),
        fsmSamDmeMgmtControllerUpdateAdaptor(18014),
        fsmSamDmeMgmtControllerActivateAdaptor(18015),
        fsmSamDmeMgmtControllerUpdateRaidController(18016),
        fsmSamDmeMgmtControllerUpdateBoardController(18017),
        fsmSamDmeFabricCartridgeSlotEpIdentify(18024),
        fsmSamDmeFabricComputemslotEpIdentify(18025),
        fsmSamDmeEquipmentChassisOobStorageAdminCfg(18026),
        fsmSamDmeComputeServerUnitDiscover(18032),
        fsmSamDmeMgmtIfFaPresence(18033),
        fsmSamDmeMgmtIfFaConn(18034),
        fsmSamDmeEquipmentiocardEvacuate(18045),
        fsmSamDmeEquipmentiocardResetEvacuate(18046),
        fsmSamDmeComputePhysicalCleartpm(18051),
        fsmSamDmeEquipmentiocardResetPeerCmc(18102),
        fsmSamDmeSwExtUtilityConfPortBreakout(18124),
        fsmSamDmeEquipmentSwitchiocardEvacuate(18146),
        fsmSamDmeEquipmentSwitchiocardResetEvacuate(18147),
        fsmSamDmeMorefImportRootApplyMoRefs(18161),
        fsmSamDmeStorageEnclosureRemoveEnclosure(18169),
        fsmSamDmeMgmtControllerPowerCap(18184),
        fsmSamDmeEquipmentSystemiocontrollerResetCmc(18185),
        fsmSamDmeComputePhysicalDiskZoningInventory(18186),
        fsmSamDmeEquipmentChassisAssociate(18207),
        fsmSamDmeEquipmentChassisDisassociate(18208),
        fsmSamDmeEtherServerIntfioConfig(18237),
        fsmSamDmeMgmtControllerEnableSecureBoot(18239),
        fsmSamDmeMgmtControllerUpdateColusacmc(18240),
        fsmSamDmeMgmtControllerActivateColusacmc(18241),
        fsmSamDmeEquipmentChassisChassisUpgrade(18242),
        fsmSamDmeMgmtControllerUpdateColusaBoardController(18243),
        fsmSamDmeMgmtControllerUpdateSasExpander(18244),
        fsmSamDmeMgmtControllerActivateSasExpander(18245),
        fsmSamDmeMgmtControllerActivateLocalDisk(18246),
        fsmSamDmeStorageLocalDiskUpdateLocalDisk(18247),
        fsmSamDmeMgmtControllerUpdateucsmanagersp(18259),
        fsmSamDmeComputePhysicalDiag(18260),
        fsmSamDmeComputePhysicalCimcSecurityConfig(18261),
        fsmSamDmeSwPortDiscoverDeploy(18290),
        fsmSamDmePolicyPolicyScopeContReportPolicyFailFsm(18293),
        fsmSamDmePolicyRequestorResolveFromCentral(18294),
        fsmSamDmeFabricReservedVlanDeploy(18336),
        fsmSamDmeEquipmentChassisFwUpgrade(18339),
        fsmSamDmeMgmtControllerKvmCert(18342),
        fsmSamDmeQosclassSlowDrainConfigQosslowDrain(18361),
        fsmSamDmeQosclassSlowDrainConfigQosslowDrainFex(18362),
        fsmSamDmeComputePhysicalExecuteActions(18375),
        fsmSamDmeEquipmentChassisFanPolicyConfig(18376),
        fsmSamDmeComputePhysicalNvmeSwitchRecovery(18377),
        fsmSamDmeMgmtControllerUpdateStorageServercmc(18379),
        fsmSamDmeMgmtControllerActivateStorageServercmc(18380),
        fsmSamDmeMgmtControllerUpgradeBoardController(18381),
        fsmSamDmeComputePhysicalReinitializeVirtualDrive(18395),
        fsmSamDmeEquipmentChassisPowerSavePolicyConfig(18404),
        fsmSamDmeFcpoolOuisDeploy(18406),
        fsmSamDmeMgmtControllerUpdateSecurefpga(18410),
        fsmSamDmePfcWatchDogConfigPfcWatchDog(18411),
        fsmSamDmeMgmtControllerConfigureSwPersonalities(18427),
        fsmSamDmeComputePhysicalConfigureServerPersonality(18428),
        fsmSamDmeComputePhysicalBiosPasswordReset(18431),
        fsmSamDmeComputePhysicalCimcSecurityUnconfig(18432),
        fsmSamDmeEquipmentChassisPowerExtendedPolicyConfig(18456),
        fsmSamDmeComputePhysicalDataSanitization(18478),
        fsmSamDmeSwrmonEpDeployrmonEp(18530),
        fsmSamDmeSecurityEncryptionEpUpdateEncryptionEp(18533),
        tcaProcessorRuntimeLoad(33142),
        tcaProcessorRuntimeLoadMin(33144),
        tcaProcessorRuntimeLoadMax(33145),
        tcaProcessorRuntimeLoadAvg(33146),
        tcaFcStatsBytesRxDelta(33167),
        tcaFcStatsBytesRxDeltaMin(33168),
        tcaFcStatsBytesRxDeltaMax(33169),
        tcaFcStatsBytesRxDeltaAvg(33170),
        tcaFcStatsPacketsRxDelta(33177),
        tcaFcStatsPacketsRxDeltaMin(33178),
        tcaFcStatsPacketsRxDeltaMax(33179),
        tcaFcStatsPacketsRxDeltaAvg(33180),
        tcaFcStatsBytesTxDelta(33187),
        tcaFcStatsBytesTxDeltaMin(33188),
        tcaFcStatsBytesTxDeltaMax(33189),
        tcaFcStatsBytesTxDeltaAvg(33190),
        tcaFcStatsPacketsTxDelta(33197),
        tcaFcStatsPacketsTxDeltaMin(33198),
        tcaFcStatsPacketsTxDeltaMax(33199),
        tcaFcStatsPacketsTxDeltaAvg(33200),
        tcaFcErrStatsCrcRxDelta(33211),
        tcaFcErrStatsCrcRxDeltaMin(33212),
        tcaFcErrStatsCrcRxDeltaMax(33213),
        tcaFcErrStatsCrcRxDeltaAvg(33214),
        tcaFcErrStatsDiscardRxDelta(33221),
        tcaFcErrStatsDiscardRxDeltaMin(33222),
        tcaFcErrStatsDiscardRxDeltaMax(33223),
        tcaFcErrStatsDiscardRxDeltaAvg(33224),
        tcaFcErrStatsTooLongRxDelta(33231),
        tcaFcErrStatsTooLongRxDeltaMin(33232),
        tcaFcErrStatsTooLongRxDeltaMax(33233),
        tcaFcErrStatsTooLongRxDeltaAvg(33234),
        tcaFcErrStatsTooShortRxDelta(33241),
        tcaFcErrStatsTooShortRxDeltaMin(33242),
        tcaFcErrStatsTooShortRxDeltaMax(33243),
        tcaFcErrStatsTooShortRxDeltaAvg(33244),
        tcaFcErrStatsRxDelta(33251),
        tcaFcErrStatsRxDeltaMin(33252),
        tcaFcErrStatsRxDeltaMax(33253),
        tcaFcErrStatsRxDeltaAvg(33254),
        tcaFcErrStatsDiscardTxDelta(33261),
        tcaFcErrStatsDiscardTxDeltaMin(33262),
        tcaFcErrStatsDiscardTxDeltaMax(33263),
        tcaFcErrStatsDiscardTxDeltaAvg(33264),
        tcaFcErrStatsTxDelta(33271),
        tcaFcErrStatsTxDeltaMin(33272),
        tcaFcErrStatsTxDeltaMax(33273),
        tcaFcErrStatsTxDeltaAvg(33274),
        tcaFcErrStatsLinkFailuresDelta(33281),
        tcaFcErrStatsLinkFailuresDeltaMin(33282),
        tcaFcErrStatsLinkFailuresDeltaMax(33283),
        tcaFcErrStatsLinkFailuresDeltaAvg(33284),
        tcaFcErrStatsSyncLossesDelta(33291),
        tcaFcErrStatsSyncLossesDeltaMin(33292),
        tcaFcErrStatsSyncLossesDeltaMax(33293),
        tcaFcErrStatsSyncLossesDeltaAvg(33294),
        tcaFcErrStatsSignalLossesDelta(33301),
        tcaFcErrStatsSignalLossesDeltaMin(33302),
        tcaFcErrStatsSignalLossesDeltaMax(33303),
        tcaFcErrStatsSignalLossesDeltaAvg(33304),
        tcaMemoryRuntimeTotal(33483),
        tcaMemoryRuntimeTotalMin(33485),
        tcaMemoryRuntimeTotalMax(33486),
        tcaMemoryRuntimeTotalAvg(33487),
        tcaMemoryRuntimeAvailable(33491),
        tcaMemoryRuntimeAvailableMin(33493),
        tcaMemoryRuntimeAvailableMax(33494),
        tcaMemoryRuntimeAvailableAvg(33495),
        tcaMemoryRuntimeCached(33499),
        tcaMemoryRuntimeCachedMin(33501),
        tcaMemoryRuntimeCachedMax(33502),
        tcaMemoryRuntimeCachedAvg(33503),
        tcaAdaptorEthPortStatsTotalPacketsDelta(33720),
        tcaAdaptorEthPortStatsTotalPacketsDeltaMin(33721),
        tcaAdaptorEthPortStatsTotalPacketsDeltaMax(33722),
        tcaAdaptorEthPortStatsTotalPacketsDeltaAvg(33723),
        tcaAdaptorEthPortStatsGoodPacketsDelta(33730),
        tcaAdaptorEthPortStatsGoodPacketsDeltaMin(33731),
        tcaAdaptorEthPortStatsGoodPacketsDeltaMax(33732),
        tcaAdaptorEthPortStatsGoodPacketsDeltaAvg(33733),
        tcaAdaptorEthPortStatsVlanPacketsDelta(33740),
        tcaAdaptorEthPortStatsVlanPacketsDeltaMin(33741),
        tcaAdaptorEthPortStatsVlanPacketsDeltaMax(33742),
        tcaAdaptorEthPortStatsVlanPacketsDeltaAvg(33743),
        tcaAdaptorEthPortStatsPausePacketsDelta(33750),
        tcaAdaptorEthPortStatsPausePacketsDeltaMin(33751),
        tcaAdaptorEthPortStatsPausePacketsDeltaMax(33752),
        tcaAdaptorEthPortStatsPausePacketsDeltaAvg(33753),
        tcaAdaptorEthPortStatsPerPriorityPausePacketsDelta(33760),
        tcaAdaptorEthPortStatsPerPriorityPausePacketsDeltaMin(33761),
        tcaAdaptorEthPortStatsPerPriorityPausePacketsDeltaMax(33762),
        tcaAdaptorEthPortStatsPerPriorityPausePacketsDeltaAvg(33763),
        tcaAdaptorEthPortStatsPppPacketsDelta(33770),
        tcaAdaptorEthPortStatsPppPacketsDeltaMin(33771),
        tcaAdaptorEthPortStatsPppPacketsDeltaMax(33772),
        tcaAdaptorEthPortStatsPppPacketsDeltaAvg(33773),
        tcaAdaptorEthPortBySizeSmallStatsLessThan64Delta(33810),
        tcaAdaptorEthPortBySizeSmallStatsLessThan64DeltaMin(33811),
        tcaAdaptorEthPortBySizeSmallStatsLessThan64DeltaMax(33812),
        tcaAdaptorEthPortBySizeSmallStatsLessThan64DeltaAvg(33813),
        tcaAdaptorEthPortBySizeSmallStatsEquals64Delta(33820),
        tcaAdaptorEthPortBySizeSmallStatsEquals64DeltaMin(33821),
        tcaAdaptorEthPortBySizeSmallStatsEquals64DeltaMax(33822),
        tcaAdaptorEthPortBySizeSmallStatsEquals64DeltaAvg(33823),
        tcaAdaptorEthPortBySizeSmallStatsLessThan128Delta(33830),
        tcaAdaptorEthPortBySizeSmallStatsLessThan128DeltaMin(33831),
        tcaAdaptorEthPortBySizeSmallStatsLessThan128DeltaMax(33832),
        tcaAdaptorEthPortBySizeSmallStatsLessThan128DeltaAvg(33833),
        tcaAdaptorEthPortBySizeSmallStatsLessThan256Delta(33840),
        tcaAdaptorEthPortBySizeSmallStatsLessThan256DeltaMin(33841),
        tcaAdaptorEthPortBySizeSmallStatsLessThan256DeltaMax(33842),
        tcaAdaptorEthPortBySizeSmallStatsLessThan256DeltaAvg(33843),
        tcaAdaptorEthPortBySizeSmallStatsLessThan512Delta(33850),
        tcaAdaptorEthPortBySizeSmallStatsLessThan512DeltaMin(33851),
        tcaAdaptorEthPortBySizeSmallStatsLessThan512DeltaMax(33852),
        tcaAdaptorEthPortBySizeSmallStatsLessThan512DeltaAvg(33853),
        tcaAdaptorEthPortBySizeSmallStatsLessThan1024Delta(33860),
        tcaAdaptorEthPortBySizeSmallStatsLessThan1024DeltaMin(33861),
        tcaAdaptorEthPortBySizeSmallStatsLessThan1024DeltaMax(33862),
        tcaAdaptorEthPortBySizeSmallStatsLessThan1024DeltaAvg(33863),
        tcaAdaptorEthPortBySizeLargeStatsLessThanOrEqualTo1518Delta(33875),
        tcaAdaptorEthPortBySizeLargeStatsLessThanOrEqualTo1518DeltaMin(33876),
        tcaAdaptorEthPortBySizeLargeStatsLessThanOrEqualTo1518DeltaMax(33877),
        tcaAdaptorEthPortBySizeLargeStatsLessThanOrEqualTo1518DeltaAvg(33878),
        tcaAdaptorEthPortBySizeLargeStatsLessThan2048Delta(33885),
        tcaAdaptorEthPortBySizeLargeStatsLessThan2048DeltaMin(33886),
        tcaAdaptorEthPortBySizeLargeStatsLessThan2048DeltaMax(33887),
        tcaAdaptorEthPortBySizeLargeStatsLessThan2048DeltaAvg(33888),
        tcaAdaptorEthPortBySizeLargeStatsLessThan4096Delta(33895),
        tcaAdaptorEthPortBySizeLargeStatsLessThan4096DeltaMin(33896),
        tcaAdaptorEthPortBySizeLargeStatsLessThan4096DeltaMax(33897),
        tcaAdaptorEthPortBySizeLargeStatsLessThan4096DeltaAvg(33898),
        tcaAdaptorEthPortBySizeLargeStatsLessThan8192Delta(33905),
        tcaAdaptorEthPortBySizeLargeStatsLessThan8192DeltaMin(33906),
        tcaAdaptorEthPortBySizeLargeStatsLessThan8192DeltaMax(33907),
        tcaAdaptorEthPortBySizeLargeStatsLessThan8192DeltaAvg(33908),
        tcaAdaptorEthPortBySizeLargeStatsLessThan9216Delta(33915),
        tcaAdaptorEthPortBySizeLargeStatsLessThan9216DeltaMin(33916),
        tcaAdaptorEthPortBySizeLargeStatsLessThan9216DeltaMax(33917),
        tcaAdaptorEthPortBySizeLargeStatsLessThan9216DeltaAvg(33918),
        tcaAdaptorEthPortBySizeLargeStatsGreaterThanOrEqualTo9216Delta(33925),
        tcaAdaptorEthPrtBySizeLargeStatsGreaterThanOrEqualTo9216DeltaMin(33926),
        tcaAdaptorEthPrtBySizeLargeStatsGreaterThanOrEqualTo9216DeltaMax(33927),
        tcaAdaptorEthPrtBySizeLargeStatsGreaterThanOrEqualTo9216DeltaAvg(33928),
        tcaAdaptorEthPortOutsizedStatsOversizedPacketsDelta(33940),
        tcaAdaptorEthPortOutsizedStatsOversizedPacketsDeltaMin(33941),
        tcaAdaptorEthPortOutsizedStatsOversizedPacketsDeltaMax(33942),
        tcaAdaptorEthPortOutsizedStatsOversizedPacketsDeltaAvg(33943),
        tcaAdaptorEthPortOutsizedStatsOversizedGoodCrcPacketsDelta(33950),
        tcaAdaptorEthPortOutsizedStatsOversizedGoodCrcPacketsDeltaMin(33951),
        tcaAdaptorEthPortOutsizedStatsOversizedGoodCrcPacketsDeltaMax(33952),
        tcaAdaptorEthPortOutsizedStatsOversizedGoodCrcPacketsDeltaAvg(33953),
        tcaAdaptorEthPortOutsizedStatsOversizedBadCrcPacketsDelta(33960),
        tcaAdaptorEthPortOutsizedStatsOversizedBadCrcPacketsDeltaMin(33961),
        tcaAdaptorEthPortOutsizedStatsOversizedBadCrcPacketsDeltaMax(33962),
        tcaAdaptorEthPortOutsizedStatsOversizedBadCrcPacketsDeltaAvg(33963),
        tcaAdaptorEthPortOutsizedStatsUndersizedGoodCrcPacketsDelta(33970),
        tcaAdaptorEthPortOutsizedStatsUndersizedGoodCrcPacketsDeltaMin(33971),
        tcaAdaptorEthPortOutsizedStatsUndersizedGoodCrcPacketsDeltaMax(33972),
        tcaAdaptorEthPortOutsizedStatsUndersizedGoodCrcPacketsDeltaAvg(33973),
        tcaAdaptorEthPortOutsizedStatsUndersizedBadCrcPacketsDelta(33980),
        tcaAdaptorEthPortOutsizedStatsUndersizedBadCrcPacketsDeltaMin(33981),
        tcaAdaptorEthPortOutsizedStatsUndersizedBadCrcPacketsDeltaMax(33982),
        tcaAdaptorEthPortOutsizedStatsUndersizedBadCrcPacketsDeltaAvg(33983),
        tcaAdaptorEthPortMcastStatsUnicastPacketsDelta(33995),
        tcaAdaptorEthPortMcastStatsUnicastPacketsDeltaMin(33996),
        tcaAdaptorEthPortMcastStatsUnicastPacketsDeltaMax(33997),
        tcaAdaptorEthPortMcastStatsUnicastPacketsDeltaAvg(33998),
        tcaAdaptorEthPortMcastStatsMulticastPacketsDelta(34005),
        tcaAdaptorEthPortMcastStatsMulticastPacketsDeltaMin(34006),
        tcaAdaptorEthPortMcastStatsMulticastPacketsDeltaMax(34007),
        tcaAdaptorEthPortMcastStatsMulticastPacketsDeltaAvg(34008),
        tcaAdaptorEthPortMcastStatsBroadcastPacketsDelta(34015),
        tcaAdaptorEthPortMcastStatsBroadcastPacketsDeltaMin(34016),
        tcaAdaptorEthPortMcastStatsBroadcastPacketsDeltaMax(34017),
        tcaAdaptorEthPortMcastStatsBroadcastPacketsDeltaAvg(34018),
        tcaAdaptorEthPortErrStatsMacDiscardedPacketsDelta(34030),
        tcaAdaptorEthPortErrStatsMacDiscardedPacketsDeltaMin(34031),
        tcaAdaptorEthPortErrStatsMacDiscardedPacketsDeltaMax(34032),
        tcaAdaptorEthPortErrStatsMacDiscardedPacketsDeltaAvg(34033),
        tcaAdaptorEthPortErrStatsBadCrcPacketsDelta(34040),
        tcaAdaptorEthPortErrStatsBadCrcPacketsDeltaMin(34041),
        tcaAdaptorEthPortErrStatsBadCrcPacketsDeltaMax(34042),
        tcaAdaptorEthPortErrStatsBadCrcPacketsDeltaAvg(34043),
        tcaAdaptorEthPortErrStatsBadLengthPacketsDelta(34050),
        tcaAdaptorEthPortErrStatsBadLengthPacketsDeltaMin(34051),
        tcaAdaptorEthPortErrStatsBadLengthPacketsDeltaMax(34052),
        tcaAdaptorEthPortErrStatsBadLengthPacketsDeltaAvg(34053),
        tcaAdaptorFcPortStatsRxFramesDelta(34064),
        tcaAdaptorFcPortStatsRxFramesDeltaMin(34065),
        tcaAdaptorFcPortStatsRxFramesDeltaMax(34066),
        tcaAdaptorFcPortStatsRxFramesDeltaAvg(34067),
        tcaAdaptorFcPortStatsTxFramesDelta(34074),
        tcaAdaptorFcPortStatsTxFramesDeltaMin(34075),
        tcaAdaptorFcPortStatsTxFramesDeltaMax(34076),
        tcaAdaptorFcPortStatsTxFramesDeltaAvg(34077),
        tcaAdaptorFcPortStatsRxBadFramesDelta(34084),
        tcaAdaptorFcPortStatsRxBadFramesDeltaMin(34085),
        tcaAdaptorFcPortStatsRxBadFramesDeltaMax(34086),
        tcaAdaptorFcPortStatsRxBadFramesDeltaAvg(34087),
        tcaAdaptorFcPortStatsTxBadFramesDelta(34094),
        tcaAdaptorFcPortStatsTxBadFramesDeltaMin(34095),
        tcaAdaptorFcPortStatsTxBadFramesDeltaMax(34096),
        tcaAdaptorFcPortStatsTxBadFramesDeltaAvg(34097),
        tcaAdaptorVnicStatsPacketsTxDelta(34108),
        tcaAdaptorVnicStatsPacketsTxDeltaMin(34109),
        tcaAdaptorVnicStatsPacketsTxDeltaMax(34110),
        tcaAdaptorVnicStatsPacketsTxDeltaAvg(34111),
        tcaAdaptorVnicStatsPacketsRxDelta(34118),
        tcaAdaptorVnicStatsPacketsRxDeltaMin(34119),
        tcaAdaptorVnicStatsPacketsRxDeltaMax(34120),
        tcaAdaptorVnicStatsPacketsRxDeltaAvg(34121),
        tcaAdaptorVnicStatsBytesTxDelta(34128),
        tcaAdaptorVnicStatsBytesTxDeltaMin(34129),
        tcaAdaptorVnicStatsBytesTxDeltaMax(34130),
        tcaAdaptorVnicStatsBytesTxDeltaAvg(34131),
        tcaAdaptorVnicStatsBytesRxDelta(34138),
        tcaAdaptorVnicStatsBytesRxDeltaMin(34139),
        tcaAdaptorVnicStatsBytesRxDeltaMax(34140),
        tcaAdaptorVnicStatsBytesRxDeltaAvg(34141),
        tcaAdaptorVnicStatsErrorsTxDelta(34148),
        tcaAdaptorVnicStatsErrorsTxDeltaMin(34149),
        tcaAdaptorVnicStatsErrorsTxDeltaMax(34150),
        tcaAdaptorVnicStatsErrorsTxDeltaAvg(34151),
        tcaAdaptorVnicStatsErrorsRxDelta(34158),
        tcaAdaptorVnicStatsErrorsRxDeltaMin(34159),
        tcaAdaptorVnicStatsErrorsRxDeltaMax(34160),
        tcaAdaptorVnicStatsErrorsRxDeltaAvg(34161),
        tcaAdaptorVnicStatsDroppedTxDelta(34168),
        tcaAdaptorVnicStatsDroppedTxDeltaMin(34169),
        tcaAdaptorVnicStatsDroppedTxDeltaMax(34170),
        tcaAdaptorVnicStatsDroppedTxDeltaAvg(34171),
        tcaAdaptorVnicStatsDroppedRxDelta(34178),
        tcaAdaptorVnicStatsDroppedRxDeltaMin(34179),
        tcaAdaptorVnicStatsDroppedRxDeltaMax(34180),
        tcaAdaptorVnicStatsDroppedRxDeltaAvg(34181),
        tcaAdaptorFcIffc4StatsInputRequestsDelta(34192),
        tcaAdaptorFcIffc4StatsInputRequestsDeltaMin(34193),
        tcaAdaptorFcIffc4StatsInputRequestsDeltaMax(34194),
        tcaAdaptorFcIffc4StatsInputRequestsDeltaAvg(34195),
        tcaAdaptorFcIffc4StatsOutputRequestsDelta(34202),
        tcaAdaptorFcIffc4StatsOutputRequestsDeltaMin(34203),
        tcaAdaptorFcIffc4StatsOutputRequestsDeltaMax(34204),
        tcaAdaptorFcIffc4StatsOutputRequestsDeltaAvg(34205),
        tcaAdaptorFcIffc4StatsControlRequestsDelta(34212),
        tcaAdaptorFcIffc4StatsControlRequestsDeltaMin(34213),
        tcaAdaptorFcIffc4StatsControlRequestsDeltaMax(34214),
        tcaAdaptorFcIffc4StatsControlRequestsDeltaAvg(34215),
        tcaAdaptorFcIffc4StatsInputMegabytesDelta(34222),
        tcaAdaptorFcIffc4StatsInputMegabytesDeltaMin(34223),
        tcaAdaptorFcIffc4StatsInputMegabytesDeltaMax(34224),
        tcaAdaptorFcIffc4StatsInputMegabytesDeltaAvg(34225),
        tcaAdaptorFcIffc4StatsOutputMegabytesDelta(34232),
        tcaAdaptorFcIffc4StatsOutputMegabytesDeltaMin(34233),
        tcaAdaptorFcIffc4StatsOutputMegabytesDeltaMax(34234),
        tcaAdaptorFcIffc4StatsOutputMegabytesDeltaAvg(34235),
        tcaAdaptorMenloBaseErrorStatsCorrectableErrorsDelta(34246),
        tcaAdaptorMenloBaseErrorStatsCorrectableErrorsDeltaMin(34247),
        tcaAdaptorMenloBaseErrorStatsCorrectableErrorsDeltaMax(34248),
        tcaAdaptorMenloBaseErrorStatsCorrectableErrorsDeltaAvg(34249),
        tcaAdaptorMenloBaseErrorStatsUncorrectableErrorsDelta(34256),
        tcaAdaptorMenloBaseErrorStatsUncorrectableErrorsDeltaMin(34257),
        tcaAdaptorMenloBaseErrorStatsUncorrectableErrorsDeltaMax(34258),
        tcaAdaptorMenloBaseErrorStatsUncorrectableErrorsDeltaAvg(34259),
        tcaAdaptorMenloMcpuStatsDropAclDelta(34271),
        tcaAdaptorMenloMcpuStatsDropAclDeltaMin(34272),
        tcaAdaptorMenloMcpuStatsDropAclDeltaMax(34273),
        tcaAdaptorMenloMcpuStatsDropAclDeltaAvg(34274),
        tcaAdaptorMenloMcpuStatsDropOverrunDelta(34281),
        tcaAdaptorMenloMcpuStatsDropOverrunDeltaMin(34282),
        tcaAdaptorMenloMcpuStatsDropOverrunDeltaMax(34283),
        tcaAdaptorMenloMcpuStatsDropOverrunDeltaAvg(34284),
        tcaAdaptorMenloMcpuStatsDropRuntDelta(34291),
        tcaAdaptorMenloMcpuStatsDropRuntDeltaMin(34292),
        tcaAdaptorMenloMcpuStatsDropRuntDeltaMax(34293),
        tcaAdaptorMenloMcpuStatsDropRuntDeltaAvg(34294),
        tcaAdaptorMenloMcpuStatsTruncateOverrunDelta(34301),
        tcaAdaptorMenloMcpuStatsTruncateOverrunDeltaMin(34302),
        tcaAdaptorMenloMcpuStatsTruncateOverrunDeltaMax(34303),
        tcaAdaptorMenloMcpuStatsTruncateOverrunDeltaAvg(34304),
        tcaAdaptorMenloMcpuErrorStatsCorrectableErrorsDelta(34316),
        tcaAdaptorMenloMcpuErrorStatsCorrectableErrorsDeltaMin(34317),
        tcaAdaptorMenloMcpuErrorStatsCorrectableErrorsDeltaMax(34318),
        tcaAdaptorMenloMcpuErrorStatsCorrectableErrorsDeltaAvg(34319),
        tcaAdaptorMenloMcpuErrorStatsPopErrorsDelta(34326),
        tcaAdaptorMenloMcpuErrorStatsPopErrorsDeltaMin(34327),
        tcaAdaptorMenloMcpuErrorStatsPopErrorsDeltaMax(34328),
        tcaAdaptorMenloMcpuErrorStatsPopErrorsDeltaAvg(34329),
        tcaAdaptorMenloMcpuErrorStatsPushErrorsDelta(34336),
        tcaAdaptorMenloMcpuErrorStatsPushErrorsDeltaMin(34337),
        tcaAdaptorMenloMcpuErrorStatsPushErrorsDeltaMax(34338),
        tcaAdaptorMenloMcpuErrorStatsPushErrorsDeltaAvg(34339),
        tcaAdaptorMenloMcpuErrorStatsUncorrectableErrorsDelta(34346),
        tcaAdaptorMenloMcpuErrorStatsUncorrectableErrorsDeltaMin(34347),
        tcaAdaptorMenloMcpuErrorStatsUncorrectableErrorsDeltaMax(34348),
        tcaAdaptorMenloMcpuErrorStatsUncorrectableErrorsDeltaAvg(34349),
        tcaAdaptorMenloEthStatsDropOverrunDelta(34361),
        tcaAdaptorMenloEthStatsDropOverrunDeltaMin(34362),
        tcaAdaptorMenloEthStatsDropOverrunDeltaMax(34363),
        tcaAdaptorMenloEthStatsDropOverrunDeltaAvg(34364),
        tcaAdaptorMenloEthStatsDropRuntDelta(34371),
        tcaAdaptorMenloEthStatsDropRuntDeltaMin(34372),
        tcaAdaptorMenloEthStatsDropRuntDeltaMax(34373),
        tcaAdaptorMenloEthStatsDropRuntDeltaAvg(34374),
        tcaAdaptorMenloEthStatsTruncateOverrunDelta(34381),
        tcaAdaptorMenloEthStatsTruncateOverrunDeltaMin(34382),
        tcaAdaptorMenloEthStatsTruncateOverrunDeltaMax(34383),
        tcaAdaptorMenloEthStatsTruncateOverrunDeltaAvg(34384),
        tcaAdaptorMenloEthErrorStatsCorrectableErrorsDelta(34396),
        tcaAdaptorMenloEthErrorStatsCorrectableErrorsDeltaMin(34397),
        tcaAdaptorMenloEthErrorStatsCorrectableErrorsDeltaMax(34398),
        tcaAdaptorMenloEthErrorStatsCorrectableErrorsDeltaAvg(34399),
        tcaAdaptorMenloEthErrorStatsDropAclDelta(34406),
        tcaAdaptorMenloEthErrorStatsDropAclDeltaMin(34407),
        tcaAdaptorMenloEthErrorStatsDropAclDeltaMax(34408),
        tcaAdaptorMenloEthErrorStatsDropAclDeltaAvg(34409),
        tcaAdaptorMenloEthErrorStatsPopErrorsDelta(34416),
        tcaAdaptorMenloEthErrorStatsPopErrorsDeltaMin(34417),
        tcaAdaptorMenloEthErrorStatsPopErrorsDeltaMax(34418),
        tcaAdaptorMenloEthErrorStatsPopErrorsDeltaAvg(34419),
        tcaAdaptorMenloEthErrorStatsPushErrorsDelta(34426),
        tcaAdaptorMenloEthErrorStatsPushErrorsDeltaMin(34427),
        tcaAdaptorMenloEthErrorStatsPushErrorsDeltaMax(34428),
        tcaAdaptorMenloEthErrorStatsPushErrorsDeltaAvg(34429),
        tcaAdaptorMenloEthErrorStatsUncorrectableErrorsDelta(34436),
        tcaAdaptorMenloEthErrorStatsUncorrectableErrorsDeltaMin(34437),
        tcaAdaptorMenloEthErrorStatsUncorrectableErrorsDeltaMax(34438),
        tcaAdaptorMenloEthErrorStatsUncorrectableErrorsDeltaAvg(34439),
        tcaAdaptorMenloFcStatsDropAclDelta(34451),
        tcaAdaptorMenloFcStatsDropAclDeltaMin(34452),
        tcaAdaptorMenloFcStatsDropAclDeltaMax(34453),
        tcaAdaptorMenloFcStatsDropAclDeltaAvg(34454),
        tcaAdaptorMenloFcStatsDropOverrunDelta(34461),
        tcaAdaptorMenloFcStatsDropOverrunDeltaMin(34462),
        tcaAdaptorMenloFcStatsDropOverrunDeltaMax(34463),
        tcaAdaptorMenloFcStatsDropOverrunDeltaAvg(34464),
        tcaAdaptorMenloFcStatsDropRuntDelta(34471),
        tcaAdaptorMenloFcStatsDropRuntDeltaMin(34472),
        tcaAdaptorMenloFcStatsDropRuntDeltaMax(34473),
        tcaAdaptorMenloFcStatsDropRuntDeltaAvg(34474),
        tcaAdaptorMenloFcStatsTruncateOverrunDelta(34481),
        tcaAdaptorMenloFcStatsTruncateOverrunDeltaMin(34482),
        tcaAdaptorMenloFcStatsTruncateOverrunDeltaMax(34483),
        tcaAdaptorMenloFcStatsTruncateOverrunDeltaAvg(34484),
        tcaAdaptorMenloFcErrorStatsCorrectableErrorsDelta(34496),
        tcaAdaptorMenloFcErrorStatsCorrectableErrorsDeltaMin(34497),
        tcaAdaptorMenloFcErrorStatsCorrectableErrorsDeltaMax(34498),
        tcaAdaptorMenloFcErrorStatsCorrectableErrorsDeltaAvg(34499),
        tcaAdaptorMenloFcErrorStatsPopErrorsDelta(34506),
        tcaAdaptorMenloFcErrorStatsPopErrorsDeltaMin(34507),
        tcaAdaptorMenloFcErrorStatsPopErrorsDeltaMax(34508),
        tcaAdaptorMenloFcErrorStatsPopErrorsDeltaAvg(34509),
        tcaAdaptorMenloFcErrorStatsPushErrorsDelta(34516),
        tcaAdaptorMenloFcErrorStatsPushErrorsDeltaMin(34517),
        tcaAdaptorMenloFcErrorStatsPushErrorsDeltaMax(34518),
        tcaAdaptorMenloFcErrorStatsPushErrorsDeltaAvg(34519),
        tcaAdaptorMenloFcErrorStatsUncorrectableErrorsDelta(34526),
        tcaAdaptorMenloFcErrorStatsUncorrectableErrorsDeltaMin(34527),
        tcaAdaptorMenloFcErrorStatsUncorrectableErrorsDeltaMax(34528),
        tcaAdaptorMenloFcErrorStatsUncorrectableErrorsDeltaAvg(34529),
        tcaAdaptorMenloqstatsDropOverrunN0Delta(34542),
        tcaAdaptorMenloqstatsDropOverrunN0DeltaMin(34543),
        tcaAdaptorMenloqstatsDropOverrunN0DeltaMax(34544),
        tcaAdaptorMenloqstatsDropOverrunN0DeltaAvg(34545),
        tcaAdaptorMenloqstatsDropOverrunN1Delta(34552),
        tcaAdaptorMenloqstatsDropOverrunN1DeltaMin(34553),
        tcaAdaptorMenloqstatsDropOverrunN1DeltaMax(34554),
        tcaAdaptorMenloqstatsDropOverrunN1DeltaAvg(34555),
        tcaAdaptorMenloqstatsTruncateOverrunN0Delta(34562),
        tcaAdaptorMenloqstatsTruncateOverrunN0DeltaMin(34563),
        tcaAdaptorMenloqstatsTruncateOverrunN0DeltaMax(34564),
        tcaAdaptorMenloqstatsTruncateOverrunN0DeltaAvg(34565),
        tcaAdaptorMenloqstatsTruncateOverrunN1Delta(34572),
        tcaAdaptorMenloqstatsTruncateOverrunN1DeltaMin(34573),
        tcaAdaptorMenloqstatsTruncateOverrunN1DeltaMax(34574),
        tcaAdaptorMenloqstatsTruncateOverrunN1DeltaAvg(34575),
        tcaAdaptorMenloqerrorStatsCorrectableErrorsDelta(34588),
        tcaAdaptorMenloqerrorStatsCorrectableErrorsDeltaMin(34589),
        tcaAdaptorMenloqerrorStatsCorrectableErrorsDeltaMax(34590),
        tcaAdaptorMenloqerrorStatsCorrectableErrorsDeltaAvg(34591),
        tcaAdaptorMenloqerrorStatsPopErrorsDelta(34598),
        tcaAdaptorMenloqerrorStatsPopErrorsDeltaMin(34599),
        tcaAdaptorMenloqerrorStatsPopErrorsDeltaMax(34600),
        tcaAdaptorMenloqerrorStatsPopErrorsDeltaAvg(34601),
        tcaAdaptorMenloqerrorStatsPushErrorsDelta(34608),
        tcaAdaptorMenloqerrorStatsPushErrorsDeltaMin(34609),
        tcaAdaptorMenloqerrorStatsPushErrorsDeltaMax(34610),
        tcaAdaptorMenloqerrorStatsPushErrorsDeltaAvg(34611),
        tcaAdaptorMenloqerrorStatsUncorrectableErrorsDelta(34618),
        tcaAdaptorMenloqerrorStatsUncorrectableErrorsDeltaMin(34619),
        tcaAdaptorMenloqerrorStatsUncorrectableErrorsDeltaMax(34620),
        tcaAdaptorMenloqerrorStatsUncorrectableErrorsDeltaAvg(34621),
        tcaAdaptorMenloNetEgStatsLearnReqDropDelta(34633),
        tcaAdaptorMenloNetEgStatsLearnReqDropDeltaMin(34634),
        tcaAdaptorMenloNetEgStatsLearnReqDropDeltaMax(34635),
        tcaAdaptorMenloNetEgStatsLearnReqDropDeltaAvg(34636),
        tcaAdaptorMenloNetEgStatsDropCmdDelta(34643),
        tcaAdaptorMenloNetEgStatsDropCmdDeltaMin(34644),
        tcaAdaptorMenloNetEgStatsDropCmdDeltaMax(34645),
        tcaAdaptorMenloNetEgStatsDropCmdDeltaAvg(34646),
        tcaAdaptorMenloNetEgStatsDropLifCfgInvalidDelta(34653),
        tcaAdaptorMenloNetEgStatsDropLifCfgInvalidDeltaMin(34654),
        tcaAdaptorMenloNetEgStatsDropLifCfgInvalidDeltaMax(34655),
        tcaAdaptorMenloNetEgStatsDropLifCfgInvalidDeltaAvg(34656),
        tcaAdaptorMenloNetEgStatsDropLifMapNoHitDelta(34663),
        tcaAdaptorMenloNetEgStatsDropLifMapNoHitDeltaMin(34664),
        tcaAdaptorMenloNetEgStatsDropLifMapNoHitDeltaMax(34665),
        tcaAdaptorMenloNetEgStatsDropLifMapNoHitDeltaAvg(34666),
        tcaAdaptorMenloNetEgStatsDropSrcBindDelta(34673),
        tcaAdaptorMenloNetEgStatsDropSrcBindDeltaMin(34674),
        tcaAdaptorMenloNetEgStatsDropSrcBindDeltaMax(34675),
        tcaAdaptorMenloNetEgStatsDropSrcBindDeltaAvg(34676),
        tcaAdaptorMenloNetInStatsFwdLookupNoHitDelta(34688),
        tcaAdaptorMenloNetInStatsFwdLookupNoHitDeltaMin(34689),
        tcaAdaptorMenloNetInStatsFwdLookupNoHitDeltaMax(34690),
        tcaAdaptorMenloNetInStatsFwdLookupNoHitDeltaAvg(34691),
        tcaAdaptorMenloNetInStatsDropFcMulticastDelta(34698),
        tcaAdaptorMenloNetInStatsDropFcMulticastDeltaMin(34699),
        tcaAdaptorMenloNetInStatsDropFcMulticastDeltaMax(34700),
        tcaAdaptorMenloNetInStatsDropFcMulticastDeltaAvg(34701),
        tcaAdaptorMenloNetInStatsDropFcLifInvalidDelta(34708),
        tcaAdaptorMenloNetInStatsDropFcLifInvalidDeltaMin(34709),
        tcaAdaptorMenloNetInStatsDropFcLifInvalidDeltaMax(34710),
        tcaAdaptorMenloNetInStatsDropFcLifInvalidDeltaAvg(34711),
        tcaAdaptorMenloNetInStatsDropNullPifDelta(34718),
        tcaAdaptorMenloNetInStatsDropNullPifDeltaMin(34719),
        tcaAdaptorMenloNetInStatsDropNullPifDeltaMax(34720),
        tcaAdaptorMenloNetInStatsDropNullPifDeltaAvg(34721),
        tcaAdaptorMenloHostPortStatsRxPausecfcdelta(34733),
        tcaAdaptorMenloHostPortStatsRxPausecfcdeltaMin(34734),
        tcaAdaptorMenloHostPortStatsRxPausecfcdeltaMax(34735),
        tcaAdaptorMenloHostPortStatsRxPausecfcdeltaAvg(34736),
        tcaAdaptorMenloHostPortStatsRxPausepfcdelta(34743),
        tcaAdaptorMenloHostPortStatsRxPausepfcdeltaMin(34744),
        tcaAdaptorMenloHostPortStatsRxPausepfcdeltaMax(34745),
        tcaAdaptorMenloHostPortStatsRxPausepfcdeltaAvg(34746),
        tcaAdaptorMenloHostPortStatsTxPausecfcdelta(34753),
        tcaAdaptorMenloHostPortStatsTxPausecfcdeltaMin(34754),
        tcaAdaptorMenloHostPortStatsTxPausecfcdeltaMax(34755),
        tcaAdaptorMenloHostPortStatsTxPausecfcdeltaAvg(34756),
        tcaAdaptorMenloHostPortStatsTxPausepfcdelta(34763),
        tcaAdaptorMenloHostPortStatsTxPausepfcdeltaMin(34764),
        tcaAdaptorMenloHostPortStatsTxPausepfcdeltaMax(34765),
        tcaAdaptorMenloHostPortStatsTxPausepfcdeltaAvg(34766),
        tcaAdaptorMenloDcePortStatsRxPausecfcdelta(34778),
        tcaAdaptorMenloDcePortStatsRxPausecfcdeltaMin(34779),
        tcaAdaptorMenloDcePortStatsRxPausecfcdeltaMax(34780),
        tcaAdaptorMenloDcePortStatsRxPausecfcdeltaAvg(34781),
        tcaAdaptorMenloDcePortStatsRxPausepfcdelta(34788),
        tcaAdaptorMenloDcePortStatsRxPausepfcdeltaMin(34789),
        tcaAdaptorMenloDcePortStatsRxPausepfcdeltaMax(34790),
        tcaAdaptorMenloDcePortStatsRxPausepfcdeltaAvg(34791),
        tcaAdaptorMenloDcePortStatsTxPausecfcdelta(34798),
        tcaAdaptorMenloDcePortStatsTxPausecfcdeltaMin(34799),
        tcaAdaptorMenloDcePortStatsTxPausecfcdeltaMax(34800),
        tcaAdaptorMenloDcePortStatsTxPausecfcdeltaAvg(34801),
        tcaAdaptorMenloDcePortStatsTxPausepfcdelta(34808),
        tcaAdaptorMenloDcePortStatsTxPausepfcdeltaMin(34809),
        tcaAdaptorMenloDcePortStatsTxPausepfcdeltaMax(34810),
        tcaAdaptorMenloDcePortStatsTxPausepfcdeltaAvg(34811),
        tcaAdaptorEtherIfStatsTxBytesDelta(34822),
        tcaAdaptorEtherIfStatsTxBytesDeltaMin(34823),
        tcaAdaptorEtherIfStatsTxBytesDeltaMax(34824),
        tcaAdaptorEtherIfStatsTxBytesDeltaAvg(34825),
        tcaAdaptorEtherIfStatsTxPacketsDelta(34832),
        tcaAdaptorEtherIfStatsTxPacketsDeltaMin(34833),
        tcaAdaptorEtherIfStatsTxPacketsDeltaMax(34834),
        tcaAdaptorEtherIfStatsTxPacketsDeltaAvg(34835),
        tcaAdaptorEtherIfStatsTxErrorsDelta(34842),
        tcaAdaptorEtherIfStatsTxErrorsDeltaMin(34843),
        tcaAdaptorEtherIfStatsTxErrorsDeltaMax(34844),
        tcaAdaptorEtherIfStatsTxErrorsDeltaAvg(34845),
        tcaAdaptorEtherIfStatsTxDroppedDelta(34852),
        tcaAdaptorEtherIfStatsTxDroppedDeltaMin(34853),
        tcaAdaptorEtherIfStatsTxDroppedDeltaMax(34854),
        tcaAdaptorEtherIfStatsTxDroppedDeltaAvg(34855),
        tcaAdaptorEtherIfStatsRxBytesDelta(34862),
        tcaAdaptorEtherIfStatsRxBytesDeltaMin(34863),
        tcaAdaptorEtherIfStatsRxBytesDeltaMax(34864),
        tcaAdaptorEtherIfStatsRxBytesDeltaAvg(34865),
        tcaAdaptorEtherIfStatsRxPacketsDelta(34872),
        tcaAdaptorEtherIfStatsRxPacketsDeltaMin(34873),
        tcaAdaptorEtherIfStatsRxPacketsDeltaMax(34874),
        tcaAdaptorEtherIfStatsRxPacketsDeltaAvg(34875),
        tcaAdaptorEtherIfStatsRxErrorsDelta(34882),
        tcaAdaptorEtherIfStatsRxErrorsDeltaMin(34883),
        tcaAdaptorEtherIfStatsRxErrorsDeltaMax(34884),
        tcaAdaptorEtherIfStatsRxErrorsDeltaAvg(34885),
        tcaAdaptorEtherIfStatsRxDroppedDelta(34892),
        tcaAdaptorEtherIfStatsRxDroppedDeltaMin(34893),
        tcaAdaptorEtherIfStatsRxDroppedDeltaMax(34894),
        tcaAdaptorEtherIfStatsRxDroppedDeltaAvg(34895),
        tcaAdaptorFcIfFrameStatsTxFramesDelta(34906),
        tcaAdaptorFcIfFrameStatsTxFramesDeltaMin(34907),
        tcaAdaptorFcIfFrameStatsTxFramesDeltaMax(34908),
        tcaAdaptorFcIfFrameStatsTxFramesDeltaAvg(34909),
        tcaAdaptorFcIfFrameStatsRxFramesDelta(34916),
        tcaAdaptorFcIfFrameStatsRxFramesDeltaMin(34917),
        tcaAdaptorFcIfFrameStatsRxFramesDeltaMax(34918),
        tcaAdaptorFcIfFrameStatsRxFramesDeltaAvg(34919),
        tcaAdaptorFcIfFrameStatsErrorFramesDelta(34926),
        tcaAdaptorFcIfFrameStatsErrorFramesDeltaMin(34927),
        tcaAdaptorFcIfFrameStatsErrorFramesDeltaMax(34928),
        tcaAdaptorFcIfFrameStatsErrorFramesDeltaAvg(34929),
        tcaAdaptorFcIfFrameStatsDumpedFramesDelta(34936),
        tcaAdaptorFcIfFrameStatsDumpedFramesDeltaMin(34937),
        tcaAdaptorFcIfFrameStatsDumpedFramesDeltaMax(34938),
        tcaAdaptorFcIfFrameStatsDumpedFramesDeltaAvg(34939),
        tcaAdaptorFcIfEventStatsLipCountDelta(34950),
        tcaAdaptorFcIfEventStatsLipCountDeltaMin(34951),
        tcaAdaptorFcIfEventStatsLipCountDeltaMax(34952),
        tcaAdaptorFcIfEventStatsLipCountDeltaAvg(34953),
        tcaAdaptorFcIfEventStatsInvalidcrccountDelta(34960),
        tcaAdaptorFcIfEventStatsInvalidcrccountDeltaMin(34961),
        tcaAdaptorFcIfEventStatsInvalidcrccountDeltaMax(34962),
        tcaAdaptorFcIfEventStatsInvalidcrccountDeltaAvg(34963),
        tcaAdaptorFcIfEventStatsNoscountDelta(34970),
        tcaAdaptorFcIfEventStatsNoscountDeltaMin(34971),
        tcaAdaptorFcIfEventStatsNoscountDeltaMax(34972),
        tcaAdaptorFcIfEventStatsNoscountDeltaAvg(34973),
        tcaAdaptorFcIfEventStatsLinkFailureCountDelta(34980),
        tcaAdaptorFcIfEventStatsLinkFailureCountDeltaMin(34981),
        tcaAdaptorFcIfEventStatsLinkFailureCountDeltaMax(34982),
        tcaAdaptorFcIfEventStatsLinkFailureCountDeltaAvg(34983),
        tcaAdaptorFcIfEventStatsLossOfSyncCountDelta(34990),
        tcaAdaptorFcIfEventStatsLossOfSyncCountDeltaMin(34991),
        tcaAdaptorFcIfEventStatsLossOfSyncCountDeltaMax(34992),
        tcaAdaptorFcIfEventStatsLossOfSyncCountDeltaAvg(34993),
        tcaAdaptorFcIfEventStatsLossOfSignalCountDelta(35000),
        tcaAdaptorFcIfEventStatsLossOfSignalCountDeltaMin(35001),
        tcaAdaptorFcIfEventStatsLossOfSignalCountDeltaMax(35002),
        tcaAdaptorFcIfEventStatsLossOfSignalCountDeltaAvg(35003),
        tcaAdaptorFcIfEventStatsSeqProtocolErrCountDelta(35010),
        tcaAdaptorFcIfEventStatsSeqProtocolErrCountDeltaMin(35011),
        tcaAdaptorFcIfEventStatsSeqProtocolErrCountDeltaMax(35012),
        tcaAdaptorFcIfEventStatsSeqProtocolErrCountDeltaAvg(35013),
        tcaAdaptorFcIfEventStatsSecondsSinceLastResetDelta(35020),
        tcaAdaptorFcIfEventStatsSecondsSinceLastResetDeltaMin(35021),
        tcaAdaptorFcIfEventStatsSecondsSinceLastResetDeltaMax(35022),
        tcaAdaptorFcIfEventStatsSecondsSinceLastResetDeltaAvg(35023),
        tcaMemoryErrorStatsEccMultibitErrorsMin(35163),
        tcaMemoryErrorStatsEccMultibitErrorsMax(35164),
        tcaMemoryErrorStatsEccMultibitErrorsAvg(35165),
        tcaSwEnvStatsMainBoardOutlet1(35166),
        tcaSwEnvStatsMainBoardOutlet1Min(35168),
        tcaSwEnvStatsMainBoardOutlet1Max(35169),
        tcaSwEnvStatsMainBoardOutlet1Avg(35170),
        tcaMemoryErrorStatsEccSinglebitErrorsMin(35173),
        tcaSwEnvStatsMainBoardOutlet2(35174),
        tcaMemoryErrorStatsEccSinglebitErrorsAvg(35175),
        tcaSwEnvStatsMainBoardOutlet2Min(35176),
        tcaSwEnvStatsMainBoardOutlet2Max(35177),
        tcaSwEnvStatsMainBoardOutlet2Avg(35178),
        tcaMemoryErrorStatsAddressParityErrorsMin(35183),
        tcaMemoryErrorStatsAddressParityErrorsMax(35184),
        tcaMemoryErrorStatsAddressParityErrorsAvg(35185),
        tcaMemoryErrorStatsAddressParityErrorsRunning(35186),
        tcaMemoryErrorStatsMismatchErrorsMin(35193),
        tcaMemoryErrorStatsMismatchErrorsMax(35194),
        tcaMemoryErrorStatsMismatchErrorsAvg(35195),
        tcaMemoryErrorStatsMismatchErrorsRunning(35196),
        tcaSwEnvStatsFanCtrlrInlet1(35198),
        tcaSwEnvStatsFanCtrlrInlet1Min(35200),
        tcaSwEnvStatsFanCtrlrInlet1Max(35201),
        tcaSwEnvStatsFanCtrlrInlet1Avg(35202),
        tcaSwEnvStatsFanCtrlrInlet2(35206),
        tcaSwEnvStatsFanCtrlrInlet2Min(35208),
        tcaSwEnvStatsFanCtrlrInlet2Max(35209),
        tcaSwEnvStatsFanCtrlrInlet2Avg(35210),
        tcaSwEnvStatsFanCtrlrInlet3(35214),
        tcaSwEnvStatsFanCtrlrInlet3Min(35216),
        tcaSwEnvStatsFanCtrlrInlet3Max(35217),
        tcaSwEnvStatsFanCtrlrInlet3Avg(35218),
        tcaSwEnvStatsFanCtrlrInlet4(35222),
        tcaSwEnvStatsFanCtrlrInlet4Min(35224),
        tcaSwEnvStatsFanCtrlrInlet4Max(35225),
        tcaSwEnvStatsFanCtrlrInlet4Avg(35226),
        tcaSwSystemStatsMemAvailable(35234),
        tcaSwSystemStatsMemAvailableMin(35236),
        tcaSwSystemStatsMemAvailableMax(35237),
        tcaSwSystemStatsMemAvailableAvg(35238),
        tcaSwSystemStatsMemCached(35242),
        tcaSwSystemStatsMemCachedMin(35244),
        tcaSwSystemStatsMemCachedMax(35245),
        tcaSwSystemStatsMemCachedAvg(35246),
        tcaSwSystemStatsLoad(35250),
        tcaSwSystemStatsLoadMin(35252),
        tcaSwSystemStatsLoadMax(35253),
        tcaSwSystemStatsLoadAvg(35254),
        tcaEtherTxStatsTotalBytesDelta(35275),
        tcaEtherTxStatsTotalBytesDeltaMin(35276),
        tcaEtherTxStatsTotalBytesDeltaMax(35277),
        tcaEtherTxStatsTotalBytesDeltaAvg(35278),
        tcaEtherTxStatsTotalPacketsDelta(35285),
        tcaEtherTxStatsTotalPacketsDeltaMin(35286),
        tcaEtherTxStatsTotalPacketsDeltaMax(35287),
        tcaEtherTxStatsTotalPacketsDeltaAvg(35288),
        tcaEtherTxStatsMulticastPacketsDelta(35295),
        tcaEtherTxStatsMulticastPacketsDeltaMin(35296),
        tcaEtherTxStatsMulticastPacketsDeltaMax(35297),
        tcaEtherTxStatsMulticastPacketsDeltaAvg(35298),
        tcaEtherTxStatsBroadcastPacketsDelta(35305),
        tcaEtherTxStatsBroadcastPacketsDeltaMin(35306),
        tcaEtherTxStatsBroadcastPacketsDeltaMax(35307),
        tcaEtherTxStatsBroadcastPacketsDeltaAvg(35308),
        tcaEtherTxStatsJumboPacketsDelta(35315),
        tcaEtherTxStatsJumboPacketsDeltaMin(35316),
        tcaEtherTxStatsJumboPacketsDeltaMax(35317),
        tcaEtherTxStatsJumboPacketsDeltaAvg(35318),
        tcaEtherRxStatsTotalBytesDelta(35329),
        tcaEtherRxStatsTotalBytesDeltaMin(35330),
        tcaEtherRxStatsTotalBytesDeltaMax(35331),
        tcaEtherRxStatsTotalBytesDeltaAvg(35332),
        tcaEtherRxStatsTotalPacketsDelta(35339),
        tcaEtherRxStatsTotalPacketsDeltaMin(35340),
        tcaEtherRxStatsTotalPacketsDeltaMax(35341),
        tcaEtherRxStatsTotalPacketsDeltaAvg(35342),
        tcaEtherRxStatsUnicastPacketsDelta(35349),
        tcaEtherRxStatsUnicastPacketsDeltaMin(35350),
        tcaEtherRxStatsUnicastPacketsDeltaMax(35351),
        tcaEtherRxStatsUnicastPacketsDeltaAvg(35352),
        tcaEtherRxStatsMulticastPacketsDelta(35359),
        tcaEtherRxStatsMulticastPacketsDeltaMin(35360),
        tcaEtherRxStatsMulticastPacketsDeltaMax(35361),
        tcaEtherRxStatsMulticastPacketsDeltaAvg(35362),
        tcaEtherRxStatsBroadcastPacketsDelta(35369),
        tcaEtherRxStatsBroadcastPacketsDeltaMin(35370),
        tcaEtherRxStatsBroadcastPacketsDeltaMax(35371),
        tcaEtherRxStatsBroadcastPacketsDeltaAvg(35372),
        tcaEtherRxStatsJumboPacketsDelta(35379),
        tcaEtherRxStatsJumboPacketsDeltaMin(35380),
        tcaEtherRxStatsJumboPacketsDeltaMax(35381),
        tcaEtherRxStatsJumboPacketsDeltaAvg(35382),
        tcaComputeMbPowerStatsConsumedPower(35962),
        tcaComputeMbPowerStatsConsumedPowerMin(35964),
        tcaComputeMbPowerStatsConsumedPowerMax(35965),
        tcaComputeMbPowerStatsConsumedPowerAvg(35966),
        tcaComputeMbTempStatsFmTempSenIo(35974),
        tcaComputeMbTempStatsFmTempSenIoMin(35976),
        tcaComputeMbTempStatsFmTempSenIoMax(35977),
        tcaComputeMbTempStatsFmTempSenIoAvg(35978),
        tcaEquipmentChassisStatsInputPower(36234),
        tcaEquipmentChassisStatsInputPowerMin(36236),
        tcaEquipmentChassisStatsInputPowerMax(36237),
        tcaEquipmentChassisStatsInputPowerAvg(36238),
        tcaEquipmentChassisStatsOutputPower(36242),
        tcaEquipmentChassisStatsOutputPowerMin(36244),
        tcaEquipmentChassisStatsOutputPowerMax(36245),
        tcaEquipmentChassisStatsOutputPowerAvg(36246),
        tcaEquipmentPsuStatsAmbientTemp(36266),
        tcaEquipmentPsuStatsAmbientTempMin(36268),
        tcaEquipmentPsuStatsAmbientTempMax(36269),
        tcaEquipmentPsuStatsAmbientTempAvg(36270),
        tcaEquipmentPsuStatsOutputCurrent(36274),
        tcaEquipmentPsuStatsOutputCurrentMin(36276),
        tcaEquipmentPsuStatsOutputCurrentMax(36277),
        tcaEquipmentPsuStatsOutputCurrentAvg(36278),
        tcaEquipmentPsuStatsOutputPower(36282),
        tcaEquipmentPsuStatsOutputPowerMin(36284),
        tcaEquipmentPsuStatsOutputPowerMax(36285),
        tcaEquipmentPsuStatsOutputPowerAvg(36286),
        tcaEquipmentPsuInputStatsCurrent(36294),
        tcaEquipmentPsuInputStatsCurrentMin(36296),
        tcaEquipmentPsuInputStatsCurrentMax(36297),
        tcaEquipmentPsuInputStatsCurrentAvg(36298),
        tcaEquipmentPsuInputStatsVoltage(36302),
        tcaEquipmentPsuInputStatsVoltageMin(36304),
        tcaEquipmentPsuInputStatsVoltageMax(36305),
        tcaEquipmentPsuInputStatsVoltageAvg(36306),
        tcaEquipmentPsuInputStatsPower(36310),
        tcaEquipmentPsuInputStatsPowerMin(36312),
        tcaEquipmentPsuInputStatsPowerMax(36313),
        tcaEquipmentPsuInputStatsPowerAvg(36314),
        tcaEquipmentFanModuleStatsAmbientTemp(36323),
        tcaEquipmentFanModuleStatsAmbientTempMin(36325),
        tcaEquipmentFanModuleStatsAmbientTempMax(36326),
        tcaEquipmentFanModuleStatsAmbientTempAvg(36327),
        tcaEquipmentFanStatsSpeed(36335),
        tcaEquipmentFanStatsSpeedMin(36337),
        tcaEquipmentFanStatsSpeedMax(36338),
        tcaEquipmentFanStatsSpeedAvg(36339),
        tcaEquipmentPsuStatsOutput12v(37154),
        tcaEquipmentPsuStatsOutput12vMin(37156),
        tcaEquipmentPsuStatsOutput12vMax(37157),
        tcaEquipmentPsuStatsOutput12vAvg(37158),
        tcaEquipmentPsuStatsOutput3v3(37162),
        tcaEquipmentPsuStatsOutput3v3Min(37164),
        tcaEquipmentPsuStatsOutput3v3Max(37165),
        tcaEquipmentPsuStatsOutput3v3Avg(37166),
        tcaEquipmentPsuStatsInput210v(37170),
        tcaEquipmentPsuStatsInput210vMin(37172),
        tcaEquipmentPsuStatsInput210vMax(37173),
        tcaEquipmentPsuStatsInput210vAvg(37174),
        tcaEquipmentIocardStatsAmbientTemp(37269),
        tcaEquipmentIocardStatsAmbientTempMin(37271),
        tcaEquipmentIocardStatsAmbientTempMax(37272),
        tcaEquipmentIocardStatsAmbientTempAvg(37273),
        tcaEtherErrStatsAlignDelta(37313),
        tcaEtherErrStatsAlignDeltaMin(37314),
        tcaEtherErrStatsAlignDeltaMax(37315),
        tcaEtherErrStatsAlignDeltaAvg(37316),
        tcaEtherErrStatsFcsDelta(37323),
        tcaEtherErrStatsFcsDeltaMin(37324),
        tcaEtherErrStatsFcsDeltaMax(37325),
        tcaEtherErrStatsFcsDeltaAvg(37326),
        tcaEtherErrStatsXmitDelta(37333),
        tcaEtherErrStatsXmitDeltaMin(37334),
        tcaEtherErrStatsXmitDeltaMax(37335),
        tcaEtherErrStatsXmitDeltaAvg(37336),
        tcaEtherErrStatsRcvDelta(37343),
        tcaEtherErrStatsRcvDeltaMin(37344),
        tcaEtherErrStatsRcvDeltaMax(37345),
        tcaEtherErrStatsRcvDeltaAvg(37346),
        tcaEtherErrStatsUnderSizeDelta(37353),
        tcaEtherErrStatsUnderSizeDeltaMin(37354),
        tcaEtherErrStatsUnderSizeDeltaMax(37355),
        tcaEtherErrStatsUnderSizeDeltaAvg(37356),
        tcaEtherErrStatsOutDiscardDelta(37363),
        tcaEtherErrStatsOutDiscardDeltaMin(37364),
        tcaEtherErrStatsOutDiscardDeltaMax(37365),
        tcaEtherErrStatsOutDiscardDeltaAvg(37366),
        tcaEtherErrStatsIntMacTxDelta(37383),
        tcaEtherErrStatsIntMacTxDeltaMin(37384),
        tcaEtherErrStatsIntMacTxDeltaMax(37385),
        tcaEtherErrStatsIntMacTxDeltaAvg(37386),
        tcaEtherErrStatsIntMacRxDelta(37393),
        tcaEtherErrStatsIntMacRxDeltaMin(37394),
        tcaEtherErrStatsIntMacRxDeltaMax(37395),
        tcaEtherErrStatsIntMacRxDeltaAvg(37396),
        tcaEtherLossStatsSingleCollisionDelta(37403),
        tcaEtherLossStatsSingleCollisionDeltaMin(37404),
        tcaEtherLossStatsSingleCollisionDeltaMax(37405),
        tcaEtherLossStatsSingleCollisionDeltaAvg(37406),
        tcaEtherLossStatsMultiCollisionDelta(37413),
        tcaEtherLossStatsMultiCollisionDeltaMin(37414),
        tcaEtherLossStatsMultiCollisionDeltaMax(37415),
        tcaEtherLossStatsMultiCollisionDeltaAvg(37416),
        tcaEtherLossStatsLateCollisionDelta(37423),
        tcaEtherLossStatsLateCollisionDeltaMin(37424),
        tcaEtherLossStatsLateCollisionDeltaMax(37425),
        tcaEtherLossStatsLateCollisionDeltaAvg(37426),
        tcaEtherLossStatsCarrierSenseDelta(37443),
        tcaEtherLossStatsCarrierSenseDeltaMin(37444),
        tcaEtherLossStatsCarrierSenseDeltaMax(37445),
        tcaEtherLossStatsCarrierSenseDeltaAvg(37446),
        tcaProcessorErrorStatsMirroringIntraSockErrorsMin(37451),
        tcaProcessorErrorStatsMirroringIntraSockErrorsMax(37452),
        tcaProcessorErrorStatsMirroringIntraSockErrorsAvg(37453),
        tcaProcessorErrorStatsMirroringIntraSockErrorsRunning(37454),
        tcaEtherLossStatsGiantsDeltaMax(37455),
        tcaEtherLossStatsGiantsDeltaAvg(37456),
        tcaProcessorErrorStatsMirroringInterSockErrorsMin(37461),
        tcaProcessorErrorStatsMirroringInterSockErrorsMax(37462),
        tcaProcessorErrorStatsMirroringInterSockErrorsAvg(37463),
        tcaProcessorErrorStatsMirroringInterSockErrorsRunning(37464),
        tcaEtherLossStatsSymbolDeltaMax(37465),
        tcaEtherLossStatsSymbolDeltaAvg(37466),
        tcaProcessorErrorStatsSparingErrorsMin(37471),
        tcaProcessorErrorStatsSparingErrorsMax(37472),
        tcaProcessorErrorStatsSparingErrorsAvg(37473),
        tcaProcessorErrorStatsSparingErrorsRunning(37474),
        tcaEtherLossStatsSqetestDeltaMax(37475),
        tcaEtherLossStatsSqetestDeltaAvg(37476),
        tcaProcessorErrorStatsSmiLinkCorrErrorsMin(37481),
        tcaProcessorErrorStatsSmiLinkCorrErrorsMax(37482),
        tcaProcessorErrorStatsSmiLinkCorrErrorsAvg(37483),
        tcaProcessorErrorStatsSmiLinkCorrErrorsRunning(37484),
        tcaEtherPauseStatsRecvPauseDelta(37485),
        tcaEtherPauseStatsRecvPauseDeltaMin(37486),
        tcaEtherPauseStatsRecvPauseDeltaMax(37487),
        tcaEtherPauseStatsRecvPauseDeltaAvg(37488),
        tcaProcessorErrorStatsSmiLinkUncorrErrorsMin(37491),
        tcaProcessorErrorStatsSmiLinkUncorrErrorsMax(37492),
        tcaProcessorErrorStatsSmiLinkUncorrErrorsAvg(37493),
        tcaProcessorErrorStatsSmiLinkUncorrErrorsRunning(37494),
        tcaEtherPauseStatsXmitPauseDelta(37495),
        tcaEtherPauseStatsXmitPauseDeltaMin(37496),
        tcaEtherPauseStatsXmitPauseDeltaMax(37497),
        tcaEtherPauseStatsXmitPauseDeltaAvg(37498),
        tcaEtherPauseStatsResetsDelta(37505),
        tcaEtherPauseStatsResetsDeltaMin(37506),
        tcaEtherPauseStatsResetsDeltaMax(37507),
        tcaEtherPauseStatsResetsDeltaAvg(37508),
        tcaEtherLossStatsExcessCollisionDelta(37532),
        tcaEtherLossStatsExcessCollisionDeltaMin(37533),
        tcaEtherLossStatsExcessCollisionDeltaMax(37534),
        tcaEtherLossStatsExcessCollisionDeltaAvg(37535),
        tcaEtherTxStatsUnicastPacketsDelta(37543),
        tcaEtherTxStatsUnicastPacketsDeltaMin(37544),
        tcaEtherTxStatsUnicastPacketsDeltaMax(37545),
        tcaEtherTxStatsUnicastPacketsDeltaAvg(37546),
        tcaEtherErrStatsDeferredTxDelta(37553),
        tcaEtherErrStatsDeferredTxDeltaMin(37554),
        tcaEtherErrStatsDeferredTxDeltaMax(37555),
        tcaEtherErrStatsDeferredTxDeltaAvg(37556),
        tcaComputeMbPowerStatsInputVoltage(37564),
        tcaComputeMbPowerStatsInputVoltageMin(37566),
        tcaComputeMbPowerStatsInputVoltageMax(37567),
        tcaComputeMbPowerStatsInputVoltageAvg(37568),
        tcaComputeMbPowerStatsInputCurrent(37572),
        tcaComputeMbPowerStatsInputCurrentMin(37574),
        tcaComputeMbPowerStatsInputCurrentMax(37575),
        tcaComputeMbPowerStatsInputCurrentAvg(37576),
        tcaComputeMbTempStatsFmTempSenRear(37580),
        tcaComputeMbTempStatsFmTempSenRearMin(37582),
        tcaComputeMbTempStatsFmTempSenRearMax(37583),
        tcaComputeMbTempStatsFmTempSenRearAvg(37584),
        tcaMemoryUnitEnvStatsTemperature(37600),
        tcaMemoryUnitEnvStatsTemperatureMin(37602),
        tcaMemoryUnitEnvStatsTemperatureMax(37603),
        tcaMemoryUnitEnvStatsTemperatureAvg(37604),
        tcaProcessorEnvStatsTemperature(37610),
        tcaProcessorEnvStatsTemperatureMin(37612),
        tcaProcessorEnvStatsTemperatureMax(37613),
        tcaProcessorEnvStatsTemperatureAvg(37614),
        tcaComputePcieFatalProtocolStatsFlowControlErrorsMin(37615),
        tcaComputePcieFatalProtocolStatsFlowControlErrorsMax(37616),
        tcaComputePcieFatalProtocolStatsFlowControlErrorsAvg(37617),
        tcaComputePcieFatalProtocolStatsFlowControlErrorsRunning(37618),
        tcaComputePcieFatalProtocolStatsDllpErrorsMin(37625),
        tcaComputePcieFatalProtocolStatsDllpErrorsMax(37626),
        tcaComputePcieFatalProtocolStatsDllpErrorsAvg(37627),
        tcaComputePcieFatalProtocolStatsDllpErrorsRunning(37628),
        tcaComputePcieFatalReceiveStatsUnsupportedRequestErrorsMin(37637),
        tcaComputePcieFatalReceiveStatsUnsupportedRequestErrorsMax(37638),
        tcaComputePcieFatalReceiveStatsUnsupportedRequestErrorsAvg(37639),
        tcaComputePcieFatalReceiveStatsUnsupportedRequestErrorsRunning(37640),
        tcaComputePcieFatalReceiveStatsErrFatalErrorsMin(37647),
        tcaComputePcieFatalReceiveStatsErrFatalErrorsMax(37648),
        tcaComputePcieFatalReceiveStatsErrFatalErrorsAvg(37649),
        tcaComputePcieFatalReceiveStatsErrFatalErrorsRunning(37650),
        tcaComputePcieFatalReceiveStatsErrNonFatalErrorsMin(37657),
        tcaComputePcieFatalReceiveStatsErrNonFatalErrorsMax(37658),
        tcaComputePcieFatalReceiveStatsErrNonFatalErrorsAvg(37659),
        tcaComputePcieFatalReceiveStatsErrNonFatalErrorsRunning(37660),
        tcaComputePcieFatalReceiveStatsBufferOverflowErrorsMin(37667),
        tcaComputePcieFatalReceiveStatsBufferOverflowErrorsMax(37668),
        tcaComputePcieFatalReceiveStatsBufferOverflowErrorsAvg(37669),
        tcaComputePcieFatalReceiveStatsBufferOverflowErrorsRunning(37670),
        tcaComputePcieFatalCompletionStatsUnexpectedErrorsMin(37679),
        tcaComputePcieFatalCompletionStatsUnexpectedErrorsMax(37680),
        tcaComputePcieFatalCompletionStatsUnexpectedErrorsAvg(37681),
        tcaComputePcieFatalCompletionStatsUnexpectedErrorsRunning(37682),
        tcaComputePcieFatalCompletionStatsTimeoutErrorsMin(37689),
        tcaComputePcieFatalCompletionStatsTimeoutErrorsMax(37690),
        tcaComputePcieFatalCompletionStatsTimeoutErrorsAvg(37691),
        tcaComputePcieFatalCompletionStatsTimeoutErrorsRunning(37692),
        tcaComputePcieFatalCompletionStatsAbortErrorsMin(37699),
        tcaComputePcieFatalCompletionStatsAbortErrorsMax(37700),
        tcaComputePcieFatalCompletionStatsAbortErrorsAvg(37701),
        tcaComputePcieFatalCompletionStatsAbortErrorsRunning(37702),
        tcaComputePcieFatalStatsSurpriseLinkDownErrorsMin(37711),
        tcaComputePcieFatalStatsSurpriseLinkDownErrorsMax(37712),
        tcaComputePcieFatalStatsSurpriseLinkDownErrorsAvg(37713),
        tcaComputePcieFatalStatsSurpriseLinkDownErrorsRunning(37714),
        tcaComputePcieFatalStatsPoisonedtlperrorsMin(37721),
        tcaComputePcieFatalStatsPoisonedtlperrorsMax(37722),
        tcaComputePcieFatalStatsPoisonedtlperrorsAvg(37723),
        tcaComputePcieFatalStatsPoisonedtlperrorsRunning(37724),
        tcaComputePcieFatalStatsAcsViolationErrorsMin(37731),
        tcaComputePcieFatalStatsAcsViolationErrorsMax(37732),
        tcaComputePcieFatalStatsAcsViolationErrorsAvg(37733),
        tcaComputePcieFatalStatsAcsViolationErrorsRunning(37734),
        tcaComputePcieFatalStatsMalformedtlperrorsMin(37741),
        tcaComputePcieFatalStatsMalformedtlperrorsMax(37742),
        tcaComputePcieFatalStatsMalformedtlperrorsAvg(37743),
        tcaComputePcieFatalStatsMalformedtlperrorsRunning(37744),
        tcaSwEnvStatsPsuCtrlrInlet1(37771),
        tcaSwEnvStatsPsuCtrlrInlet1Min(37773),
        tcaSwEnvStatsPsuCtrlrInlet1Max(37774),
        tcaSwEnvStatsPsuCtrlrInlet1Avg(37775),
        tcaSwEnvStatsPsuCtrlrInlet2(37779),
        tcaSwEnvStatsPsuCtrlrInlet2Min(37781),
        tcaSwEnvStatsPsuCtrlrInlet2Max(37782),
        tcaSwEnvStatsPsuCtrlrInlet2Avg(37783),
        tcaComputePcieFatalProtocolStatsDllpErrors(38022),
        tcaComputePcieFatalProtocolStatsFlowControlErrors(38032),
        tcaComputePcieFatalReceiveStatsUnsupportedRequestErrors(38044),
        tcaComputePcieFatalReceiveStatsErrFatalErrors(38054),
        tcaComputePcieFatalReceiveStatsErrNonFatalErrors(38064),
        tcaComputePcieFatalCompletionStatsUnexpectedErrors(38086),
        tcaComputePcieFatalCompletionStatsTimeoutErrors(38096),
        tcaComputePcieFatalCompletionStatsAbortErrors(38106),
        tcaComputePcieFatalStatsSurpriseLinkDownErrors(38128),
        tcaComputePcieFatalStatsPoisonedtlperrors(38138),
        tcaComputePcieFatalStatsAcsViolationErrors(38148),
        tcaComputePcieFatalStatsMalformedtlperrors(38158),
        tcaEquipmentIocardStatsTemp(38311),
        tcaEquipmentIocardStatsTempMin(38313),
        tcaEquipmentIocardStatsTempMax(38314),
        tcaEquipmentIocardStatsTempAvg(38315),
        tcaProcessorEnvStatsInputCurrent(38349),
        tcaProcessorEnvStatsInputCurrentMin(38351),
        tcaProcessorEnvStatsInputCurrentMax(38352),
        tcaProcessorEnvStatsInputCurrentAvg(38353),
        tcaMemoryArrayEnvStatsInputCurrent(38357),
        tcaMemoryArrayEnvStatsInputCurrentMin(38359),
        tcaMemoryArrayEnvStatsInputCurrentMax(38360),
        tcaMemoryArrayEnvStatsInputCurrentAvg(38361),
        tcaAdaptorEthPortBySizeLargeStatsNoBreakdownGreaterThan1518Delta(38470),
        tcaAdaptorEthPortBySizeLargeStatsNoBrkdnGreaterThan1518DeltaMin(38471),
        tcaAdaptorEthPortBySizeLargeStatsNoBrkdnGreaterThan1518DeltaMax(38472),
        tcaAdaptorEthPortBySizeLargeStatsNoBrkdnGreaterThan1518DeltaAvg(38473),
        tcaPowerGroupStatsPower(38557),
        tcaPowerGroupStatsPowerMin(38559),
        tcaPowerGroupStatsPowerMax(38560),
        tcaPowerGroupStatsPowerAvg(38561),
        tcaMemoryBufferUnitEnvStatsTemperature(38624),
        tcaMemoryBufferUnitEnvStatsTemperatureMin(38626),
        tcaMemoryBufferUnitEnvStatsTemperatureMax(38627),
        tcaMemoryBufferUnitEnvStatsTemperatureAvg(38628),
        tcaComputeIohubEnvStatsTemperature(38678),
        tcaComputeIohubEnvStatsTemperatureMin(38680),
        tcaComputeIohubEnvStatsTemperatureMax(38681),
        tcaComputeIohubEnvStatsTemperatureAvg(38682),
        tcaComputeMbTempStatsFmTempSenRearl(39082),
        tcaComputeMbTempStatsFmTempSenRearlmin(39084),
        tcaComputeMbTempStatsFmTempSenRearlmax(39085),
        tcaComputeMbTempStatsFmTempSenRearlavg(39086),
        tcaComputeMbTempStatsFmTempSenRearr(39090),
        tcaComputeMbTempStatsFmTempSenRearrmin(39092),
        tcaComputeMbTempStatsFmTempSenRearrmax(39093),
        tcaComputeMbTempStatsFmTempSenRearravg(39094),
        tcaEquipmentFexEnvStatsOutlet1(39107),
        tcaEquipmentFexEnvStatsOutlet1Min(39109),
        tcaEquipmentFexEnvStatsOutlet1Max(39110),
        tcaEquipmentFexEnvStatsOutlet1Avg(39111),
        tcaEquipmentFexEnvStatsOutlet2(39115),
        tcaEquipmentFexEnvStatsOutlet2Min(39117),
        tcaEquipmentFexEnvStatsOutlet2Max(39118),
        tcaEquipmentFexEnvStatsOutlet2Avg(39119),
        tcaEquipmentFexEnvStatsInlet(39123),
        tcaEquipmentFexEnvStatsInletMin(39125),
        tcaEquipmentFexEnvStatsInletMax(39126),
        tcaEquipmentFexEnvStatsInletAvg(39127),
        tcaEquipmentFexEnvStatsInlet1(39131),
        tcaEquipmentFexEnvStatsInlet1Min(39133),
        tcaEquipmentFexEnvStatsInlet1Max(39134),
        tcaEquipmentFexEnvStatsInlet1Avg(39135),
        tcaEquipmentFexEnvStatsDie1(39139),
        tcaEquipmentFexEnvStatsDie1Min(39141),
        tcaEquipmentFexEnvStatsDie1Max(39142),
        tcaEquipmentFexEnvStatsDie1Avg(39143),
        tcaEquipmentFexPowerSummaryTotalPower(39166),
        tcaEquipmentFexPowerSummaryTotalPowerMin(39168),
        tcaEquipmentFexPowerSummaryTotalPowerMax(39169),
        tcaEquipmentFexPowerSummaryTotalPowerAvg(39170),
        tcaEquipmentFexPowerSummaryReservedPower(39174),
        tcaEquipmentFexPowerSummaryReservedPowerMin(39176),
        tcaEquipmentFexPowerSummaryReservedPowerMax(39177),
        tcaEquipmentFexPowerSummaryReservedPowerAvg(39178),
        tcaEquipmentFexPowerSummaryModulePower(39182),
        tcaEquipmentFexPowerSummaryModulePowerMin(39184),
        tcaEquipmentFexPowerSummaryModulePowerMax(39185),
        tcaEquipmentFexPowerSummaryModulePowerAvg(39186),
        tcaEquipmentFexPowerSummaryAvailablePower(39190),
        tcaEquipmentFexPowerSummaryAvailablePowerMin(39192),
        tcaEquipmentFexPowerSummaryAvailablePowerMax(39193),
        tcaEquipmentFexPowerSummaryAvailablePowerAvg(39194),
        tcaEquipmentFexPsuInputStatsCurrent(39200),
        tcaEquipmentFexPsuInputStatsCurrentMin(39202),
        tcaEquipmentFexPsuInputStatsCurrentMax(39203),
        tcaEquipmentFexPsuInputStatsCurrentAvg(39204),
        tcaEquipmentFexPsuInputStatsVoltage(39208),
        tcaEquipmentFexPsuInputStatsVoltageMin(39210),
        tcaEquipmentFexPsuInputStatsVoltageMax(39211),
        tcaEquipmentFexPsuInputStatsVoltageAvg(39212),
        tcaEquipmentFexPsuInputStatsPower(39216),
        tcaEquipmentFexPsuInputStatsPowerMin(39218),
        tcaEquipmentFexPsuInputStatsPowerMax(39219),
        tcaEquipmentFexPsuInputStatsPowerAvg(39220),
        tcaEquipmentRackUnitPsuStatsAmbientTemp(39227),
        tcaEquipmentRackUnitPsuStatsAmbientTempMin(39229),
        tcaEquipmentRackUnitPsuStatsAmbientTempMax(39230),
        tcaEquipmentRackUnitPsuStatsAmbientTempAvg(39231),
        tcaEquipmentRackUnitPsuStatsOutputCurrent(39235),
        tcaEquipmentRackUnitPsuStatsOutputCurrentMin(39237),
        tcaEquipmentRackUnitPsuStatsOutputCurrentMax(39238),
        tcaEquipmentRackUnitPsuStatsOutputCurrentAvg(39239),
        tcaEquipmentRackUnitPsuStatsOutputPower(39243),
        tcaEquipmentRackUnitPsuStatsOutputPowerMin(39245),
        tcaEquipmentRackUnitPsuStatsOutputPowerMax(39246),
        tcaEquipmentRackUnitPsuStatsOutputPowerAvg(39247),
        tcaEquipmentRackUnitPsuStatsInputPower(39251),
        tcaEquipmentRackUnitPsuStatsInputPowerMin(39253),
        tcaEquipmentRackUnitPsuStatsInputPowerMax(39254),
        tcaEquipmentRackUnitPsuStatsInputPowerAvg(39255),
        tcaEquipmentRackUnitPsuStatsOutputVoltage(39259),
        tcaEquipmentRackUnitPsuStatsOutputVoltageMin(39261),
        tcaEquipmentRackUnitPsuStatsOutputVoltageMax(39262),
        tcaEquipmentRackUnitPsuStatsOutputVoltageAvg(39263),
        tcaEquipmentRackUnitPsuStatsInputVoltage(39267),
        tcaEquipmentRackUnitPsuStatsInputVoltageMin(39269),
        tcaEquipmentRackUnitPsuStatsInputVoltageMax(39270),
        tcaEquipmentRackUnitPsuStatsInputVoltageAvg(39271),
        tcaAdaptorHbavnicStatsPacketsTxDelta(39392),
        tcaAdaptorHbavnicStatsPacketsTxDeltaMin(39393),
        tcaAdaptorHbavnicStatsPacketsTxDeltaMax(39394),
        tcaAdaptorHbavnicStatsPacketsTxDeltaAvg(39395),
        tcaAdaptorHbavnicStatsPacketsRxDelta(39402),
        tcaAdaptorHbavnicStatsPacketsRxDeltaMin(39403),
        tcaAdaptorHbavnicStatsPacketsRxDeltaMax(39404),
        tcaAdaptorHbavnicStatsPacketsRxDeltaAvg(39405),
        tcaAdaptorHbavnicStatsBytesTxDelta(39412),
        tcaAdaptorHbavnicStatsBytesTxDeltaMin(39413),
        tcaAdaptorHbavnicStatsBytesTxDeltaMax(39414),
        tcaAdaptorHbavnicStatsBytesTxDeltaAvg(39415),
        tcaAdaptorHbavnicStatsBytesRxDelta(39422),
        tcaAdaptorHbavnicStatsBytesRxDeltaMin(39423),
        tcaAdaptorHbavnicStatsBytesRxDeltaMax(39424),
        tcaAdaptorHbavnicStatsBytesRxDeltaAvg(39425),
        tcaAdaptorHbavnicStatsErrorsTxDelta(39432),
        tcaAdaptorHbavnicStatsErrorsTxDeltaMin(39433),
        tcaAdaptorHbavnicStatsErrorsTxDeltaMax(39434),
        tcaAdaptorHbavnicStatsErrorsTxDeltaAvg(39435),
        tcaAdaptorHbavnicStatsErrorsRxDelta(39442),
        tcaAdaptorHbavnicStatsErrorsRxDeltaMin(39443),
        tcaAdaptorHbavnicStatsErrorsRxDeltaMax(39444),
        tcaAdaptorHbavnicStatsErrorsRxDeltaAvg(39445),
        tcaAdaptorHbavnicStatsDroppedTxDelta(39452),
        tcaAdaptorHbavnicStatsDroppedTxDeltaMin(39453),
        tcaAdaptorHbavnicStatsDroppedTxDeltaMax(39454),
        tcaAdaptorHbavnicStatsDroppedTxDeltaAvg(39455),
        tcaAdaptorHbavnicStatsDroppedRxDelta(39462),
        tcaAdaptorHbavnicStatsDroppedRxDeltaMin(39463),
        tcaAdaptorHbavnicStatsDroppedRxDeltaMax(39464),
        tcaAdaptorHbavnicStatsDroppedRxDeltaAvg(39465),
        tcaAdaptorNicvnicStatsPacketsTxDelta(39474),
        tcaAdaptorNicvnicStatsPacketsTxDeltaMin(39475),
        tcaAdaptorNicvnicStatsPacketsTxDeltaMax(39476),
        tcaAdaptorNicvnicStatsPacketsTxDeltaAvg(39477),
        tcaAdaptorNicvnicStatsPacketsRxDelta(39484),
        tcaAdaptorNicvnicStatsPacketsRxDeltaMin(39485),
        tcaAdaptorNicvnicStatsPacketsRxDeltaMax(39486),
        tcaAdaptorNicvnicStatsPacketsRxDeltaAvg(39487),
        tcaAdaptorNicvnicStatsBytesTxDelta(39494),
        tcaAdaptorNicvnicStatsBytesTxDeltaMin(39495),
        tcaAdaptorNicvnicStatsBytesTxDeltaMax(39496),
        tcaAdaptorNicvnicStatsBytesTxDeltaAvg(39497),
        tcaAdaptorNicvnicStatsBytesRxDelta(39504),
        tcaAdaptorNicvnicStatsBytesRxDeltaMin(39505),
        tcaAdaptorNicvnicStatsBytesRxDeltaMax(39506),
        tcaAdaptorNicvnicStatsBytesRxDeltaAvg(39507),
        tcaAdaptorNicvnicStatsErrorsTxDelta(39514),
        tcaAdaptorNicvnicStatsErrorsTxDeltaMin(39515),
        tcaAdaptorNicvnicStatsErrorsTxDeltaMax(39516),
        tcaAdaptorNicvnicStatsErrorsTxDeltaAvg(39517),
        tcaAdaptorNicvnicStatsErrorsRxDelta(39524),
        tcaAdaptorNicvnicStatsErrorsRxDeltaMin(39525),
        tcaAdaptorNicvnicStatsErrorsRxDeltaMax(39526),
        tcaAdaptorNicvnicStatsErrorsRxDeltaAvg(39527),
        tcaAdaptorNicvnicStatsDroppedTxDelta(39534),
        tcaAdaptorNicvnicStatsDroppedTxDeltaMin(39535),
        tcaAdaptorNicvnicStatsDroppedTxDeltaMax(39536),
        tcaAdaptorNicvnicStatsDroppedTxDeltaAvg(39537),
        tcaAdaptorNicvnicStatsDroppedRxDelta(39544),
        tcaAdaptorNicvnicStatsDroppedRxDeltaMin(39545),
        tcaAdaptorNicvnicStatsDroppedRxDeltaMax(39546),
        tcaAdaptorNicvnicStatsDroppedRxDeltaAvg(39547),
        tcaComputePcieFatalReceiveStatsBufferOverflowErrors(39583),
        tcaProcessorErrorStatsMirroringIntraSockErrors(39649),
        tcaProcessorErrorStatsMirroringInterSockErrors(39658),
        tcaProcessorErrorStatsSparingErrors(39667),
        tcaProcessorErrorStatsSmiLinkCorrErrors(39676),
        tcaProcessorErrorStatsSmiLinkUncorrErrors(39685),
        tcaMemoryErrorStatsEccMultibitErrors(39702),
        tcaMemoryErrorStatsEccSinglebitErrors(39711),
        tcaMemoryErrorStatsAddressParityErrors(39720),
        tcaMemoryErrorStatsMismatchErrors(39729),
        tcaEquipmentRackUnitFanStatsSpeed(39794),
        tcaEquipmentRackUnitFanStatsSpeedMin(39796),
        tcaEquipmentRackUnitFanStatsSpeedMax(39797),
        tcaEquipmentRackUnitFanStatsSpeedAvg(39798),
        tcaComputeRackUnitMbTempStatsFrontTemp(40092),
        tcaComputeRackUnitMbTempStatsFrontTempMin(40094),
        tcaComputeRackUnitMbTempStatsFrontTempMax(40095),
        tcaComputeRackUnitMbTempStatsFrontTempAvg(40096),
        tcaComputeRackUnitMbTempStatsRearTemp(40100),
        tcaComputeRackUnitMbTempStatsRearTempMin(40102),
        tcaComputeRackUnitMbTempStatsRearTempMax(40103),
        tcaComputeRackUnitMbTempStatsRearTempAvg(40104),
        tcaComputeRackUnitMbTempStatsAmbientTemp(40108),
        tcaComputeRackUnitMbTempStatsAmbientTempMin(40110),
        tcaComputeRackUnitMbTempStatsAmbientTempMax(40111),
        tcaComputeRackUnitMbTempStatsAmbientTempAvg(40112),
        tcaComputeRackUnitMbTempStatsIoh1Temp(40116),
        tcaComputeRackUnitMbTempStatsIoh1TempMin(40118),
        tcaComputeRackUnitMbTempStatsIoh1TempMax(40119),
        tcaComputeRackUnitMbTempStatsIoh1TempAvg(40120),
        tcaComputeRackUnitMbTempStatsIoh2Temp(40124),
        tcaComputeRackUnitMbTempStatsIoh2TempMin(40126),
        tcaComputeRackUnitMbTempStatsIoh2TempMax(40127),
        tcaComputeRackUnitMbTempStatsIoh2TempAvg(40128),
        tcaEquipmentPsuOutputStatsCurrent(40441),
        tcaEquipmentPsuOutputStatsCurrentMin(40443),
        tcaEquipmentPsuOutputStatsCurrentMax(40444),
        tcaEquipmentPsuOutputStatsCurrentAvg(40445),
        tcaEquipmentPsuOutputStatsVoltage(40449),
        tcaEquipmentPsuOutputStatsVoltageMin(40451),
        tcaEquipmentPsuOutputStatsVoltageMax(40452),
        tcaEquipmentPsuOutputStatsVoltageAvg(40453),
        tcaEquipmentPsuOutputStatsPower(40457),
        tcaEquipmentPsuOutputStatsPowerMin(40459),
        tcaEquipmentPsuOutputStatsPowerMax(40460),
        tcaEquipmentPsuOutputStatsPowerAvg(40461),
        tcaEquipmentNetworkElementFanStatsSpeed(40583),
        tcaEquipmentNetworkElementFanStatsSpeedMin(40585),
        tcaEquipmentNetworkElementFanStatsSpeedMax(40586),
        tcaEquipmentNetworkElementFanStatsSpeedAvg(40587),
        tcaEquipmentNetworkElementFanStatsDrivePercentage(40591),
        tcaEquipmentNetworkElementFanStatsDrivePercentageMin(40593),
        tcaEquipmentNetworkElementFanStatsDrivePercentageMax(40594),
        tcaEquipmentNetworkElementFanStatsDrivePercentageAvg(40595),
        tcaSwCardEnvStatsSlotOutlet1(41016),
        tcaSwCardEnvStatsSlotOutlet1Min(41018),
        tcaSwCardEnvStatsSlotOutlet1Max(41019),
        tcaSwCardEnvStatsSlotOutlet1Avg(41020),
        tcaSwCardEnvStatsSlotOutlet2(41024),
        tcaSwCardEnvStatsSlotOutlet2Min(41026),
        tcaSwCardEnvStatsSlotOutlet2Max(41027),
        tcaSwCardEnvStatsSlotOutlet2Avg(41028),
        tcaSwCardEnvStatsSlotOutlet3(41032),
        tcaSwCardEnvStatsSlotOutlet3Min(41034),
        tcaSwCardEnvStatsSlotOutlet3Max(41035),
        tcaSwCardEnvStatsSlotOutlet3Avg(41036),
        tcaEtherFcoeInterfaceStatsPacketsTxDelta(41049),
        tcaEtherFcoeInterfaceStatsPacketsTxDeltaMin(41050),
        tcaEtherFcoeInterfaceStatsPacketsTxDeltaMax(41051),
        tcaEtherFcoeInterfaceStatsPacketsTxDeltaAvg(41052),
        tcaEtherFcoeInterfaceStatsPacketsRxDelta(41059),
        tcaEtherFcoeInterfaceStatsPacketsRxDeltaMin(41060),
        tcaEtherFcoeInterfaceStatsPacketsRxDeltaMax(41061),
        tcaEtherFcoeInterfaceStatsPacketsRxDeltaAvg(41062),
        tcaEtherFcoeInterfaceStatsBytesTxDelta(41069),
        tcaEtherFcoeInterfaceStatsBytesTxDeltaMin(41070),
        tcaEtherFcoeInterfaceStatsBytesTxDeltaMax(41071),
        tcaEtherFcoeInterfaceStatsBytesTxDeltaAvg(41072),
        tcaEtherFcoeInterfaceStatsBytesRxDelta(41079),
        tcaEtherFcoeInterfaceStatsBytesRxDeltaMin(41080),
        tcaEtherFcoeInterfaceStatsBytesRxDeltaMax(41081),
        tcaEtherFcoeInterfaceStatsBytesRxDeltaAvg(41082),
        tcaEtherFcoeInterfaceStatsErrorsTxDelta(41089),
        tcaEtherFcoeInterfaceStatsErrorsTxDeltaMin(41090),
        tcaEtherFcoeInterfaceStatsErrorsTxDeltaMax(41091),
        tcaEtherFcoeInterfaceStatsErrorsTxDeltaAvg(41092),
        tcaEtherFcoeInterfaceStatsErrorsRxDelta(41099),
        tcaEtherFcoeInterfaceStatsErrorsRxDeltaMin(41100),
        tcaEtherFcoeInterfaceStatsErrorsRxDeltaMax(41101),
        tcaEtherFcoeInterfaceStatsErrorsRxDeltaAvg(41102),
        tcaEtherFcoeInterfaceStatsDroppedTxDelta(41109),
        tcaEtherFcoeInterfaceStatsDroppedTxDeltaMin(41110),
        tcaEtherFcoeInterfaceStatsDroppedTxDeltaMax(41111),
        tcaEtherFcoeInterfaceStatsDroppedTxDeltaAvg(41112),
        tcaEtherFcoeInterfaceStatsDroppedRxDelta(41119),
        tcaEtherFcoeInterfaceStatsDroppedRxDeltaMin(41120),
        tcaEtherFcoeInterfaceStatsDroppedRxDeltaMax(41121),
        tcaEtherFcoeInterfaceStatsDroppedRxDeltaAvg(41122),
        tcaEtherNiErrStatsFrameTxDelta(43132),
        tcaEtherNiErrStatsFrameTxDeltaMin(43133),
        tcaEtherNiErrStatsFrameTxDeltaMax(43134),
        tcaEtherNiErrStatsFrameTxDeltaAvg(43135),
        tcaEtherNiErrStatsTooLongDelta(43142),
        tcaEtherNiErrStatsTooLongDeltaMin(43143),
        tcaEtherNiErrStatsTooLongDeltaMax(43144),
        tcaEtherNiErrStatsTooLongDeltaAvg(43145),
        tcaEtherNiErrStatsTooShortDelta(43152),
        tcaEtherNiErrStatsTooShortDeltaMin(43153),
        tcaEtherNiErrStatsTooShortDeltaMax(43154),
        tcaEtherNiErrStatsTooShortDeltaAvg(43155),
        tcaEtherNiErrStatsCrcDelta(43162),
        tcaEtherNiErrStatsCrcDeltaMin(43163),
        tcaEtherNiErrStatsCrcDeltaMax(43164),
        tcaEtherNiErrStatsCrcDeltaAvg(43165),
        tcaEtherNiErrStatsInRangeDelta(43172),
        tcaEtherNiErrStatsInRangeDeltaMin(43173),
        tcaEtherNiErrStatsInRangeDeltaMax(43174),
        tcaEtherNiErrStatsInRangeDeltaAvg(43175),
        tcaStorageHddMotherBoardTempStatsRightInletTemp(43209),
        tcaStorageHddMotherBoardTempStatsRightInletTempMin(43211),
        tcaStorageHddMotherBoardTempStatsRightInletTempMax(43212),
        tcaStorageHddMotherBoardTempStatsRightInletTempAvg(43213),
        tcaStorageHddMotherBoardTempStatsLeftInletTemp(43217),
        tcaStorageHddMotherBoardTempStatsLeftInletTempMin(43219),
        tcaStorageHddMotherBoardTempStatsLeftInletTempMax(43220),
        tcaStorageHddMotherBoardTempStatsLeftInletTempAvg(43221),
        tcaStorageHddMotherBoardTempStatsRightOutletTemp(43225),
        tcaStorageHddMotherBoardTempStatsRightOutletTempMin(43227),
        tcaStorageHddMotherBoardTempStatsRightOutletTempMax(43228),
        tcaStorageHddMotherBoardTempStatsRightOutletTempAvg(43229),
        tcaStorageHddMotherBoardTempStatsLeftOutletTemp(43233),
        tcaStorageHddMotherBoardTempStatsLeftOutletTempMin(43235),
        tcaStorageHddMotherBoardTempStatsLeftOutletTempMax(43236),
        tcaStorageHddMotherBoardTempStatsLeftOutletTempAvg(43237),
        tcaStorageCtrlStorageStatsCpuLoad(43549),
        tcaStorageCtrlStorageStatsCpuLoadMin(43551),
        tcaStorageCtrlStorageStatsCpuLoadMax(43552),
        tcaStorageCtrlStorageStatsCpuLoadAvg(43553),
        tcaStorageCtrlStorageStatsMemoryUsage(43557),
        tcaStorageCtrlStorageStatsMemoryUsageMin(43559),
        tcaStorageCtrlStorageStatsMemoryUsageMax(43560),
        tcaStorageCtrlStorageStatsMemoryUsageAvg(43561),
        tcaStorageStorageStatsIops(43567),
        tcaStorageStorageStatsIopsMin(43569),
        tcaStorageStorageStatsIopsMax(43570),
        tcaStorageStorageStatsIopsAvg(43571),
        tcaStorageStorageStatsLatency(43575),
        tcaStorageStorageStatsLatencyMin(43577),
        tcaStorageStorageStatsLatencyMax(43578),
        tcaStorageStorageStatsLatencyAvg(43579),
        tcaStorageStorageStatsMbps(43583),
        tcaStorageStorageStatsMbpsMin(43585),
        tcaStorageStorageStatsMbpsMax(43586),
        tcaStorageStorageStatsMbpsAvg(43587),
        tcaStorageStorageStatsReadIops(43591),
        tcaStorageStorageStatsReadIopsMin(43593),
        tcaStorageStorageStatsReadIopsMax(43594),
        tcaStorageStorageStatsReadIopsAvg(43595),
        tcaStorageStorageStatsWriteIops(43599),
        tcaStorageStorageStatsWriteIopsMin(43601),
        tcaStorageStorageStatsWriteIopsMax(43602),
        tcaStorageStorageStatsWriteIopsAvg(43603),
        tcaStorageStorageStatsReadMbps(43607),
        tcaStorageStorageStatsReadMbpsMin(43609),
        tcaStorageStorageStatsReadMbpsMax(43610),
        tcaStorageStorageStatsReadMbpsAvg(43611),
        tcaStorageStorageStatsWriteMbps(43615),
        tcaStorageStorageStatsWriteMbpsMin(43617),
        tcaStorageStorageStatsWriteMbpsMax(43618),
        tcaStorageStorageStatsWriteMbpsAvg(43619),
        tcaEquipmentSiocTempStatsRearTemp(43714),
        tcaEquipmentSiocTempStatsRearTempMin(43716),
        tcaEquipmentSiocTempStatsRearTempMax(43717),
        tcaEquipmentSiocTempStatsRearTempAvg(43718),
        tcaEquipmentSiocTempStatsFrontTemp(43722),
        tcaEquipmentSiocTempStatsFrontTempMin(43724),
        tcaEquipmentSiocTempStatsFrontTempMax(43725),
        tcaEquipmentSiocTempStatsFrontTempAvg(43726),
        tcaEquipmentSiocTempStatsMidTemp(43730),
        tcaEquipmentSiocTempStatsMidTempMin(43732),
        tcaEquipmentSiocTempStatsMidTempMax(43733),
        tcaEquipmentSiocTempStatsMidTempAvg(43734),
        tcaEquipmentSiocTempStatsCmcTemp(43738),
        tcaEquipmentSiocTempStatsCmcTempMin(43740),
        tcaEquipmentSiocTempStatsCmcTempMax(43741),
        tcaEquipmentSiocTempStatsCmcTempAvg(43742),
        tcaEquipmentSiocTempStatsVicTemp(43746),
        tcaEquipmentSiocTempStatsVicTempMin(43748),
        tcaEquipmentSiocTempStatsVicTempMax(43749),
        tcaEquipmentSiocTempStatsVicTempAvg(43750),
        tcaMemoryNvDimmEnvStatsTemperature(43935),
        tcaMemoryNvDimmEnvStatsTemperatureMin(43937),
        tcaMemoryNvDimmEnvStatsTemperatureMax(43938),
        tcaMemoryNvDimmEnvStatsTemperatureAvg(43939),
        tcaMemoryNvDimmEnvStatsVoltage(43943),
        tcaMemoryNvDimmEnvStatsVoltageMin(43945),
        tcaMemoryNvDimmEnvStatsVoltageMax(43946),
        tcaMemoryNvDimmEnvStatsVoltageAvg(43947),
        tcaComputeStorageBladeMbTempStatsFrontTemp(44035),
        tcaComputeStorageBladeMbTempStatsFrontTempMin(44037),
        tcaComputeStorageBladeMbTempStatsFrontTempMax(44038),
        tcaComputeStorageBladeMbTempStatsFrontTempAvg(44039),
        tcaComputeStorageBladeMbTempStatsLeftRearTemp(44043),
        tcaComputeStorageBladeMbTempStatsLeftRearTempMin(44045),
        tcaComputeStorageBladeMbTempStatsLeftRearTempMax(44046),
        tcaComputeStorageBladeMbTempStatsLeftRearTempAvg(44047),
        tcaComputeStorageBladeMbTempStatsRightRearTemp(44051),
        tcaComputeStorageBladeMbTempStatsRightRearTempMin(44053),
        tcaComputeStorageBladeMbTempStatsRightRearTempMax(44054),
        tcaComputeStorageBladeMbTempStatsRightRearTempAvg(44055),
        tcaEquipmentIocardStatsProcTemp(44131),
        tcaEquipmentIocardStatsProcTempMin(44133),
        tcaEquipmentIocardStatsProcTempMax(44134),
        tcaEquipmentIocardStatsProcTempAvg(44135),
        tcaEquipmentIocardStatsDimmTemp(44139),
        tcaEquipmentIocardStatsDimmTempMin(44141),
        tcaEquipmentIocardStatsDimmTempMax(44142),
        tcaEquipmentIocardStatsDimmTempAvg(44143),
        tcaStorageDiskEnvStatsTemperature(44217),
        tcaStorageDiskEnvStatsTemperatureMin(44219),
        tcaStorageDiskEnvStatsTemperatureMax(44220),
        tcaStorageDiskEnvStatsTemperatureAvg(44221),
        tcaStorageDiskEnvStatsWearPercentage(44225),
        tcaStorageDiskEnvStatsWearPercentageMin(44227),
        tcaStorageDiskEnvStatsWearPercentageMax(44228),
        tcaStorageDiskEnvStatsWearPercentageAvg(44229),
        tcaEquipmentPsuStatsInputPower(44564),
        tcaEquipmentPsuStatsInputPowerMin(44566),
        tcaEquipmentPsuStatsInputPowerMax(44567),
        tcaEquipmentPsuStatsInputPowerAvg(44568),
        tcaEquipmentChassisStatsChassisI2cerrors(44728),
        tcaEquipmentChassisStatsChassisI2cerrorsDelta(44730),
        tcaEquipmentChassisStatsChassisI2cerrorsDeltaMin(44731),
        tcaEquipmentChassisStatsChassisI2cerrorsDeltaMax(44732),
        tcaEquipmentChassisStatsChassisI2cerrorsDeltaAvg(44733),
        tcaEquipmentIocardStatsIomI2cerrors(44738),
        tcaEquipmentIocardStatsIomI2cerrorsDelta(44740),
        tcaEquipmentIocardStatsIomI2cerrorsDeltaMin(44741),
        tcaEquipmentIocardStatsIomI2cerrorsDeltaMax(44742),
        tcaEquipmentIocardStatsIomI2cerrorsDeltaAvg(44743),
        tcaEquipmentPsuStatsPsuI2cerrors(44748),
        tcaEquipmentPsuStatsPsuI2cerrorsDelta(44750),
        tcaEquipmentPsuStatsPsuI2cerrorsDeltaMin(44751),
        tcaEquipmentPsuStatsPsuI2cerrorsDeltaMax(44752),
        tcaEquipmentPsuStatsPsuI2cerrorsDeltaAvg(44753),
        tcaEquipmentFanStatsFanI2cerrorsDelta(44760),
        tcaEquipmentFanStatsFanI2cerrorsDeltaMin(44761),
        tcaEquipmentFanStatsFanI2cerrorsDeltaMax(44762),
        tcaEquipmentFanStatsFanI2cerrorsDeltaAvg(44763),
        tcaSwEnvStatsDonner(45019),
        tcaSwEnvStatsDonnerMin(45021),
        tcaSwEnvStatsDonnerMax(45022),
        tcaSwEnvStatsDonnerAvg(45023),
        tcaSwEnvStatsTd2(45027),
        tcaSwEnvStatsTd2Min(45029),
        tcaSwEnvStatsTd2Max(45030),
        tcaSwEnvStatsTd2Avg(45031),
        tcaSwEnvStatsTiburon(45035),
        tcaSwEnvStatsTiburonMin(45037),
        tcaSwEnvStatsTiburonMax(45038),
        tcaSwEnvStatsTiburonAvg(45039),
        tcaSwSystemStatsKernelMemTotal(45043),
        tcaSwSystemStatsKernelMemTotalMin(45045),
        tcaSwSystemStatsKernelMemTotalMax(45046),
        tcaSwSystemStatsKernelMemTotalAvg(45047),
        tcaSwSystemStatsKernelMemFree(45051),
        tcaSwSystemStatsKernelMemFreeMin(45053),
        tcaSwSystemStatsKernelMemFreeMax(45054),
        tcaSwSystemStatsKernelMemFreeAvg(45055),
        tcaEquipmentFexSystemStatsMemAvailable(45154),
        tcaEquipmentFexSystemStatsMemAvailableMin(45156),
        tcaEquipmentFexSystemStatsMemAvailableMax(45157),
        tcaEquipmentFexSystemStatsMemAvailableAvg(45158),
        tcaEquipmentFexSystemStatsMemCached(45162),
        tcaEquipmentFexSystemStatsMemCachedMin(45164),
        tcaEquipmentFexSystemStatsMemCachedMax(45165),
        tcaEquipmentFexSystemStatsMemCachedAvg(45166),
        tcaEquipmentFexSystemStatsLoad(45170),
        tcaEquipmentFexSystemStatsLoadMin(45172),
        tcaEquipmentFexSystemStatsLoadMax(45173),
        tcaEquipmentFexSystemStatsLoadAvg(45174),
        tcaEquipmentFexSystemStatsKernelMemTotal(45178),
        tcaEquipmentFexSystemStatsKernelMemTotalMin(45180),
        tcaEquipmentFexSystemStatsKernelMemTotalMax(45181),
        tcaEquipmentFexSystemStatsKernelMemTotalAvg(45182),
        tcaEquipmentFexSystemStatsKernelMemFree(45186),
        tcaEquipmentFexSystemStatsKernelMemFreeMin(45188),
        tcaEquipmentFexSystemStatsKernelMemFreeMax(45189),
        tcaEquipmentFexSystemStatsKernelMemFreeAvg(45190),
        tcaSwSystemStatsCorrectableParityError(45211),
        tcaSwSystemStatsCorrectableParityErrorMin(45213),
        tcaSwSystemStatsCorrectableParityErrorMax(45214),
        tcaSwSystemStatsCorrectableParityErrorAvg(45215),
        tcaEquipmentChassisStatsChassisI2cerrorsMin(45266),
        tcaEquipmentChassisStatsChassisI2cerrorsMax(45267),
        tcaEquipmentChassisStatsChassisI2cerrorsAvg(45268),
        tcaEquipmentIocardStatsIomI2cerrorsMin(45272),
        tcaEquipmentIocardStatsIomI2cerrorsMax(45273),
        tcaEquipmentIocardStatsIomI2cerrorsAvg(45274),
        tcaEquipmentPsuStatsPsuI2cerrorsMin(45278),
        tcaEquipmentPsuStatsPsuI2cerrorsMax(45279),
        tcaEquipmentPsuStatsPsuI2cerrorsAvg(45280),
        tcaEquipmentFanModuleStatsFanModuleI2cerrors(45284),
        tcaEquipmentFanModuleStatsFanModuleI2cerrorsMin(45286),
        tcaEquipmentFanModuleStatsFanModuleI2cerrorsMax(45287),
        tcaEquipmentFanModuleStatsFanModuleI2cerrorsAvg(45288),
        tcaStorageNvmeStatsTemperature(45647),
        tcaStorageNvmeStatsTemperatureMin(45649),
        tcaStorageNvmeStatsTemperatureMax(45650),
        tcaStorageNvmeStatsTemperatureAvg(45651),
        tcaStorageNvmeStatsDriveLifeUsedPercentage(45655),
        tcaStorageNvmeStatsDriveLifeUsedPercentageMin(45657),
        tcaStorageNvmeStatsDriveLifeUsedPercentageMax(45658),
        tcaStorageNvmeStatsDriveLifeUsedPercentageAvg(45659),
        tcaStorageSsdHealthStatsPowerOnHours(46020),
        tcaStorageSsdHealthStatsPowerOnHoursMin(46022),
        tcaStorageSsdHealthStatsPowerOnHoursMax(46023),
        tcaStorageSsdHealthStatsPowerOnHoursAvg(46024),
        tcaStorageSsdHealthStatsWearStatusInDays(46028),
        tcaStorageSsdHealthStatsWearStatusInDaysMin(46030),
        tcaStorageSsdHealthStatsWearStatusInDaysMax(46031),
        tcaStorageSsdHealthStatsWearStatusInDaysAvg(46032),
        tcaStorageSsdHealthStatsPowerCycleCount(46036),
        tcaStorageSsdHealthStatsPowerCycleCountMin(46038),
        tcaStorageSsdHealthStatsPowerCycleCountMax(46039),
        tcaStorageSsdHealthStatsPowerCycleCountAvg(46040),
        tcaStorageSsdHealthStatsPercentageLifeLeft(46044),
        tcaStorageSsdHealthStatsPercentageLifeLeftMin(46046),
        tcaStorageSsdHealthStatsPercentageLifeLeftMax(46047),
        tcaStorageSsdHealthStatsPercentageLifeLeftAvg(46048),
        tcaMemoryErrorStatsDramWriteDataCorrectablecrcerrors(46262),
        tcaMemoryErrorStatsDramWriteDataUnCorrectablecrcerrors(46273),
        tcaMemoryErrorStatsAddressParityErrorsCorrectable(46284),
        tcaMemoryErrorStatsAddressParityErrorsUnCorrectable(46295),
        tcaProcessorErrorStatsCorrectableLinkcrcerrors(46306),
        tcaProcessorErrorStatsUncorrectableLinkcrcerrors(46317),
        tcaStorageNvmeStatsLifeLeftInDays(46476),
        tcaStorageNvmeStatsLifeLeftInDaysMin(46478),
        tcaStorageNvmeStatsLifeLeftInDaysMax(46479),
        tcaStorageNvmeStatsLifeLeftInDaysAvg(46480),
        tcaProcessorExecStatsLoadStoreUnitCorrectableErrors(46643),
        tcaProcessorExecStatsLoadStoreUnitUncorrectableErrors(46654),
        tcaProcessorExecStatsInstructionFetchUnitCorrectableErrors(46665),
        tcaProcessorExecStatsInstructionFetchUnitUncorrectableErrors(46676),
        tcaProcessorExecStatsDecodeUnitCorrectableErrors(46687),
        tcaProcessorExecStatsDecodeUnitUncorrectableErrors(46698),
        tcaProcessorExecStatsExecutionUnitCorrectableErrors(46709),
        tcaProcessorExecStatsExecutionUnitUncorrectableErrors(46720),
        tcaProcessorCacheMemStatsL2CacheUnitCorrectableErrors(46732),
        tcaProcessorCacheMemStatsL2CacheUnitUncorrectableErrors(46743),
        tcaProcessorCacheMemStatsL3CacheUnitCorrectableErrors(46754),
        tcaProcessorCacheMemStatsL3CacheUnitUncorrectableErrors(46765),
        tcaProcessorCacheMemStatsMemTestcorrectableErrors(46776),
        tcaProcessorPcibusStatsFchcorrectableErrors(46788),
        tcaProcessorPcibusStatsFchuncorrectableErrors(46799),
        tcaProcessorPcibusStatsNorthBridgeiocorrectableErrors(46810),
        tcaProcessorPcibusStatsNorthBridgeiouncorrectableErrors(46821),
        tcaProcessorPmustatsSystemManagementUnitCorrectableErrors(46833),
        tcaProcessorPmustatsSystemManagementUnitUncorrectableErrors(46844),
        tcaProcessorIostatsSatacorrectableErrors(46856),
        tcaProcessorIostatsSatauncorrectableErrors(46867),
        tcaProcessorIostatsUsbcorrectableErrors(46878),
        tcaProcessorIostatsUsbuncorrectableErrors(46889),
        tcaProcessorIostatsPcieBankCorrectableErrors(46900),
        tcaProcessorIostatsPcieBankUncorrectableErrors(46911),
        tcaProcessorIostatsSmncorrectableErrors(46922),
        tcaProcessorIostatsSmnuncorrectableErrors(46933),
        tcaProcessorSecurityStatsPspcorrectableErrors(46945),
        tcaProcessorSecurityStatsPspuncorrectableErrors(46956),
        tcaProcessorMiscStatsCoherentSlaveCorrectableErrors(46968),
        tcaProcessorMiscStatsCoherentSlaveUncorrectableErrors(46979),
        tcaProcessorMiscStatsMpmgmntControllerCorrectableErrors(46990),
        tcaProcessorMiscStatsMpmgmntControllerUncorrectableErrors(47001),
        tcaProcessorMiscStatsParameterBlockCorrectableErrors(47012),
        tcaProcessorMiscStatsParameterBlockUncorrectableErrors(47023),
        tcaProcessorMiscStatsFloatingPointUnitCorrectableErrors(47034),
        tcaProcessorMiscStatsFloatingPointUnitUncorrectableErrors(47045),
        tcaEquipmentCrossFabricModuleStatsAmbientTemp(47252),
        tcaEquipmentCrossFabricModuleStatsAmbientTempMin(47254),
        tcaEquipmentCrossFabricModuleStatsAmbientTempMax(47255),
        tcaEquipmentCrossFabricModuleStatsAmbientTempAvg(47256),
        tcaEquipmentIocardFanModuleStatsAmbientTemp(47262),
        tcaEquipmentIocardFanModuleStatsAmbientTempMin(47264),
        tcaEquipmentIocardFanModuleStatsAmbientTempMax(47265),
        tcaEquipmentIocardFanModuleStatsAmbientTempAvg(47266),
        tcaEquipmentIocardFanStatsSpeed(47272),
        tcaEquipmentIocardFanStatsSpeedMin(47274),
        tcaEquipmentIocardFanStatsSpeedMax(47275),
        tcaEquipmentIocardFanStatsSpeedAvg(47276),
        tcaEquipmentCrossFabricModuleFanStatsSpeed(47282),
        tcaEquipmentCrossFabricModuleFanStatsSpeedMin(47284),
        tcaEquipmentCrossFabricModuleFanStatsSpeedMax(47285),
        tcaEquipmentCrossFabricModuleFanStatsSpeedAvg(47286),
        tcaComputeMbTempStatsFmTempSenFrontr(47374),
        tcaComputeMbTempStatsFmTempSenFrontrmin(47376),
        tcaComputeMbTempStatsFmTempSenFrontrmax(47377),
        tcaComputeMbTempStatsFmTempSenFrontravg(47378),
        tcaEtherMacSecTxStatsUnicastUncontrolledPacketsDelta(47410),
        tcaEtherMacSecTxStatsUnicastUncontrolledPacketsDeltaMin(47411),
        tcaEtherMacSecTxStatsUnicastUncontrolledPacketsDeltaMax(47412),
        tcaEtherMacSecTxStatsUnicastUncontrolledPacketsDeltaAvg(47413),
        tcaEtherMacSecTxStatsMulticastUncontrolledPacketsDelta(47420),
        tcaEtherMacSecTxStatsMulticastUncontrolledPacketsDeltaMin(47421),
        tcaEtherMacSecTxStatsMulticastUncontrolledPacketsDeltaMax(47422),
        tcaEtherMacSecTxStatsMulticastUncontrolledPacketsDeltaAvg(47423),
        tcaEtherMacSecTxStatsBroadcastUncontrolledPacketsDelta(47430),
        tcaEtherMacSecTxStatsBroadcastUncontrolledPacketsDeltaMin(47431),
        tcaEtherMacSecTxStatsBroadcastUncontrolledPacketsDeltaMax(47432),
        tcaEtherMacSecTxStatsBroadcastUncontrolledPacketsDeltaAvg(47433),
        tcaEtherMacSecTxStatsUncontrolledRxDropPacketsDelta(47440),
        tcaEtherMacSecTxStatsUncontrolledRxDropPacketsDeltaMin(47441),
        tcaEtherMacSecTxStatsUncontrolledRxDropPacketsDeltaMax(47442),
        tcaEtherMacSecTxStatsUncontrolledRxDropPacketsDeltaAvg(47443),
        tcaEtherMacSecTxStatsUncontrolledRxErrorPacketsDelta(47450),
        tcaEtherMacSecTxStatsUncontrolledRxErrorPacketsDeltaMin(47451),
        tcaEtherMacSecTxStatsUncontrolledRxErrorPacketsDeltaMax(47452),
        tcaEtherMacSecTxStatsUncontrolledRxErrorPacketsDeltaAvg(47453),
        tcaEtherMacSecTxStatsUnicastControlledPacketsDelta(47460),
        tcaEtherMacSecTxStatsUnicastControlledPacketsDeltaMin(47461),
        tcaEtherMacSecTxStatsUnicastControlledPacketsDeltaMax(47462),
        tcaEtherMacSecTxStatsUnicastControlledPacketsDeltaAvg(47463),
        tcaEtherMacSecTxStatsMulticastControlledPacketsDelta(47470),
        tcaEtherMacSecTxStatsMulticastControlledPacketsDeltaMin(47471),
        tcaEtherMacSecTxStatsMulticastControlledPacketsDeltaMax(47472),
        tcaEtherMacSecTxStatsMulticastControlledPacketsDeltaAvg(47473),
        tcaEtherMacSecTxStatsBroadcastControlledPacketsDelta(47480),
        tcaEtherMacSecTxStatsBroadcastControlledPacketsDeltaMin(47481),
        tcaEtherMacSecTxStatsBroadcastControlledPacketsDeltaMax(47482),
        tcaEtherMacSecTxStatsBroadcastControlledPacketsDeltaAvg(47483),
        tcaEtherMacSecTxStatsControlledRxDropPacketsDelta(47490),
        tcaEtherMacSecTxStatsControlledRxDropPacketsDeltaMin(47491),
        tcaEtherMacSecTxStatsControlledRxDropPacketsDeltaMax(47492),
        tcaEtherMacSecTxStatsControlledRxDropPacketsDeltaAvg(47493),
        tcaEtherMacSecTxStatsControlledRxErrorPacketsDelta(47500),
        tcaEtherMacSecTxStatsControlledRxErrorPacketsDeltaMin(47501),
        tcaEtherMacSecTxStatsControlledRxErrorPacketsDeltaMax(47502),
        tcaEtherMacSecTxStatsControlledRxErrorPacketsDeltaAvg(47503),
        tcaEtherMacSecTxStatsControlledPacketsDelta(47510),
        tcaEtherMacSecTxStatsControlledPacketsDeltaMin(47511),
        tcaEtherMacSecTxStatsControlledPacketsDeltaMax(47512),
        tcaEtherMacSecTxStatsControlledPacketsDeltaAvg(47513),
        tcaEtherMacSecRxStatsUnicastUncontrolledPacketsDelta(47522),
        tcaEtherMacSecRxStatsUnicastUncontrolledPacketsDeltaMin(47523),
        tcaEtherMacSecRxStatsUnicastUncontrolledPacketsDeltaMax(47524),
        tcaEtherMacSecRxStatsUnicastUncontrolledPacketsDeltaAvg(47525),
        tcaEtherMacSecRxStatsMulticastUncontrolledPacketsDelta(47532),
        tcaEtherMacSecRxStatsMulticastUncontrolledPacketsDeltaMin(47533),
        tcaEtherMacSecRxStatsMulticastUncontrolledPacketsDeltaMax(47534),
        tcaEtherMacSecRxStatsMulticastUncontrolledPacketsDeltaAvg(47535),
        tcaEtherMacSecRxStatsBroadcastUncontrolledPacketsDelta(47542),
        tcaEtherMacSecRxStatsBroadcastUncontrolledPacketsDeltaMin(47543),
        tcaEtherMacSecRxStatsBroadcastUncontrolledPacketsDeltaMax(47544),
        tcaEtherMacSecRxStatsBroadcastUncontrolledPacketsDeltaAvg(47545),
        tcaEtherMacSecRxStatsUncontrolledRxDropPacketsDelta(47552),
        tcaEtherMacSecRxStatsUncontrolledRxDropPacketsDeltaMin(47553),
        tcaEtherMacSecRxStatsUncontrolledRxDropPacketsDeltaMax(47554),
        tcaEtherMacSecRxStatsUncontrolledRxDropPacketsDeltaAvg(47555),
        tcaEtherMacSecRxStatsUncontrolledRxErrorPacketsDelta(47562),
        tcaEtherMacSecRxStatsUncontrolledRxErrorPacketsDeltaMin(47563),
        tcaEtherMacSecRxStatsUncontrolledRxErrorPacketsDeltaMax(47564),
        tcaEtherMacSecRxStatsUncontrolledRxErrorPacketsDeltaAvg(47565),
        tcaEtherMacSecRxStatsUnicastControlledPacketsDelta(47572),
        tcaEtherMacSecRxStatsUnicastControlledPacketsDeltaMin(47573),
        tcaEtherMacSecRxStatsUnicastControlledPacketsDeltaMax(47574),
        tcaEtherMacSecRxStatsUnicastControlledPacketsDeltaAvg(47575),
        tcaEtherMacSecRxStatsMulticastControlledPacketsDelta(47582),
        tcaEtherMacSecRxStatsMulticastControlledPacketsDeltaMin(47583),
        tcaEtherMacSecRxStatsMulticastControlledPacketsDeltaMax(47584),
        tcaEtherMacSecRxStatsMulticastControlledPacketsDeltaAvg(47585),
        tcaEtherMacSecRxStatsBroadcastControlledPacketsDelta(47592),
        tcaEtherMacSecRxStatsBroadcastControlledPacketsDeltaMin(47593),
        tcaEtherMacSecRxStatsBroadcastControlledPacketsDeltaMax(47594),
        tcaEtherMacSecRxStatsBroadcastControlledPacketsDeltaAvg(47595),
        tcaEtherMacSecRxStatsControlledRxDropPacketsDelta(47602),
        tcaEtherMacSecRxStatsControlledRxDropPacketsDeltaMin(47603),
        tcaEtherMacSecRxStatsControlledRxDropPacketsDeltaMax(47604),
        tcaEtherMacSecRxStatsControlledRxDropPacketsDeltaAvg(47605),
        tcaEtherMacSecRxStatsControlledRxErrorPacketsDelta(47612),
        tcaEtherMacSecRxStatsControlledRxErrorPacketsDeltaMin(47613),
        tcaEtherMacSecRxStatsControlledRxErrorPacketsDeltaMax(47614),
        tcaEtherMacSecRxStatsControlledRxErrorPacketsDeltaAvg(47615),
        tcaEtherMacSecRxStatsControlledPacketsDelta(47622),
        tcaEtherMacSecRxStatsControlledPacketsDeltaMin(47623),
        tcaEtherMacSecRxStatsControlledPacketsDeltaMax(47624),
        tcaEtherMacSecRxStatsControlledPacketsDeltaAvg(47625),
        tcaAdaptorEthPortErrStatsNoBufferDropPacketsDelta(47686),
        tcaAdaptorEthPortErrStatsNoBufferDropPacketsDeltaMin(47687),
        tcaAdaptorEthPortErrStatsNoBufferDropPacketsDeltaMax(47688),
        tcaAdaptorEthPortErrStatsNoBufferDropPacketsDeltaAvg(47689),
        tcaAdaptorEthPortPfcStatsPriority0QueueWaitTime(47698),
        tcaAdaptorEthPortPfcStatsPriority0QueueWaitTimeMin(47700),
        tcaAdaptorEthPortPfcStatsPriority0QueueWaitTimeMax(47701),
        tcaAdaptorEthPortPfcStatsPriority0QueueWaitTimeAvg(47702),
        tcaAdaptorEthPortPfcStatsPriority1QueueWaitTime(47706),
        tcaAdaptorEthPortPfcStatsPriority1QueueWaitTimeMin(47708),
        tcaAdaptorEthPortPfcStatsPriority1QueueWaitTimeMax(47709),
        tcaAdaptorEthPortPfcStatsPriority1QueueWaitTimeAvg(47710),
        tcaAdaptorEthPortPfcStatsPriority2QueueWaitTime(47714),
        tcaAdaptorEthPortPfcStatsPriority2QueueWaitTimeMin(47716),
        tcaAdaptorEthPortPfcStatsPriority2QueueWaitTimeMax(47717),
        tcaAdaptorEthPortPfcStatsPriority2QueueWaitTimeAvg(47718),
        tcaAdaptorEthPortPfcStatsPriority3QueueWaitTime(47722),
        tcaAdaptorEthPortPfcStatsPriority3QueueWaitTimeMin(47724),
        tcaAdaptorEthPortPfcStatsPriority3QueueWaitTimeMax(47725),
        tcaAdaptorEthPortPfcStatsPriority3QueueWaitTimeAvg(47726),
        tcaAdaptorEthPortPfcStatsPriority4QueueWaitTime(47730),
        tcaAdaptorEthPortPfcStatsPriority4QueueWaitTimeMin(47732),
        tcaAdaptorEthPortPfcStatsPriority4QueueWaitTimeMax(47733),
        tcaAdaptorEthPortPfcStatsPriority4QueueWaitTimeAvg(47734),
        tcaAdaptorEthPortPfcStatsPriority5QueueWaitTime(47738),
        tcaAdaptorEthPortPfcStatsPriority5QueueWaitTimeMin(47740),
        tcaAdaptorEthPortPfcStatsPriority5QueueWaitTimeMax(47741),
        tcaAdaptorEthPortPfcStatsPriority5QueueWaitTimeAvg(47742),
        tcaAdaptorEthPortPfcStatsPriority6QueueWaitTime(47746),
        tcaAdaptorEthPortPfcStatsPriority6QueueWaitTimeMin(47748),
        tcaAdaptorEthPortPfcStatsPriority6QueueWaitTimeMax(47749),
        tcaAdaptorEthPortPfcStatsPriority6QueueWaitTimeAvg(47750),
        tcaAdaptorEthPortPfcStatsPriority7QueueWaitTime(47754),
        tcaAdaptorEthPortPfcStatsPriority7QueueWaitTimeMin(47756),
        tcaAdaptorEthPortPfcStatsPriority7QueueWaitTimeMax(47757),
        tcaAdaptorEthPortPfcStatsPriority7QueueWaitTimeAvg(47758),
        fsmSamDmeSysdebugLogControlEpPersistenceRemoteInv(77832),
        fsmSamDmeMgmtRegistryInfoConfigureRemoteInv(77834),
        fsmSamDmeOrgOrgConfigureRemoteInv(77835),
        fsmSamDmeTopSystemHostNameRemoteInv(77840),
        fsmSamDmeEquipmentiocardFePresenceRemoteInv(77845),
        fsmSamDmeEquipmentiocardFeConnRemoteInv(77846),
        fsmSamDmeEquipmentChassisRemoveChassisRemoteInv(77847),
        fsmSetLocatorLedRemoteInv(77848),
        fsmSamDmeMgmtDataExporterExportDataRemoteInv(77855),
        fsmSamDmeMgmtDataImporterImportDataRemoteInv(77856),
        fsmUpdateElementRemoteInv(77864),
        fsmSamDmeTestingServiceProfileResolvePolicyFsmRemoteInv(77881),
        fsmSamDmeTestingServiceProfileResolveManyPolicyFsmRemoteInv(77882),
        fsmSamDmeCertRepairEpRepairCertRemoteInv(77944),
        fsmResolveResourceFsmRemoteInv(77951),
        fsmResolvevmfsmRemoteInv(77952),
        fsmResolveControllerFsmRemoteInv(77953),
        fsmSamDmeMgmtControllerExtMgmtIfConfigRemoteInv(77958),
        fsmSamDmeFabricComputeSlotEpIdentifyRemoteInv(77959),
        fsmSamDmeComputeBladeDiscoverRemoteInv(77960),
        fsmReleasePolicyFsmRemoteInv(77972),
        fsmSamDmeEquipmentChassisPsuPolicyConfigRemoteInv(77973),
        fsmSamDmeAdaptorHostFcIfResetFcPersBindingRemoteInv(77974),
        fsmSamDmeComputeBladeDiagRemoteInv(77975),
        fsmResolveManyOperationFsmRemoteInv(77976),
        fsmResolveManyStorageFsmRemoteInv(77977),
        fsmReleaseManyPolicyFsmRemoteInv(77978),
        fsmSwitchModeRemoteInv(77979),
        fsmReleaseManyStorageFsmRemoteInv(77980),
        fsmResolveAllPolicyFsmRemoteInv(77981),
        fsmResolveAllOperationFsmRemoteInv(77982),
        fsmResolveAllStorageFsmRemoteInv(77983),
        fsmReleaseAllPolicyFsmRemoteInv(77984),
        fsmReleaseAllOperationFsmRemoteInv(77985),
        fsmReleaseAllStorageFsmRemoteInv(77986),
        fsmSamDmeVnicProfileSetDeployRemoteInv(77990),
        fsmUpdateSvcEpRemoteInv(78016),
        fsmSamDmeCommSvcEpRestartWebSvcRemoteInv(78017),
        fsmUpdateEpRemoteInv(78019),
        fsmUpdateRealmRemoteInv(78020),
        fsmUpdateUserEpRemoteInv(78021),
        fsmSamDmePkiEpUpdateEpRemoteInv(78022),
        fsmSingleRemoteInv(78040),
        fsmSamDmeSysfileMutationGlobalRemoteInv(78041),
        fsmSamDmeConfigBackupDeleteRemoteInv(78042),
        fsmSamDmeSysdebugManualCoreFileExportTargetExportRemoteInv(78044),
        fsmSamDmeSysdebugAutoCoreFileExportTargetConfigureRemoteInv(78045),
        fsmSamDmeSysdebugLogControlEpLogControlPersistRemoteInv(78046),
        fsmSamDmeConsumerInstRenameCfgDirRemoteInv(78047),
        fsmSamDmeNfsClientDefAddConfigRemoteInv(78048),
        fsmSamDmeNfsClientDefDeleteConfigRemoteInv(78049),
        fsmSamDmeSwAccessDomainDeployRemoteInv(78074),
        fsmSamDmeSwEthLanBorderDeployRemoteInv(78075),
        fsmSamDmeSwFcSanBorderDeployRemoteInv(78076),
        fsmSamDmeSwUtilityDomainDeployRemoteInv(78077),
        fsmSamDmeComputeSystemRegisterRemoteInv(78079),
        fsmSamDmeSyntheticFsObjCreateRemoteInv(78081),
        fsmUpdateContextFsmRemoteInv(78083),
        fsmSamDmeFirmwareDownloaderDownloadRemoteInv(78090),
        fsmSamDmeFirmwareImageDeleteRemoteInv(78091),
        fsmUpdateSwitchRemoteInv(78093),
        fsmUpdateiomRemoteInv(78094),
        fsmSamDmeMgmtControllerActivateiomRemoteInv(78095),
        fsmUpdatebmcRemoteInv(78096),
        fsmSamDmeMgmtControllerActivatebmcRemoteInv(78097),
        fsmSamDmeCallhomeEpConfigCallhomeRemoteInv(78110),
        fsmSwMgmtOobIfConfigRemoteInv(78113),
        fsmSwMgmtInbandIfConfigRemoteInv(78114),
        fsmVirtualIfConfigRemoteInv(78119),
        fsmSamDmeMgmtIfEnableVipRemoteInv(78120),
        fsmSamDmeMgmtIfDisableVipRemoteInv(78121),
        fsmSamDmeMgmtIfEnablehaRemoteInv(78122),
        fsmSamDmeMgmtBackupBackupRemoteInv(78123),
        fsmSamDmeMgmtImporterImportRemoteInv(78124),
        fsmSamDmeOrgOrgConfigurePeerRemoteInv(78168),
        fsmSamDmeTopSystemPeerHostNameRemoteInv(78169),
        fsmSamDmeStatsCollectionPolicyUpdateEpRemoteInv(78182),
        fsmSamDmeQosclassDefinitionConfigGlobalQoSremoteInv(78185),
        fsmSamDmeEpqosDefinitionDeployRemoteInv(78189),
        fsmSamDmeEpqosDefinitionDelTaskRemoveRemoteInv(78190),
        fsmSamDmeControllerEpQuiesceRemoteInv(78204),
        fsmSamDmeConfigConsumerCatalogueCreateRemoteInv(78209),
        fsmSamDmeNfsExportDefImageSyncRemoteInv(78210),
        fsmSamDmeNfsExportDefAddRepoRemoteInv(78211),
        fsmUpdateIdentRemoteInv(78233),
        fsmSyncRemoteInv(78234),
        fsmSyncVnetEpucsRemoteInv(78240),
        fsmSamDmeEquipmentiocardResetCmcRemoteInv(78243),
        fsmSyncChangeucsRemoteInv(78248),
        fsmUpdateucsmanagerRemoteInv(78255),
        fsmSysConfigRemoteInv(78263),
        fsmSamDmeAdaptorExtEthIfPathResetRemoteInv(78292),
        fsmSamDmeAdaptorHostEthIfCircuitResetRemoteInv(78297),
        fsmSamDmeAdaptorHostFcIfCircuitResetRemoteInv(78298),
        fsmSamDmeExtvmmProviderConfigRemoteInv(78319),
        fsmSamDmeExtvmmKeyStoreCertInstallRemoteInv(78320),
        fsmSamDmeExtvmmSwitchDelTaskRemoveProviderRemoteInv(78321),
        fsmSamDmeExtvmmMasterExtKeyConfigRemoteInv(78338),
        fsmUpdaterRemoteInv(78344),
        fsmSamDmeFirmwareDistributableDeleteRemoteInv(78346),
        fsmDiscoverRemoteInv(78360),
        fsmAssociateRemoteInv(78361),
        fsmDisassociateRemoteInv(78362),
        fsmDecommissionRemoteInv(78364),
        fsmSoftShutdownRemoteInv(78365),
        fsmHardShutdownRemoteInv(78366),
        fsmTurnupRemoteInv(78367),
        fsmPowercycleRemoteInv(78368),
        fsmHardresetRemoteInv(78369),
        fsmSoftresetRemoteInv(78370),
        fsmSwConnUpdRemoteInv(78371),
        fsmBiosRecoveryRemoteInv(78372),
        fsmCmosResetRemoteInv(78374),
        fsmResetBmcRemoteInv(78375),
        fsmUpdateExtUsersRemoteInv(78378),
        fsmUpdateAdaptorRemoteInv(78379),
        fsmActivateAdaptorRemoteInv(78380),
        fsmConfigSoLremoteInv(78381),
        fsmUnconfigSoLremoteInv(78382),
        fsmSetFeLocatorLedRemoteInv(78383),
        fsmSamDmeEquipmentChassisPowerCapRemoteInv(78384),
        fsmSamDmeEquipmentiocardMuxOfflineRemoteInv(78385),
        fsmPowerCapRemoteInv(78390),
        fsmUpdateBoardControllerRemoteInv(78404),
        fsmDeployCatalogueRemoteInv(78405),
        fsmSamDmeComputePhysicalAssociateRemoteInv(78413),
        fsmSamDmeComputePhysicalDisassociateRemoteInv(78414),
        fsmSamDmeComputePhysicalPowerCapRemoteInv(78415),
        fsmSamDmeComputePhysicalDecommissionRemoteInv(78416),
        fsmSamDmeComputePhysicalSoftShutdownRemoteInv(78417),
        fsmSamDmeComputePhysicalHardShutdownRemoteInv(78418),
        fsmSamDmeComputePhysicalTurnupRemoteInv(78419),
        fsmSamDmeComputePhysicalPowercycleRemoteInv(78420),
        fsmSamDmeComputePhysicalHardresetRemoteInv(78421),
        fsmSamDmeComputePhysicalSoftresetRemoteInv(78422),
        fsmSamDmeComputePhysicalSwConnUpdRemoteInv(78423),
        fsmSamDmeComputePhysicalBiosRecoveryRemoteInv(78424),
        fsmSamDmeComputePhysicalCmosResetRemoteInv(78426),
        fsmSamDmeComputePhysicalResetBmcRemoteInv(78427),
        fsmSamDmeEquipmentiocardResetIomRemoteInv(78428),
        fsmInstallRemoteInv(78431),
        fsmClearRemoteInv(78432),
        fsmUpdateFlexlmRemoteInv(78433),
        fsmSamDmeComputeRackUnitDiscoverRemoteInv(78434),
        fsmSamDmeLsServerConfigureRemoteInv(78435),
        fsmSamDmeSwEthMonDeployRemoteInv(78440),
        fsmSamDmeSwFcMonDeployRemoteInv(78441),
        fsmSamDmeFabricSanCloudSwitchModeRemoteInv(78442),
        fsmRemoveFexRemoteInv(78447),
        fsmSamDmeComputePhysicalUpdateExtUsersRemoteInv(78448),
        fsmSamDmeSysdebugTechSupportInitiateRemoteInv(78452),
        fsmSamDmeSysdebugTechSupportDeleteTechSupFileRemoteInv(78453),
        fsmSamDmeSysdebugTechSupportDownloadRemoteInv(78454),
        fsmActivateCatalogRemoteInv(78457),
        fsmActivateMgmtExtRemoteInv(78458),
        fsmSamDmeDupeChangeTrackerEpConfigureRemoteInv(78472),
        fsmTriggerRemoteInv(78475),
        fsmSamDmeComputePhysicalUpdateAdaptorRemoteInv(78483),
        fsmSamDmeComputePhysicalActivateAdaptorRemoteInv(78484),
        fsmSamDmeCapabilityCatalogueActivateCatalogRemoteInv(78485),
        fsmSamDmeCapabilityMgmtExtensionActivateMgmtExtRemoteInv(78486),
        fsmSamDmeLicenseDownloaderDownloadRemoteInv(78490),
        fsmSamDmeLicenseFileInstallRemoteInv(78491),
        fsmSamDmeLicenseFileClearRemoteInv(78492),
        fsmSamDmeLicenseInstanceUpdateFlexlmRemoteInv(78493),
        fsmConfigureRemoteInv(78500),
        fsmMuxOfflineRemoteInv(78501),
        fsmSamDmeComputePhysicalConfigSoLremoteInv(78523),
        fsmSamDmeComputePhysicalUnconfigSoLremoteInv(78524),
        fsmSamDmePortpioInCompatSfpPresenceRemoteInv(78529),
        fsmSamDmeComputePhysicalDiagnosticInterruptRemoteInv(78556),
        fsmSamDmeSysdebugCoreDownloadRemoteInv(78573),
        fsmSamDmeEquipmentChassisDynamicReallocationRemoteInv(78574),
        fsmSamDmeCallhomeHolderConfigureRemoteInv(78591),
        fsmSamDmeCallhomeHolderInventoryRemoteInv(78592),
        fsmSamDmeComputePhysicalResetKvmRemoteInv(78603),
        fsmSamDmeSmartlicenseAgentConfigureRemoteInv(78604),
        fsmSamDmeSmartlicenseTestConfigureRemoteInv(78605),
        fsmSamDmeSmartlicenseEntitlementEpConfigureRemoteInv(78606),
        fsmSamDmeSmartlicenseHolderConfigureRemoteInv(78607),
        fsmSamDmeMgmtControllerOnlineRemoteInv(78609),
        fsmSamDmeComputeRackUnitOfflineRemoteInv(78610),
        fsmSamDmeEquipmentLocatorLedSetFiLocatorLedRemoteInv(78627),
        fsmConfPhysicalRemoteInv(78630),
        fsmClusterRoleRemoteInv(78632),
        fsmIlluminateRemoteInv(78635),
        fsmSetFiLocatorLedRemoteInv(78636),
        fsmDeployAliasRemoteInv(78647),
        fsmSamDmeFabricEpMgrConfigureRemoteInv(78654),
        fsmSamDmeVnicProfileSetDeployAliasRemoteInv(78663),
        fsmSamDmeSwPhysConfPhysicalRemoteInv(78679),
        fsmSamDmeExtvmmEpClusterRoleRemoteInv(78694),
        fsmSamDmeVmLifeCyclePolicyConfigRemoteInv(78699),
        fsmUpdateStateRemoteInv(78701),
        fsmSamDmeEquipmentBeaconLedIlluminateRemoteInv(78702),
        fsmSamDmeEtherServerIntfioConfigSpeedRemoteInv(78711),
        fsmUpdatebiosRemoteInv(78721),
        fsmSamDmeComputePhysicalActivatebiosRemoteInv(78722),
        fsmSamDmeCommDateTimeTimezoneRemoteInv(78752),
        fsmSamDmeFirmwareSystemDeployRemoteInv(78765),
        fsmSamDmeFirmwareSystemApplyCatalogPackRemoteInv(78766),
        fsmSamDmeMgmtExportPolicyReportConfigCopyRemoteInv(78779),
        fsmSamDmeMgmtImporterReportConfigImportRemoteInv(78780),
        fsmSamDmeNfsMountInstMountRemoteInv(78788),
        fsmSamDmeNfsMountInstUnmountRemoteInv(78789),
        fsmSamDmeNfsMountDefReportNfsMountSuspendRemoteInv(78790),
        fsmSamDmeStorageSystemSyncRemoteInv(78807),
        fsmSamDmePolicyControlEpOpRemoteDomainRegRemoteInv(78811),
        fsmSamDmePolicyControlEpOpRemoteDomainUnRegRemoteInv(78812),
        fsmSamDmeEquipmentChassisProfileConfigureRemoteInv(78813),
        fsmSamDmeSwFcSanBorderActivateZoneSetRemoteInv(78821),
        fsmSamDmeExtpolEpRegisterFsmRemoteInv(78822),
        fsmSamDmeExtpolRegistryCrossDomainConfigRemoteInv(78823),
        fsmSamDmeExtpolRegistryCrossDomainDeleteRemoteInv(78824),
        fsmSamDmeExtpolEpRepairCertRemoteInv(78839),
        fsmSamDmePolicyControlEpOperateRemoteInv(78840),
        fsmSamDmePolicyPolicyScopeReleasePolicyFsmRemoteInv(78842),
        fsmSamDmePolicyPolicyScopeReleaseOperationFsmRemoteInv(78843),
        fsmSamDmePolicyPolicyScopeReleaseStorageFsmRemoteInv(78844),
        fsmSamDmePolicyPolicyScopeResolveManyPolicyFsmRemoteInv(78845),
        fsmSamDmePolicyPolicyScopeResolveManyOperationFsmRemoteInv(78846),
        fsmSamDmePolicyPolicyScopeResolveManyStorageFsmRemoteInv(78847),
        fsmSamDmePolicyPolicyScopeReleaseManyPolicyFsmRemoteInv(78848),
        fsmSamDmePolicyPolicyScopeReleaseManyOperationFsmRemoteInv(78849),
        fsmSamDmePolicyPolicyScopeReleaseManyStorageFsmRemoteInv(78850),
        fsmSamDmePolicyPolicyScopeResolveAllPolicyFsmRemoteInv(78851),
        fsmSamDmePolicyPolicyScopeResolveAllOperationFsmRemoteInv(78852),
        fsmSamDmePolicyPolicyScopeResolveAllStorageFsmRemoteInv(78853),
        fsmSamDmePolicyPolicyScopeReleaseAllPolicyFsmRemoteInv(78854),
        fsmSamDmePolicyPolicyScopeReleaseAllOperationFsmRemoteInv(78855),
        fsmSamDmePolicyPolicyScopeReleaseAllStorageFsmRemoteInv(78856),
        fsmSamDmeIdentIdentRequestUpdateIdentRemoteInv(78858),
        fsmSamDmeIdentMetaSystemSyncRemoteInv(78859),
        fsmSamDmeMgmtControllerRegistryConfigRemoteInv(78860),
        fsmSamDmeGlRequestEvaluateRemoteInv(78861),
        fsmSamDmeGlRequestCreateGlobalIdPoolRemoteInv(78862),
        fsmSamDmeGlRequestCreateGlobalPolicyRemoteInv(78863),
        fsmSamDmeGlRequestGlobalizeRemoteInv(78864),
        fsmSamDmeObserveObservedResolvePolicyFsmRemoteInv(78865),
        fsmSamDmeObserveObservedResolveResourceFsmRemoteInv(78866),
        fsmSamDmeObserveObservedResolvevmfsmRemoteInv(78867),
        fsmSamDmeObserveObservedResolveControllerFsmRemoteInv(78868),
        fsmSamDmeDiagSrvCtrlOperationConfigureRemoteInv(78884),
        fsmSamDmePortpioInCompatSfpReplacedRemoteInv(78885),
        fsmSamDmeFdPhysicalConfigureRemoteInv(78891),
        fsmSamDmeVnicOutbandMgmtEpConfigureOutbandRemoteInv(78913),
        fsmSamDmeDomainProfileConfigureRemoteInv(78914),
        fsmSamDmeComputePhysicalResetIpmiRemoteInv(78916),
        fsmSamDmeComputePhysicalFwUpgradeRemoteInv(78917),
        fsmSamDmeComputeRackUnitAdapterResetRemoteInv(78918),
        fsmSamDmeFabricFcZoneProfileConfigureRemoteInv(78919),
        fsmSamDmeComputeServerDiscPolicyResolveScrubPolicyRemoteInv(78923),
        fsmSamDmeExtpolProviderReportConfigImportRemoteInv(78925),
        fsmSamDmeFabricVnetEpSyncEpPushVnetEpDeletionRemoteInv(79039),
        fsmSamDmeGmetaHolderInventoryRemoteInv(79041),
        fsmSamDmeComputePhysicalCimcSessionDeleteRemoteInv(79042),
        fsmSamDmePolicyControlledTypeOperateRemoteInv(79052),
        fsmSamDmeMgmtControllerExtMgmtInterfaceConfigRemoteInv(79100),
        fsmSamDmeComputeRackUnitCreateDhcpEntryRemoteInv(79101),
        fsmSamDmeComputePhysicalServiceInfraDeployRemoteInv(79102),
        fsmSamDmeComputePhysicalServiceInfraWithdrawRemoteInv(79103),
        fsmSamDmeComputePhysicalUpdateBoardControllerRemoteInv(79107),
        fsmSamDmeComputePhysicalConfigBoardRemoteInv(79142),
        fsmSamDmeComputePhysicalResetMemoryErrorsRemoteInv(79143),
        fsmSamDmeMgmtipv6IfAddrSwMgmtOobIpv6IfConfigRemoteInv(79147),
        fsmSamDmeSwEthLanFlowMonDeployRemoteInv(79153),
        fsmSamDmeExtvmmNetworkSetsDeployRemoteInv(79173),
        fsmSamDmeComputePhysicalFlashControllerRemoteInv(79202),
        fsmSamDmeSysdebugLogExportPolicyConfigureRemoteInv(79228),
        fsmSamDmeStorageFlexFlashControllermopsResetRemoteInv(79231),
        fsmSamDmeStorageFlexFlashControllermopsFormatRemoteInv(79232),
        fsmSamDmeStorageFlexFlashControllermopsPairRemoteInv(79233),
        fsmSamDmeComputePhysicalEnableCimcSecureBootRemoteInv(79246),
        fsmSamDmeIdentMetaSystemUcscUnivSyncRemoteInv(79264),
        fsmSamDmeStoragePartitionDeployStorageRemoteInv(79361),
        fsmSamDmeStorageProcessorDiscoverSystemRemoteInv(79362),
        fsmSamDmeStorageProcessorEnterMaintenanceRemoteInv(79363),
        fsmSamDmeStorageProcessorExitMaintenanceRemoteInv(79364),
        fsmSamDmeStorageProcessorDeploySystemRemoteInv(79365),
        fsmSamDmeStorageProcessorUndeploySystemRemoteInv(79366),
        fsmSamDmeStorageProcessorHaTakeOverRemoteInv(79367),
        fsmSamDmeStoragePartitionScrubraidgroupRemoteInv(79368),
        fsmSamDmeMgmtControllerLockConfigRemoteInv(79373),
        fsmSamDmeMgmtControllerPowerBudgetReclaimConfigRemoteInv(79374),
        fsmSamDmeComputePhysicalOobStorageAdminConfigRemoteInv(79375),
        fsmSamDmeEquipmentiocardBaseFePresenceRemoteInv(79380),
        fsmSamDmeEquipmentiocardBaseFeConnRemoteInv(79381),
        fsmSamDmeEquipmentLocatorLedSetDiskLocatorLedRemoteInv(79394),
        fsmSamDmeLstorageProcessorConfigureRemoteInv(79418),
        fsmSamDmeOsControllerDeployosRemoteInv(79424),
        fsmSamDmeEquipmentPsuUpdatepsuRemoteInv(79427),
        fsmSamDmeMgmtControllerUpdatecmcRemoteInv(79452),
        fsmSamDmeMgmtControllerActivatecmcRemoteInv(79453),
        fsmSamDmeMgmtControllerUpdateAdaptorRemoteInv(79454),
        fsmSamDmeMgmtControllerActivateAdaptorRemoteInv(79455),
        fsmSamDmeMgmtControllerUpdateRaidControllerRemoteInv(79456),
        fsmSamDmeMgmtControllerUpdateBoardControllerRemoteInv(79457),
        fsmSamDmeFabricCartridgeSlotEpIdentifyRemoteInv(79464),
        fsmSamDmeFabricComputemslotEpIdentifyRemoteInv(79465),
        fsmSamDmeEquipmentChassisOobStorageAdminCfgRemoteInv(79466),
        fsmSamDmeComputeServerUnitDiscoverRemoteInv(79472),
        fsmSamDmeMgmtIfFaPresenceRemoteInv(79473),
        fsmSamDmeMgmtIfFaConnRemoteInv(79474),
        fsmSamDmeEquipmentiocardEvacuateRemoteInv(79485),
        fsmSamDmeEquipmentiocardResetEvacuateRemoteInv(79486),
        fsmSamDmeComputePhysicalCleartpmRemoteInv(79491),
        fsmSamDmeEquipmentiocardResetPeerCmcRemoteInv(79542),
        fsmSamDmeSwExtUtilityConfPortBreakoutRemoteInv(79564),
        fsmSamDmeEquipmentSwitchiocardEvacuateRemoteInv(79586),
        fsmSamDmeEquipmentSwitchiocardResetEvacuateRemoteInv(79587),
        fsmSamDmeMorefImportRootApplyMoRefsRemoteInv(79601),
        fsmSamDmeStorageEnclosureRemoveEnclosureRemoteInv(79609),
        fsmSamDmeMgmtControllerPowerCapRemoteInv(79624),
        fsmSamDmeEquipmentSystemiocontrollerResetCmcRemoteInv(79625),
        fsmSamDmeComputePhysicalDiskZoningInventoryRemoteInv(79626),
        fsmSamDmeEquipmentChassisAssociateRemoteInv(79647),
        fsmSamDmeEquipmentChassisDisassociateRemoteInv(79648),
        fsmSamDmeEtherServerIntfioConfigRemoteInv(79677),
        fsmSamDmeMgmtControllerEnableSecureBootRemoteInv(79679),
        fsmSamDmeMgmtControllerUpdateColusacmcRemoteInv(79680),
        fsmSamDmeMgmtControllerActivateColusacmcRemoteInv(79681),
        fsmSamDmeEquipmentChassisChassisUpgradeRemoteInv(79682),
        fsmSamDmeMgmtControllerUpdateColusaBoardControllerRemoteInv(79683),
        fsmSamDmeMgmtControllerUpdateSasExpanderRemoteInv(79684),
        fsmSamDmeMgmtControllerActivateSasExpanderRemoteInv(79685),
        fsmSamDmeMgmtControllerActivateLocalDiskRemoteInv(79686),
        fsmSamDmeStorageLocalDiskUpdateLocalDiskRemoteInv(79687),
        fsmSamDmeMgmtControllerUpdateucsmanagerspRemoteInv(79699),
        fsmSamDmeComputePhysicalDiagRemoteInv(79700),
        fsmSamDmeComputePhysicalCimcSecurityConfigRemoteInv(79701),
        fsmSamDmeSwPortDiscoverDeployRemoteInv(79730),
        fsmSamDmePolicyPolicyScopeContReportPolicyFailFsmRemoteInv(79733),
        fsmSamDmePolicyRequestorResolveFromCentralRemoteInv(79734),
        fsmSamDmeFabricReservedVlanDeployRemoteInv(79776),
        fsmSamDmeEquipmentChassisFwUpgradeRemoteInv(79779),
        fsmSamDmeMgmtControllerKvmCertRemoteInv(79782),
        fsmSamDmeQosclassSlowDrainConfigQosslowDrainRemoteInv(79801),
        fsmSamDmeQosclassSlowDrainConfigQosslowDrainFexRemoteInv(79802),
        fsmSamDmeComputePhysicalExecuteActionsRemoteInv(79815),
        fsmSamDmeEquipmentChassisFanPolicyConfigRemoteInv(79816),
        fsmSamDmeComputePhysicalNvmeSwitchRecoveryRemoteInv(79817),
        fsmSamDmeMgmtControllerUpdateStorageServercmcRemoteInv(79819),
        fsmSamDmeMgmtControllerActivateStorageServercmcRemoteInv(79820),
        fsmSamDmeMgmtControllerUpgradeBoardControllerRemoteInv(79821),
        fsmSamDmeComputePhysicalReinitializeVirtualDriveRemoteInv(79835),
        fsmSamDmeEquipmentChassisPowerSavePolicyConfigRemoteInv(79844),
        fsmSamDmeFcpoolOuisDeployRemoteInv(79846),
        fsmSamDmeMgmtControllerUpdateSecurefpgaRemoteInv(79850),
        fsmSamDmePfcWatchDogConfigPfcWatchDogRemoteInv(79851),
        fsmSamDmeMgmtControllerConfigureSwPersonalitiesRemoteInv(79867),
        fsmSamDmeComputePhysicalConfigureServerPersonalityRemoteInv(79868),
        fsmSamDmeComputePhysicalBiosPasswordResetRemoteInv(79871),
        fsmSamDmeComputePhysicalCimcSecurityUnconfigRemoteInv(79872),
        fsmSamDmeEquipmentChassisPowerExtendedPolicyConfigRemoteInv(79896),
        fsmSamDmeComputePhysicalDataSanitizationRemoteInv(79918),
        fsmSamDmeSwrmonEpDeployrmonEpRemoteInv(79970),
        fsmSamDmeSecurityEncryptionEpUpdateEncryptionEpRemoteInv(79973),
        fsmSamDmeSysdebugLogControlEpPersistenceFsmFail(999432),
        fsmSamDmeMgmtRegistryInfoConfigureFsmFail(999434),
        fsmSamDmeOrgOrgConfigureFsmFail(999435),
        fsmSamDmeTopSystemHostNameFsmFail(999440),
        fsmSamDmeEquipmentiocardFePresenceFsmFail(999445),
        fsmSamDmeEquipmentiocardFeConnFsmFail(999446),
        fsmSamDmeEquipmentChassisRemoveChassisFsmFail(999447),
        fsmSetLocatorLedFsmFail(999448),
        fsmSamDmeMgmtDataExporterExportDataFsmFail(999455),
        fsmSamDmeMgmtDataImporterImportDataFsmFail(999456),
        fsmUpdateElementFsmFail(999464),
        fsmSamDmeTestingServiceProfileResolvePolicyFsmFsmFail(999481),
        fsmSamDmeTestingServiceProfileResolveManyPolicyFsmFsmFail(999482),
        fsmSamDmeCertRepairEpRepairCertFsmFail(999544),
        fsmResolveResourceFsmFsmFail(999551),
        fsmResolvevmfsmFsmFail(999552),
        fsmResolveControllerFsmFsmFail(999553),
        fsmSamDmeMgmtControllerExtMgmtIfConfigFsmFail(999558),
        fsmSamDmeFabricComputeSlotEpIdentifyFsmFail(999559),
        fsmSamDmeComputeBladeDiscoverFsmFail(999560),
        fsmReleasePolicyFsmFsmFail(999572),
        fsmSamDmeEquipmentChassisPsuPolicyConfigFsmFail(999573),
        fsmSamDmeAdaptorHostFcIfResetFcPersBindingFsmFail(999574),
        fsmSamDmeComputeBladeDiagFsmFail(999575),
        fsmResolveManyOperationFsmFsmFail(999576),
        fsmResolveManyStorageFsmFsmFail(999577),
        fsmReleaseManyPolicyFsmFsmFail(999578),
        fsmSwitchModeFsmFail(999579),
        fsmReleaseManyStorageFsmFsmFail(999580),
        fsmResolveAllPolicyFsmFsmFail(999581),
        fsmResolveAllOperationFsmFsmFail(999582),
        fsmResolveAllStorageFsmFsmFail(999583),
        fsmReleaseAllPolicyFsmFsmFail(999584),
        fsmReleaseAllOperationFsmFsmFail(999585),
        fsmReleaseAllStorageFsmFsmFail(999586),
        fsmSamDmeVnicProfileSetDeployFsmFail(999590),
        fsmUpdateSvcEpFsmFail(999616),
        fsmSamDmeCommSvcEpRestartWebSvcFsmFail(999617),
        fsmUpdateEpFsmFail(999619),
        fsmUpdateRealmFsmFail(999620),
        fsmUpdateUserEpFsmFail(999621),
        fsmSamDmePkiEpUpdateEpFsmFail(999622),
        fsmSingleFsmFail(999640),
        fsmSamDmeSysfileMutationGlobalFsmFail(999641),
        fsmSamDmeConfigBackupDeleteFsmFail(999642),
        fsmSamDmeSysdebugManualCoreFileExportTargetExportFsmFail(999644),
        fsmSamDmeSysdebugAutoCoreFileExportTargetConfigureFsmFail(999645),
        fsmSamDmeSysdebugLogControlEpLogControlPersistFsmFail(999646),
        fsmSamDmeConsumerInstRenameCfgDirFsmFail(999647),
        fsmSamDmeNfsClientDefAddConfigFsmFail(999648),
        fsmSamDmeNfsClientDefDeleteConfigFsmFail(999649),
        fsmSamDmeSwAccessDomainDeployFsmFail(999674),
        fsmSamDmeSwEthLanBorderDeployFsmFail(999675),
        fsmSamDmeSwFcSanBorderDeployFsmFail(999676),
        fsmSamDmeSwUtilityDomainDeployFsmFail(999677),
        fsmSamDmeComputeSystemRegisterFsmFail(999679),
        fsmSamDmeSyntheticFsObjCreateFsmFail(999681),
        fsmUpdateContextFsmFsmFail(999683),
        fsmSamDmeFirmwareDownloaderDownloadFsmFail(999690),
        fsmSamDmeFirmwareImageDeleteFsmFail(999691),
        fsmUpdateSwitchFsmFail(999693),
        fsmUpdateiomFsmFail(999694),
        fsmSamDmeMgmtControllerActivateiomFsmFail(999695),
        fsmUpdatebmcFsmFail(999696),
        fsmSamDmeMgmtControllerActivatebmcFsmFail(999697),
        fsmSamDmeCallhomeEpConfigCallhomeFsmFail(999710),
        fsmSwMgmtOobIfConfigFsmFail(999713),
        fsmSwMgmtInbandIfConfigFsmFail(999714),
        fsmVirtualIfConfigFsmFail(999719),
        fsmSamDmeMgmtIfEnableVipFsmFail(999720),
        fsmSamDmeMgmtIfDisableVipFsmFail(999721),
        fsmSamDmeMgmtIfEnablehaFsmFail(999722),
        fsmSamDmeMgmtBackupBackupFsmFail(999723),
        fsmSamDmeMgmtImporterImportFsmFail(999724),
        fsmSamDmeOrgOrgConfigurePeerFsmFail(999768),
        fsmSamDmeTopSystemPeerHostNameFsmFail(999769),
        fsmSamDmeStatsCollectionPolicyUpdateEpFsmFail(999782),
        fsmSamDmeQosclassDefinitionConfigGlobalQoSfsmFail(999785),
        fsmSamDmeEpqosDefinitionDeployFsmFail(999789),
        fsmSamDmeEpqosDefinitionDelTaskRemoveFsmFail(999790),
        fsmSamDmeControllerEpQuiesceFsmFail(999804),
        fsmSamDmeConfigConsumerCatalogueCreateFsmFail(999809),
        fsmSamDmeNfsExportDefImageSyncFsmFail(999810),
        fsmSamDmeNfsExportDefAddRepoFsmFail(999811),
        fsmUpdateIdentFsmFail(999833),
        fsmSyncFsmFail(999834),
        fsmSyncVnetEpucsFsmFail(999840),
        fsmSamDmeEquipmentiocardResetCmcFsmFail(999843),
        fsmSyncChangeucsFsmFail(999848),
        fsmUpdateucsmanagerFsmFail(999855),
        fsmSysConfigFsmFail(999863),
        fsmSamDmeAdaptorExtEthIfPathResetFsmFail(999892),
        fsmSamDmeAdaptorHostEthIfCircuitResetFsmFail(999897),
        fsmSamDmeAdaptorHostFcIfCircuitResetFsmFail(999898),
        fsmSamDmeExtvmmProviderConfigFsmFail(999919),
        fsmSamDmeExtvmmKeyStoreCertInstallFsmFail(999920),
        fsmSamDmeExtvmmSwitchDelTaskRemoveProviderFsmFail(999921),
        fsmSamDmeExtvmmMasterExtKeyConfigFsmFail(999938),
        fsmUpdaterFsmFail(999944),
        fsmSamDmeFirmwareDistributableDeleteFsmFail(999946),
        fsmDiscoverFsmFail(999960),
        fsmAssociateFsmFail(999961),
        fsmDisassociateFsmFail(999962),
        fsmDecommissionFsmFail(999964),
        fsmSoftShutdownFsmFail(999965),
        fsmHardShutdownFsmFail(999966),
        fsmTurnupFsmFail(999967),
        fsmPowercycleFsmFail(999968),
        fsmHardresetFsmFail(999969),
        fsmSoftresetFsmFail(999970),
        fsmSwConnUpdFsmFail(999971),
        fsmBiosRecoveryFsmFail(999972),
        fsmCmosResetFsmFail(999974),
        fsmResetBmcFsmFail(999975),
        fsmUpdateExtUsersFsmFail(999978),
        fsmUpdateAdaptorFsmFail(999979),
        fsmActivateAdaptorFsmFail(999980),
        fsmConfigSoLfsmFail(999981),
        fsmUnconfigSoLfsmFail(999982),
        fsmSetFeLocatorLedFsmFail(999983),
        fsmSamDmeEquipmentChassisPowerCapFsmFail(999984),
        fsmSamDmeEquipmentiocardMuxOfflineFsmFail(999985),
        fsmPowerCapFsmFail(999990),
        fsmUpdateBoardControllerFsmFail(1000004),
        fsmDeployCatalogueFsmFail(1000005),
        fsmSamDmeComputePhysicalAssociateFsmFail(1000013),
        fsmSamDmeComputePhysicalDisassociateFsmFail(1000014),
        fsmSamDmeComputePhysicalPowerCapFsmFail(1000015),
        fsmSamDmeComputePhysicalDecommissionFsmFail(1000016),
        fsmSamDmeComputePhysicalSoftShutdownFsmFail(1000017),
        fsmSamDmeComputePhysicalHardShutdownFsmFail(1000018),
        fsmSamDmeComputePhysicalTurnupFsmFail(1000019),
        fsmSamDmeComputePhysicalPowercycleFsmFail(1000020),
        fsmSamDmeComputePhysicalHardresetFsmFail(1000021),
        fsmSamDmeComputePhysicalSoftresetFsmFail(1000022),
        fsmSamDmeComputePhysicalSwConnUpdFsmFail(1000023),
        fsmSamDmeComputePhysicalBiosRecoveryFsmFail(1000024),
        fsmSamDmeComputePhysicalCmosResetFsmFail(1000026),
        fsmSamDmeComputePhysicalResetBmcFsmFail(1000027),
        fsmSamDmeEquipmentiocardResetIomFsmFail(1000028),
        fsmInstallFsmFail(1000031),
        fsmClearFsmFail(1000032),
        fsmUpdateFlexlmFsmFail(1000033),
        fsmSamDmeComputeRackUnitDiscoverFsmFail(1000034),
        fsmSamDmeLsServerConfigureFsmFail(1000035),
        fsmSamDmeSwEthMonDeployFsmFail(1000040),
        fsmSamDmeSwFcMonDeployFsmFail(1000041),
        fsmSamDmeFabricSanCloudSwitchModeFsmFail(1000042),
        fsmRemoveFexFsmFail(1000047),
        fsmSamDmeComputePhysicalUpdateExtUsersFsmFail(1000048),
        fsmSamDmeSysdebugTechSupportInitiateFsmFail(1000052),
        fsmSamDmeSysdebugTechSupportDeleteTechSupFileFsmFail(1000053),
        fsmSamDmeSysdebugTechSupportDownloadFsmFail(1000054),
        fsmActivateCatalogFsmFail(1000057),
        fsmActivateMgmtExtFsmFail(1000058),
        fsmSamDmeDupeChangeTrackerEpConfigureFsmFail(1000072),
        fsmTriggerFsmFail(1000075),
        fsmSamDmeComputePhysicalUpdateAdaptorFsmFail(1000083),
        fsmSamDmeComputePhysicalActivateAdaptorFsmFail(1000084),
        fsmSamDmeCapabilityCatalogueActivateCatalogFsmFail(1000085),
        fsmSamDmeCapabilityMgmtExtensionActivateMgmtExtFsmFail(1000086),
        fsmSamDmeLicenseDownloaderDownloadFsmFail(1000090),
        fsmSamDmeLicenseFileInstallFsmFail(1000091),
        fsmSamDmeLicenseFileClearFsmFail(1000092),
        fsmSamDmeLicenseInstanceUpdateFlexlmFsmFail(1000093),
        fsmConfigureFsmFail(1000100),
        fsmMuxOfflineFsmFail(1000101),
        fsmSamDmeComputePhysicalConfigSoLfsmFail(1000123),
        fsmSamDmeComputePhysicalUnconfigSoLfsmFail(1000124),
        fsmSamDmePortpioInCompatSfpPresenceFsmFail(1000129),
        fsmSamDmeComputePhysicalDiagnosticInterruptFsmFail(1000156),
        fsmSamDmeSysdebugCoreDownloadFsmFail(1000173),
        fsmSamDmeEquipmentChassisDynamicReallocationFsmFail(1000174),
        fsmSamDmeCallhomeHolderConfigureFsmFail(1000191),
        fsmSamDmeCallhomeHolderInventoryFsmFail(1000192),
        fsmSamDmeComputePhysicalResetKvmFsmFail(1000203),
        fsmSamDmeSmartlicenseAgentConfigureFsmFail(1000204),
        fsmSamDmeSmartlicenseTestConfigureFsmFail(1000205),
        fsmSamDmeSmartlicenseEntitlementEpConfigureFsmFail(1000206),
        fsmSamDmeSmartlicenseHolderConfigureFsmFail(1000207),
        fsmSamDmeMgmtControllerOnlineFsmFail(1000209),
        fsmSamDmeComputeRackUnitOfflineFsmFail(1000210),
        fsmSamDmeEquipmentLocatorLedSetFiLocatorLedFsmFail(1000227),
        fsmConfPhysicalFsmFail(1000230),
        fsmClusterRoleFsmFail(1000232),
        fsmIlluminateFsmFail(1000235),
        fsmSetFiLocatorLedFsmFail(1000236),
        fsmDeployAliasFsmFail(1000247),
        fsmSamDmeFabricEpMgrConfigureFsmFail(1000254),
        fsmSamDmeVnicProfileSetDeployAliasFsmFail(1000263),
        fsmSamDmeSwPhysConfPhysicalFsmFail(1000279),
        fsmSamDmeExtvmmEpClusterRoleFsmFail(1000294),
        fsmSamDmeVmLifeCyclePolicyConfigFsmFail(1000299),
        fsmUpdateStateFsmFail(1000301),
        fsmSamDmeEquipmentBeaconLedIlluminateFsmFail(1000302),
        fsmSamDmeEtherServerIntfioConfigSpeedFsmFail(1000311),
        fsmUpdatebiosFsmFail(1000321),
        fsmSamDmeComputePhysicalActivatebiosFsmFail(1000322),
        fsmSamDmeCommDateTimeTimezoneFsmFail(1000352),
        fsmSamDmeFirmwareSystemDeployFsmFail(1000365),
        fsmSamDmeFirmwareSystemApplyCatalogPackFsmFail(1000366),
        fsmSamDmeMgmtExportPolicyReportConfigCopyFsmFail(1000379),
        fsmSamDmeMgmtImporterReportConfigImportFsmFail(1000380),
        fsmSamDmeNfsMountInstMountFsmFail(1000388),
        fsmSamDmeNfsMountInstUnmountFsmFail(1000389),
        fsmSamDmeNfsMountDefReportNfsMountSuspendFsmFail(1000390),
        fsmSamDmeStorageSystemSyncFsmFail(1000407),
        fsmSamDmePolicyControlEpOpRemoteDomainRegFsmFail(1000411),
        fsmSamDmePolicyControlEpOpRemoteDomainUnRegFsmFail(1000412),
        fsmSamDmeEquipmentChassisProfileConfigureFsmFail(1000413),
        fsmSamDmeSwFcSanBorderActivateZoneSetFsmFail(1000421),
        fsmSamDmeExtpolEpRegisterFsmFsmFail(1000422),
        fsmSamDmeExtpolRegistryCrossDomainConfigFsmFail(1000423),
        fsmSamDmeExtpolRegistryCrossDomainDeleteFsmFail(1000424),
        fsmSamDmeExtpolEpRepairCertFsmFail(1000439),
        fsmSamDmePolicyControlEpOperateFsmFail(1000440),
        fsmSamDmePolicyPolicyScopeReleasePolicyFsmFsmFail(1000442),
        fsmSamDmePolicyPolicyScopeReleaseOperationFsmFsmFail(1000443),
        fsmSamDmePolicyPolicyScopeReleaseStorageFsmFsmFail(1000444),
        fsmSamDmePolicyPolicyScopeResolveManyPolicyFsmFsmFail(1000445),
        fsmSamDmePolicyPolicyScopeResolveManyOperationFsmFsmFail(1000446),
        fsmSamDmePolicyPolicyScopeResolveManyStorageFsmFsmFail(1000447),
        fsmSamDmePolicyPolicyScopeReleaseManyPolicyFsmFsmFail(1000448),
        fsmSamDmePolicyPolicyScopeReleaseManyOperationFsmFsmFail(1000449),
        fsmSamDmePolicyPolicyScopeReleaseManyStorageFsmFsmFail(1000450),
        fsmSamDmePolicyPolicyScopeResolveAllPolicyFsmFsmFail(1000451),
        fsmSamDmePolicyPolicyScopeResolveAllOperationFsmFsmFail(1000452),
        fsmSamDmePolicyPolicyScopeResolveAllStorageFsmFsmFail(1000453),
        fsmSamDmePolicyPolicyScopeReleaseAllPolicyFsmFsmFail(1000454),
        fsmSamDmePolicyPolicyScopeReleaseAllOperationFsmFsmFail(1000455),
        fsmSamDmePolicyPolicyScopeReleaseAllStorageFsmFsmFail(1000456),
        fsmSamDmeIdentIdentRequestUpdateIdentFsmFail(1000458),
        fsmSamDmeIdentMetaSystemSyncFsmFail(1000459),
        fsmSamDmeMgmtControllerRegistryConfigFsmFail(1000460),
        fsmSamDmeGlRequestEvaluateFsmFail(1000461),
        fsmSamDmeGlRequestCreateGlobalIdPoolFsmFail(1000462),
        fsmSamDmeGlRequestCreateGlobalPolicyFsmFail(1000463),
        fsmSamDmeGlRequestGlobalizeFsmFail(1000464),
        fsmSamDmeObserveObservedResolvePolicyFsmFsmFail(1000465),
        fsmSamDmeObserveObservedResolveResourceFsmFsmFail(1000466),
        fsmSamDmeObserveObservedResolvevmfsmFsmFail(1000467),
        fsmSamDmeObserveObservedResolveControllerFsmFsmFail(1000468),
        fsmSamDmeDiagSrvCtrlOperationConfigureFsmFail(1000484),
        fsmSamDmePortpioInCompatSfpReplacedFsmFail(1000485),
        fsmSamDmeFdPhysicalConfigureFsmFail(1000491),
        fsmSamDmeVnicOutbandMgmtEpConfigureOutbandFsmFail(1000513),
        fsmSamDmeDomainProfileConfigureFsmFail(1000514),
        fsmSamDmeComputePhysicalResetIpmiFsmFail(1000516),
        fsmSamDmeComputePhysicalFwUpgradeFsmFail(1000517),
        fsmSamDmeComputeRackUnitAdapterResetFsmFail(1000518),
        fsmSamDmeFabricFcZoneProfileConfigureFsmFail(1000519),
        fsmSamDmeComputeServerDiscPolicyResolveScrubPolicyFsmFail(1000523),
        fsmSamDmeExtpolProviderReportConfigImportFsmFail(1000525),
        fsmSamDmeFabricVnetEpSyncEpPushVnetEpDeletionFsmFail(1000639),
        fsmSamDmeGmetaHolderInventoryFsmFail(1000641),
        fsmSamDmeComputePhysicalCimcSessionDeleteFsmFail(1000642),
        fsmSamDmePolicyControlledTypeOperateFsmFail(1000652),
        fsmSamDmeMgmtControllerExtMgmtInterfaceConfigFsmFail(1000700),
        fsmSamDmeComputeRackUnitCreateDhcpEntryFsmFail(1000701),
        fsmSamDmeComputePhysicalServiceInfraDeployFsmFail(1000702),
        fsmSamDmeComputePhysicalServiceInfraWithdrawFsmFail(1000703),
        fsmSamDmeComputePhysicalUpdateBoardControllerFsmFail(1000707),
        fsmSamDmeComputePhysicalConfigBoardFsmFail(1000742),
        fsmSamDmeComputePhysicalResetMemoryErrorsFsmFail(1000743),
        fsmSamDmeMgmtipv6IfAddrSwMgmtOobIpv6IfConfigFsmFail(1000747),
        fsmSamDmeSwEthLanFlowMonDeployFsmFail(1000753),
        fsmSamDmeExtvmmNetworkSetsDeployFsmFail(1000773),
        fsmSamDmeComputePhysicalFlashControllerFsmFail(1000802),
        fsmSamDmeSysdebugLogExportPolicyConfigureFsmFail(1000828),
        fsmSamDmeStorageFlexFlashControllermopsResetFsmFail(1000831),
        fsmSamDmeStorageFlexFlashControllermopsFormatFsmFail(1000832),
        fsmSamDmeStorageFlexFlashControllermopsPairFsmFail(1000833),
        fsmSamDmeComputePhysicalEnableCimcSecureBootFsmFail(1000846),
        fsmSamDmeIdentMetaSystemUcscUnivSyncFsmFail(1000864),
        fsmSamDmeStoragePartitionDeployStorageFsmFail(1000961),
        fsmSamDmeStorageProcessorDiscoverSystemFsmFail(1000962),
        fsmSamDmeStorageProcessorEnterMaintenanceFsmFail(1000963),
        fsmSamDmeStorageProcessorExitMaintenanceFsmFail(1000964),
        fsmSamDmeStorageProcessorDeploySystemFsmFail(1000965),
        fsmSamDmeStorageProcessorUndeploySystemFsmFail(1000966),
        fsmSamDmeStorageProcessorHaTakeOverFsmFail(1000967),
        fsmSamDmeStoragePartitionScrubraidgroupFsmFail(1000968),
        fsmSamDmeMgmtControllerLockConfigFsmFail(1000973),
        fsmSamDmeMgmtControllerPowerBudgetReclaimConfigFsmFail(1000974),
        fsmSamDmeComputePhysicalOobStorageAdminConfigFsmFail(1000975),
        fsmSamDmeEquipmentiocardBaseFePresenceFsmFail(1000980),
        fsmSamDmeEquipmentiocardBaseFeConnFsmFail(1000981),
        fsmSamDmeEquipmentLocatorLedSetDiskLocatorLedFsmFail(1000994),
        fsmSamDmeLstorageProcessorConfigureFsmFail(1001018),
        fsmSamDmeOsControllerDeployosFsmFail(1001024),
        fsmSamDmeEquipmentPsuUpdatepsuFsmFail(1001027),
        fsmSamDmeMgmtControllerUpdatecmcFsmFail(1001052),
        fsmSamDmeMgmtControllerActivatecmcFsmFail(1001053),
        fsmSamDmeMgmtControllerUpdateAdaptorFsmFail(1001054),
        fsmSamDmeMgmtControllerActivateAdaptorFsmFail(1001055),
        fsmSamDmeMgmtControllerUpdateRaidControllerFsmFail(1001056),
        fsmSamDmeMgmtControllerUpdateBoardControllerFsmFail(1001057),
        fsmSamDmeFabricCartridgeSlotEpIdentifyFsmFail(1001064),
        fsmSamDmeFabricComputemslotEpIdentifyFsmFail(1001065),
        fsmSamDmeEquipmentChassisOobStorageAdminCfgFsmFail(1001066),
        fsmSamDmeComputeServerUnitDiscoverFsmFail(1001072),
        fsmSamDmeMgmtIfFaPresenceFsmFail(1001073),
        fsmSamDmeMgmtIfFaConnFsmFail(1001074),
        fsmSamDmeEquipmentiocardEvacuateFsmFail(1001085),
        fsmSamDmeEquipmentiocardResetEvacuateFsmFail(1001086),
        fsmSamDmeComputePhysicalCleartpmFsmFail(1001091),
        fsmSamDmeEquipmentiocardResetPeerCmcFsmFail(1001142),
        fsmSamDmeSwExtUtilityConfPortBreakoutFsmFail(1001164),
        fsmSamDmeEquipmentSwitchiocardEvacuateFsmFail(1001186),
        fsmSamDmeEquipmentSwitchiocardResetEvacuateFsmFail(1001187),
        fsmSamDmeMorefImportRootApplyMoRefsFsmFail(1001201),
        fsmSamDmeStorageEnclosureRemoveEnclosureFsmFail(1001209),
        fsmSamDmeMgmtControllerPowerCapFsmFail(1001224),
        fsmSamDmeEquipmentSystemiocontrollerResetCmcFsmFail(1001225),
        fsmSamDmeComputePhysicalDiskZoningInventoryFsmFail(1001226),
        fsmSamDmeEquipmentChassisAssociateFsmFail(1001247),
        fsmSamDmeEquipmentChassisDisassociateFsmFail(1001248),
        fsmSamDmeEtherServerIntfioConfigFsmFail(1001277),
        fsmSamDmeMgmtControllerEnableSecureBootFsmFail(1001279),
        fsmSamDmeMgmtControllerUpdateColusacmcFsmFail(1001280),
        fsmSamDmeMgmtControllerActivateColusacmcFsmFail(1001281),
        fsmSamDmeEquipmentChassisChassisUpgradeFsmFail(1001282),
        fsmSamDmeMgmtControllerUpdateColusaBoardControllerFsmFail(1001283),
        fsmSamDmeMgmtControllerUpdateSasExpanderFsmFail(1001284),
        fsmSamDmeMgmtControllerActivateSasExpanderFsmFail(1001285),
        fsmSamDmeMgmtControllerActivateLocalDiskFsmFail(1001286),
        fsmSamDmeStorageLocalDiskUpdateLocalDiskFsmFail(1001287),
        fsmSamDmeMgmtControllerUpdateucsmanagerspFsmFail(1001299),
        fsmSamDmeComputePhysicalDiagFsmFail(1001300),
        fsmSamDmeComputePhysicalCimcSecurityConfigFsmFail(1001301),
        fsmSamDmeSwPortDiscoverDeployFsmFail(1001330),
        fsmSamDmePolicyPolicyScopeContReportPolicyFailFsmFsmFail(1001333),
        fsmSamDmePolicyRequestorResolveFromCentralFsmFail(1001334),
        fsmSamDmeFabricReservedVlanDeployFsmFail(1001376),
        fsmSamDmeEquipmentChassisFwUpgradeFsmFail(1001379),
        fsmSamDmeMgmtControllerKvmCertFsmFail(1001382),
        fsmSamDmeQosclassSlowDrainConfigQosslowDrainFsmFail(1001401),
        fsmSamDmeQosclassSlowDrainConfigQosslowDrainFexFsmFail(1001402),
        fsmSamDmeComputePhysicalExecuteActionsFsmFail(1001415),
        fsmSamDmeEquipmentChassisFanPolicyConfigFsmFail(1001416),
        fsmSamDmeComputePhysicalNvmeSwitchRecoveryFsmFail(1001417),
        fsmSamDmeMgmtControllerUpdateStorageServercmcFsmFail(1001419),
        fsmSamDmeMgmtControllerActivateStorageServercmcFsmFail(1001420),
        fsmSamDmeMgmtControllerUpgradeBoardControllerFsmFail(1001421),
        fsmSamDmeComputePhysicalReinitializeVirtualDriveFsmFail(1001435),
        fsmSamDmeEquipmentChassisPowerSavePolicyConfigFsmFail(1001444),
        fsmSamDmeFcpoolOuisDeployFsmFail(1001446),
        fsmSamDmeMgmtControllerUpdateSecurefpgaFsmFail(1001450),
        fsmSamDmePfcWatchDogConfigPfcWatchDogFsmFail(1001451),
        fsmSamDmeMgmtControllerConfigureSwPersonalitiesFsmFail(1001467),
        fsmSamDmeComputePhysicalConfigureServerPersonalityFsmFail(1001468),
        fsmSamDmeComputePhysicalBiosPasswordResetFsmFail(1001471),
        fsmSamDmeComputePhysicalCimcSecurityUnconfigFsmFail(1001472),
        fsmSamDmeEquipmentChassisPowerExtendedPolicyConfigFsmFail(1001496),
        fsmSamDmeComputePhysicalDataSanitizationFsmFail(1001518),
        fsmSamDmeSwrmonEpDeployrmonEpFsmFail(1001570),
        fsmSamDmeSecurityEncryptionEpUpdateEncryptionEpFsmFail(1001573),
        unrVnicTemplStatsPolicyName(4522530),
        unrVnicSanConnTemplQosPolicyName(4522532),
        unrVnicIpV4PooledAddrName(4522544),
        unrVnicVnicPinToGroupName(4522556),
        unrVnicVnicStatsPolicyName(4522561),
        unrVnicProfileQosPolicyName(4522588),
        unrVnicFcNodeIdentPoolName(4522603),
        unrLsServerSrcTemplName(4525234),
        unrLsServerIdentPoolName(4525239),
        unrLsServerBootPolicyName(4525240),
        unrLsServerLocalDiskPolicyName(4525241),
        unrLsServerScrubPolicyName(4525247),
        unrLsServerDynamicConPolicyName(4525248),
        unrLsServerHostFwPolicyName(4525250),
        unrLsServerMgmtFwPolicyName(4525251),
        unrLsServerMgmtAccessPolicyName(4525252),
        unrLsServerSolPolicyName(4525253),
        unrLsServerStatsPolicyName(4525254),
        unrVnicEtherBaseQosPolicyName(4526517),
        unrVnicEtherBaseNwCtrlPolicyName(4526850),
        unrVnicProfileNwCtrlPolicyName(4526851),
        unrLsServerVconProfileName(4526901),
        unrLsServerBiosProfileName(4526902),
        unrLsRequirementName(4527601),
        unrLsServerPowerPolicyName(4528591),
        unrLsServerMaintPolicyName(4528596),
        unrVnicSanConnTemplIdentPoolName(4528609),
        unrVnicLanConnTemplNwCtrlPolicyName(4528611),
        unrVnicLanConnTemplIdentPoolName(4528613),
        unrVnicFcBaseAdaptorProfileName(4528616),
        unrVnicFcBaseIdentPoolName(4528618),
        unrVnicFcBaseNwTemplName(4528620),
        unrVnicEtherBaseAdaptorProfileName(4528623),
        unrVnicEtherBaseIdentPoolName(4528625),
        unrVnicEtherBaseNwTemplName(4528627),
        unrVnicLanConnTemplQosPolicyName(4528680),
        unrVnicFcBaseQosPolicyName(4528682),
        unrTrigTriggerableScheduler(4528842),
        unrPolicySystemProfileDeviceProfileRef(4529259),
        unrFabricEthEstcEpNwCtrlPolicyName(4529444),
        unrFabricEthEstcPcNwCtrlPolicyName(4529447),
        unrFabricEthLanEpOperationEthLinkProfileName(4529479),
        unrVnicIscsiIdentPoolName(4529601),
        unrVnicIscsiAuthProfileName(4529604),
        unrVnicIscsiConfProfileName(4529606),
        unrVnicIscsiStaticTargetIfAuthProfileName(4529615),
        unrVnicIpv4PooledIscsiAddrIdentPoolName(4529838),
        unrVnicIscsiIqnIdentPoolName(4529847),
        unrVnicIscsiAdaptorProfileName(4529849),
        unrVnicFcBasePinToGroupName(4529971),
        unrVnicEtherBasePinToGroupName(4529973),
        unrFaultSuppressTaskSuppressPolicyName(4530050),
        unrVnicFcGroupTemplStorageConnPolicyName(4530085),
        unrVnicAgroupStatsPolicyName(4530100),
        unrVnicFcGroupDefStorageConnPolicyName(4530109),
        unrVnicIscsiBaseIdentPoolName(4530112),
        unrVnicIscsiBaseAdaptorProfileName(4530114),
        unrVnicDynamicConPolicyRefConPolicyName(4530117),
        unrVnicConnDefLanConnPolicyName(4530119),
        unrVnicConnDefSanConnPolicyName(4530121),
        unrFabricVlanMcastPolicyName(4530139),
        unrVnicIscsiBootVnicIqnIdentPoolName(4530389),
        unrVnicIscsiBootVnicAuthProfileName(4530391),
        unrLsServerExtippoolName(4530407),
        unrVnicIscsiNodeIqnIdentPoolName(4531275),
        unrFabricFcoeSanPcOperationLacpPolicyName(4531414),
        unrFabricFcoeSanPcEpOperationEthLinkProfileName(4531419),
        unrFabricEthLinkProfileUdldLinkPolicyName(4531446),
        unrFabricEthLinkProfileCdpLinkPolicyName(4531448),
        unrFabricFcoeSanEpOperationEthLinkProfileName(4531455),
        unrFabricFcoeSanEpEthLinkProfileName(4531458),
        unrVnicVmqConPolicyRefConPolicyName(4531468),
        unrVnicIpV4MgmtPooledAddrName(4531479),
        unrVnicIpV6MgmtPooledAddrName(4531484),
        unrVnicUsnicConPolicyRefConPolicyName(4531488),
        unrFabricEthEstcEpOperationNwCtrlPolicyName(4531519),
        unrFabricEthEstcPcOperationLacpPolicyName(4531529),
        unrFabricEthLanPcOperationLacpPolicyName(4531541),
        unrFabricEthLanPcEpOperationEthLinkProfileName(4531560),
        unrFabricEthLanEpEthLinkProfileName(4531567),
        unrFabricEthLanPcEpEthLinkProfileName(4531570),
        unrFabricFlowMonitorFlowMonRecordDef(4531624),
        unrFabricFlowMonitorFlowTimeoutPolicy(4531626),
        unrFabricNetflowMonitorRefNfMonitorName(4531631),
        unrFabricFlowMonExporterFlowExpProfile(4531652),
        unrFabricNetflowMonExporterRefNfMonExporterName(4531666),
        unrFabricFcoeSanPcEpEthLinkProfileName(4531672),
        unrExtvmmVmnetworkDefinitionExtIpPoolName(4531907),
        unrExtvmmVmnetworkFabricNetworkName(4531914),
        unrExtvmmVmndrefVmNetworkDefName(4531918),
        unrExtvmmFndreferenceFnDefName(4531923),
        unrLsServerVmediaPolicyName(4532135),
        unrLsServerKvmMgmtPolicyName(4532137),
        unrFabricEthLanPcLacpPolicyName(4532169),
        unrFabricFcoeSanPcLacpPolicyName(4532171),
        unrFabricEthEstcPcLacpPolicyName(4532175),
        unrEquipmentChassisProfileSrcTemplName(4532517),
        unrEquipmentChassisProfileChassisFwPolicyName(4532527),
        unrEquipmentChassisProfileMaintPolicyName(4532531),
        unrEquipmentChassisProfileDiskZoningPolicyName(4532533),
        unrEquipmentRequirementName(4532550),
        unrStorageAscsiLunVolumeName(4532685),
        unrStorageIpV4PooledAddrIdentPoolName(4532844),
        unrVnicEthConfigNwCtrlPolicyName(4532850),
        unrVnicEthConfigStatsPolicyName(4532852),
        unrVnicEthConfigMacPoolName(4532854),
        unrVnicEthConfigAdaptorProfileName(4532856),
        unrVnicIscsiConfigIpPoolName(4532859),
        unrVnicIscsiConfigIpPoolNameFabricb(4532861),
        unrVnicIscsiConfigIqnPoolName(4532863),
        unrVnicIscsiConfigAdaptorProfileName(4532865),
        unrVnicIscsiNodeInitiatorPolicyName(4532871),
        unrLstorageArrayAutoconfigPolicySrcTemplName(4532898),
        unrLstorageArrayAutoconfigPolicyQualifier(4532900),
        unrLstorageArraySrcTemplName(4532906),
        unrLstorageArrayHostFwPolicyName(4532915),
        unrLstorageArrayStorageFwPolicyName(4532917),
        unrLstorageArrayStatsPolicyName(4532919),
        unrLstorageArrayMaintPolicyName(4532921),
        unrLstorageProcessorSvcPolicyName(4532925),
        unrLstorageProcessorExtippoolName(4532935),
        unrLstorageQualifiedPolicyQualifier(4532954),
        unrLstorageLunSnapshotPolicyScheduleName(4532969),
        unrLstorageProfileBindingBaseStorageProfileName(4532988),
        unrLstorageSanScsiLunReplicationPolicyName(4533006),
        unrLstorageSanScsiLunSnapshotPolicyName(4533008),
        unrLstorageDasScsiLunLocalDiskPolicyName(4533010),
        unrLstorageBackstoreRequirementName(4533059),
        unrLstorageBackstoreRequirementQualifier(4533061),
        unrVnicStorageEthLifVlanName(4533226),
        unrComputeAutoconfigPolicyQualifier(4533245),
        unrComputeBladeInheritPolicyQualifier(4533247),
        unrDomainProfileSrcTemplName(4533371),
        unrDomainProfilePortDiscPolicyName(4533374),
        unrDomainProfileHwChangeDiscPolicyName(4533376),
        unrDomainProfileInbandPolicyName(4533378),
        unrDomainProfileKmipCertificatePolicyName(4533380),
        unrDomainProfileQosclassDefinitionName(4533382),
        unrFdPhysicalKmipCertificatePolicyName(4533589),
        unrVnicSanConnTemplPeerRedundancyTemplName(4534475),
        unrVnicLanConnTemplPeerRedundancyTemplName(4534477),
        unrLsServerPowerSyncPolicyName(4534557),
        unrEquipmentAutoconfigPolicyQualifier(4534831),
        unrEquipmentChassisInheritPolicyQualifier(4534833),
        unrFabricNetGroupRefName(4535084),
        unrFabricSanGroupRefName(4535086),
        unrLsServerGraphicsCardPolicyName(4535111),
        unrEquipmentChassisProfileComputeConnPolicyName(4535173),
        unrMoIpAddrKvPoolName(4535189),
        unrEquipmentChassisProfileSasExpanderConfigPolicyName(4535591),
        unrLsServerPersistentMemoryPolicyName(4535844),
        unrLsServerSpdmCertificatePolicyName(4536369),
        unrVnicSriovHpnConPolicyRefConPolicyName(4536436),
        unrFabricMacSecIfConfigMacSecKeyChainName(4536885),
        unrFabricMacSecIfConfigMacSecPolicyName(4536887),
        unrFabricMacSecIfConfigMacSecFallbackKeyChainName(4536889),
        unrFabricMacSecIfConfigMacSecEapolName(4536891),
        unrFabricAbsEthLanEpMacSecIfConfigName(4536897),
        unrVnicIpv6PooledIscsiAddrIdentPoolName(4537109),
        unrVnicAbsiscsiStaticTargetIfAuthProfileName(4537115)
    }

CucsConditionSeverity ::= TEXTUAL-CONVENTION
    STATUS        current
    DESCRIPTION
        ""
    SYNTAX        INTEGER
    {
        cleared(0),
        info(1),
        condition(2),
        warning(3),
        minor(4),
        major(5),
        critical(6)
    }

CucsConditionSmartCallHomeCause ::= TEXTUAL-CONVENTION
    STATUS        current
    DESCRIPTION
        ""
    SYNTAX        INTEGER
    {
        unspecified(0),
        providerLostConnectivity(1),
        controllerLostConnectivity(2),
        clientLostConnectivity(3),
        dbConnectReadWriteError(4),
        capacityExceeded(5),
        invalidTrustpointCertChain(6),
        invalidKeyringCertificate(7),
        duplicatedAssigned(8),
        remoteFailed(9),
        notInCompliance(10),
        coreFileGenerated(11)
    }

CucsConditionTag ::= TEXTUAL-CONVENTION
    STATUS        current
    DESCRIPTION
        ""
    SYNTAX        BITS
    {
        server(0),
        network(1),
        storage(2),
        pod(3),
        security(4),
        operations(5),
        fsmstagefail(6),
        fsmstageretry(7),
        fsmstageremoteinv(8)
    }

CucsConditionType ::= TEXTUAL-CONVENTION
    STATUS        current
    DESCRIPTION
        ""
    SYNTAX        INTEGER
    {
        generic(0),
        policy(1),
        storage(2),
        equipment(3),
        network(4),
        server(5),
        configuration(6),
        environmental(7),
        connectivity(8),
        sysdebug(9),
        operational(10),
        snmpUserNotDeployed(11),
        profileConfigQualifier(12),
        unmanageableHardware(13),
        callhome(17),
        any(65535)
    }

CucsConfigAbsDbConfigType ::= TEXTUAL-CONVENTION
    STATUS        current
    DESCRIPTION
        ""
    SYNTAX        INTEGER
    {
        unknown(0),
        postgres(1),
        oracle(2),
        mssql(3)
    }

CucsConfigBackupAdminState ::= TEXTUAL-CONVENTION
    STATUS        current
    DESCRIPTION
        ""
    SYNTAX        INTEGER
    {
        active(0),
        delete(1)
    }

CucsConfigBackupFsmCurrentFsm ::= TEXTUAL-CONVENTION
    STATUS        current
    DESCRIPTION
        ""
    SYNTAX        INTEGER
    {
        nop(0),
        delete(183)
    }

CucsConfigBackupFsmStageName ::= TEXTUAL-CONVENTION
    STATUS        current
    DESCRIPTION
        ""
    SYNTAX        INTEGER
    {
        nop(0),
        deleteBegin(183),
        deleteLocal(184),
        deleteFail(198),
        deleteSuccess(199)
    }

CucsConfigBackupFsmTaskItem ::= TEXTUAL-CONVENTION
    STATUS        current
    DESCRIPTION
        ""
    SYNTAX        INTEGER
    {
        nop(0),
        delete(183)
    }

CucsConfigComponentType ::= TEXTUAL-CONVENTION
    STATUS        current
    DESCRIPTION
        ""
    SYNTAX        INTEGER
    {
        adaptors(0),
        cartridges(1),
        cpus(2),
        controllers(3),
        cryptoCards(4),
        fans(5),
        graphicsCards(6),
        ioms(7),
        localDisks(8),
        luns(9),
        ports(10),
        psus(11),
        memory(12),
        motherboards(13)
    }

CucsConfigConfigSyncState ::= TEXTUAL-CONVENTION
    STATUS        current
    DESCRIPTION
        ""
    SYNTAX        INTEGER
    {
        unsynched(1),
        synched(2)
    }

CucsConfigConsumerCatalogueFsmCurrentFsm ::= TEXTUAL-CONVENTION
    STATUS        current
    DESCRIPTION
        ""
    SYNTAX        INTEGER
    {
        nop(0),
        delete(181),
        create(332)
    }

CucsConfigConsumerCatalogueFsmStageName ::= TEXTUAL-CONVENTION
    STATUS        current
    DESCRIPTION
        ""
    SYNTAX        INTEGER
    {
        nop(0),
        deleteBegin(181),
        deleteLocal(182),
        deleteFail(200),
        deleteSuccess(201),
        createBegin(332),
        createMakeCfgDirs(333),
        createFail(342),
        createSuccess(343)
    }

CucsConfigConsumerCatalogueFsmTaskItem ::= TEXTUAL-CONVENTION
    STATUS        current
    DESCRIPTION
        ""
    SYNTAX        INTEGER
    {
        nop(0),
        delete(181),
        create(332)
    }

CucsConfigDisruptionType ::= TEXTUAL-CONVENTION
    STATUS        current
    DESCRIPTION
        ""
    SYNTAX        INTEGER
    {
        host(0),
        fabricInterconnect(1),
        firmwareInfra(2)
    }

CucsConfigEquipmentType ::= TEXTUAL-CONVENTION
    STATUS        current
    DESCRIPTION
        ""
    SYNTAX        INTEGER
    {
        chassis(0),
        fabricInterconnect(1),
        fex(2),
        server(3)
    }

CucsConfigEstimateImpactState ::= TEXTUAL-CONVENTION
    STATUS        current
    DESCRIPTION
        ""
    SYNTAX        INTEGER
    {
        notStarted(0),
        wating(1),
        complete(2),
        timedOut(3)
    }

CucsConfigFiRebootReason ::= TEXTUAL-CONVENTION
    STATUS        current
    DESCRIPTION
        ""
    SYNTAX        BITS
    {
        maintenanceTag(0),
        qosSettings(1),
        fcMode(2),
        ethMode(3)
    }

CucsConfigImpactAnalyzerContext ::= TEXTUAL-CONVENTION
    STATUS        current
    DESCRIPTION
        ""
    SYNTAX        INTEGER
    {
        dme(0),
        import(1)
    }

CucsConfigImpactAnalyzerMode ::= TEXTUAL-CONVENTION
    STATUS        current
    DESCRIPTION
        ""
    SYNTAX        INTEGER
    {
        straight(0),
        relay(1)
    }

CucsConfigImpactAnalyzerProfileType ::= TEXTUAL-CONVENTION
    STATUS        current
    DESCRIPTION
        ""
    SYNTAX        INTEGER
    {
        serviceProfile(0),
        chassisProfile(1)
    }

CucsConfigImpactResponseState ::= TEXTUAL-CONVENTION
    STATUS        current
    DESCRIPTION
        ""
    SYNTAX        INTEGER
    {
        notStarted(0),
        waiting(1),
        complete(2),
        timedOut(3),
        suspend(4),
        lostVisibility(5)
    }

CucsConfigInstType ::= TEXTUAL-CONVENTION
    STATUS        current
    DESCRIPTION
        ""
    SYNTAX        INTEGER
    {
        unknow(0),
        sp(1),
        cp(2)
    }

CucsConfigIssues ::= TEXTUAL-CONVENTION
    STATUS        current
    DESCRIPTION
        ""
    SYNTAX        BITS
    {
        remoteFailed(0)
    }

CucsConfigNetRefType ::= TEXTUAL-CONVENTION
    STATUS        current
    DESCRIPTION
        ""
    SYNTAX        INTEGER
    {
        all(0),
        classic(1),
        aci(2)
    }

CucsConfigObjectType ::= TEXTUAL-CONVENTION
    STATUS        current
    DESCRIPTION
        ""
    SYNTAX        Counter64

CucsConfigOperState ::= TEXTUAL-CONVENTION
    STATUS        current
    DESCRIPTION
        ""
    SYNTAX        INTEGER
    {
        none(0),
        cleaning(1),
        provisioning(2),
        userCleaning(3)
    }

CucsConfigProfileType ::= TEXTUAL-CONVENTION
    STATUS        current
    DESCRIPTION
        ""
    SYNTAX        INTEGER
    {
        all(0),
        local(1),
        global(2)
    }

CucsConfigSPType ::= TEXTUAL-CONVENTION
    STATUS        current
    DESCRIPTION
        ""
    SYNTAX        INTEGER
    {
        all(0),
        local(1),
        global(2)
    }

CucsConfigSearchType ::= TEXTUAL-CONVENTION
    STATUS        current
    DESCRIPTION
        ""
    SYNTAX        INTEGER
    {
        contains(0),
        startsWith(1),
        exactMatch(2)
    }

CucsConfigSorterDirection ::= TEXTUAL-CONVENTION
    STATUS        current
    DESCRIPTION
        ""
    SYNTAX        INTEGER
    {
        ascending(0),
        descending(1)
    }

CucsConfigStorageType ::= TEXTUAL-CONVENTION
    STATUS        current
    DESCRIPTION
        ""
    SYNTAX        INTEGER
    {
        cartridge(0),
        storageBlade(1)
    }

CucsConsumerAdminState ::= TEXTUAL-CONVENTION
    STATUS        current
    DESCRIPTION
        ""
    SYNTAX        INTEGER
    {
        managed(1),
        unmanaged(2)
    }

CucsConsumerInstFsmCurrentFsm ::= TEXTUAL-CONVENTION
    STATUS        current
    DESCRIPTION
        ""
    SYNTAX        INTEGER
    {
        nop(0),
        renameCfgDir(185)
    }

CucsConsumerInstFsmStageName ::= TEXTUAL-CONVENTION
    STATUS        current
    DESCRIPTION
        ""
    SYNTAX        INTEGER
    {
        nop(0),
        renameCfgDirBegin(185),
        renameCfgDirFail(202),
        renameCfgDirSuccess(203),
        renameCfgDirMoveCfgDirsToTmpLocation(334),
        renameCfgDirMoveCfgDirsFromTmpLocation(335)
    }

CucsConsumerInstFsmTaskItem ::= TEXTUAL-CONVENTION
    STATUS        current
    DESCRIPTION
        ""
    SYNTAX        INTEGER
    {
        nop(0),
        renameCfgDir(185)
    }

CucsConsumerOperState ::= TEXTUAL-CONVENTION
    STATUS        current
    DESCRIPTION
        ""
    SYNTAX        INTEGER
    {
        ok(1),
        resetting(2),
        provisioning(3)
    }

CucsControllerEpFsmCurrentFsm ::= TEXTUAL-CONVENTION
    STATUS        current
    DESCRIPTION
        ""
    SYNTAX        INTEGER
    {
        nop(0),
        quiesce(315)
    }

CucsControllerEpFsmStageName ::= TEXTUAL-CONVENTION
    STATUS        current
    DESCRIPTION
        ""
    SYNTAX        INTEGER
    {
        nop(0),
        quiesceBegin(315),
        quiesceQuiesceMgmtController(316),
        quiesceQuiesceResMgr(317),
        quiesceQuiesceOpsMgr(318),
        quiesceQuiescePolicyMgr(319),
        quiesceQuiesceIDMgr(320),
        quiesceQuiesceStatsMgr(321),
        quiesceFail(322),
        quiesceSuccess(323)
    }

CucsControllerEpFsmTaskItem ::= TEXTUAL-CONVENTION
    STATUS        current
    DESCRIPTION
        ""
    SYNTAX        INTEGER
    {
        nop(0),
        quiesce(315)
    }

CucsCpmaintAckChangeDetails ::= TEXTUAL-CONVENTION
    STATUS        current
    DESCRIPTION
        ""
    SYNTAX        BITS
    {
        binding(0),
        hostVirtEthIf(1),
        storageControllerFw(2),
        hostEthIfProfile(3),
        hostEthIfQos(4),
        hostEthIfNwCtrl(5),
        mgmtControllerFw(6),
        hostNonvirtFcIf(7),
        localDiskFw(8),
        hostNonvirtFcIfPersBind(9),
        sasExpanderFw(10),
        implicitReboot(11),
        hostFcoeIf(12),
        vif(13),
        vlan(14),
        vsan(15),
        ip(16),
        bootOrder(17),
        bootVirtVnic(18),
        bootNonvirtVnic(19),
        bootLocalStorage(20),
        bootVirtPxe(21),
        bootNonvirtPxe(22),
        bladeIdentity(24),
        agentPolicy(25),
        localDiskPolicy(31),
        pin(32),
        sol(33),
        epAuth(34),
        biosProfile(35),
        checkpoint(36),
        implicitHostFcIfProfileRedeploy(38),
        hostEthIfQosHostControl(40),
        implicitHostEthIfProfileRedeploy(42),
        storagePath(43),
        hostIfPcie(45),
        flexflashConfig(46),
        bootmodeConfig(48),
        securebootConfig(49),
        vmediaConfig(50),
        powercapConfig(51),
        oobLocalStorageConfig(52),
        remoteStorageConfig(53),
        storageSnicConfig(56),
        fanSpeedConfig(57),
        retimerFw(58),
        ubmFw(59),
        pciSwitchFw(60),
        localDiskDataLoss(61),
        localStorageSecurity(62),
        nvmeMswitchFw(63)
    }

CucsCpmaintAckChanges ::= TEXTUAL-CONVENTION
    STATUS        current
    DESCRIPTION
        ""
    SYNTAX        BITS
    {
        serverIdentity(0),
        networking(2),
        vnicVhbaPlacement(3),
        bootOrder(4),
        serverAssignment(5),
        localStorage(7),
        chassisIdentity(22),
        storage(24),
        chassisAssignment(25),
        operationalPolicies(26)
    }

CucsCpmaintAckDisr ::= TEXTUAL-CONVENTION
    STATUS        current
    DESCRIPTION
        ""
    SYNTAX        BITS
    {
        upTime(0),
        acPowerCycle(1),
        localStorageConfigDeploymentUserack(2),
        localStorageConfigDeploymentImmediate(3)
    }

CucsCpmaintChangeMode ::= TEXTUAL-CONVENTION
    STATUS        current
    DESCRIPTION
        ""
    SYNTAX        INTEGER
    {
        noChange(0),
        unconfig(1),
        forceUnconfig(2),
        rediscover(4),
        config(8),
        diagConfig(16),
        diagUnconfig(32),
        removeConfig(64),
        diag(128)
    }

CucsDcxAdminState ::= TEXTUAL-CONVENTION
    STATUS        current
    DESCRIPTION
        ""
    SYNTAX        INTEGER
    {
        enabled(0),
        disabled(1)
    }

CucsDcxNsAllocStatus ::= TEXTUAL-CONVENTION
    STATUS        current
    DESCRIPTION
        ""
    SYNTAX        INTEGER
    {
        available(0),
        full(1),
        exceeded(2)
    }

CucsDcxOperState ::= TEXTUAL-CONVENTION
    STATUS        current
    DESCRIPTION
        ""
    SYNTAX        INTEGER
    {
        unknown(0),
        adminDown(1),
        linkDown(2),
        error(3),
        active(4),
        passive(5)
    }

CucsDcxProtState ::= TEXTUAL-CONVENTION
    STATUS        current
    DESCRIPTION
        ""
    SYNTAX        INTEGER
    {
        noProtection(0),
        active(1),
        passive(2)
    }

CucsDcxState ::= TEXTUAL-CONVENTION
    STATUS        current
    DESCRIPTION
        ""
    SYNTAX        INTEGER
    {
        unknown(0),
        present(1),
        creating(2),
        modifying(3),
        destroying(4),
        createPend(5),
        modifyPend(6),
        destroyPend(7)
    }

CucsDcxStaticMacLimitStatus ::= TEXTUAL-CONVENTION
    STATUS        current
    DESCRIPTION
        ""
    SYNTAX        INTEGER
    {
        available(0),
        reached(1)
    }

CucsDcxVIfProtRole ::= TEXTUAL-CONVENTION
    STATUS        current
    DESCRIPTION
        ""
    SYNTAX        INTEGER
    {
        unprotected(0),
        primary(1),
        backup(2)
    }

CucsDiagAdminState ::= TEXTUAL-CONVENTION
    STATUS        current
    DESCRIPTION
        ""
    SYNTAX        INTEGER
    {
        ready(0),
        trigger(1),
        cancel(2)
    }

CucsDiagBladeTestType ::= TEXTUAL-CONVENTION
    STATUS        current
    DESCRIPTION
        ""
    SYNTAX        INTEGER
    {
        disk(0),
        processor(1),
        memory(2),
        memtest(3),
        stress(4),
        pci(5)
    }

CucsDiagCpuFilter ::= TEXTUAL-CONVENTION
    STATUS        current
    DESCRIPTION
        ""
    SYNTAX        INTEGER
    {
        p0P1Cpus(0),
        allCpus(1)
    }

CucsDiagFailureAction ::= TEXTUAL-CONVENTION
    STATUS        current
    DESCRIPTION
        ""
    SYNTAX        BITS
    {
        techSupport(0),
        waitDebug(1),
        skipRemaining(2)
    }

CucsDiagMemChunkSize ::= TEXTUAL-CONVENTION
    STATUS        current
    DESCRIPTION
        ""
    SYNTAX        INTEGER
    {
        bigChunk(0),
        n5mbChunk(1)
    }

CucsDiagNetworkTestType ::= TEXTUAL-CONVENTION
    STATUS        current
    DESCRIPTION
        ""
    SYNTAX        INTEGER
    {
        eth(0),
        fc(1)
    }

CucsDiagPattern ::= TEXTUAL-CONVENTION
    STATUS        current
    DESCRIPTION
        ""
    SYNTAX        INTEGER
    {
        prbsKiller(0),
        butterfly(1),
        prbs(2),
        killer(3),
        prbsAddr(4)
    }

CucsDiagSrvCtrlType ::= TEXTUAL-CONVENTION
    STATUS        current
    DESCRIPTION
        ""
    SYNTAX        INTEGER
    {
        full(1),
        efi(33)
    }

CucsDiagSrvCtrlOperationFsmCurrentFsm ::= TEXTUAL-CONVENTION
    STATUS        current
    DESCRIPTION
        ""
    SYNTAX        INTEGER
    {
        nop(0),
        configure(612)
    }

CucsDiagSrvCtrlOperationFsmStageName ::= TEXTUAL-CONVENTION
    STATUS        current
    DESCRIPTION
        ""
    SYNTAX        INTEGER
    {
        nop(0),
        configureBegin(612),
        configureRunPolicyResolve(613),
        configureWaitForRunPolicyResolved(614),
        configureTriggerOperation(615),
        configureFail(652),
        configureSuccess(653)
    }

CucsDiagSrvCtrlOperationFsmTaskItem ::= TEXTUAL-CONVENTION
    STATUS        current
    DESCRIPTION
        ""
    SYNTAX        INTEGER
    {
        nop(0),
        configure(612)
    }

CucsDiagStatus ::= TEXTUAL-CONVENTION
    STATUS        current
    DESCRIPTION
        ""
    SYNTAX        INTEGER
    {
        unknown(0),
        inProgress(1),
        failed(2),
        notRun(3),
        cancelled(4),
        scheduled(5)
    }

CucsDiagStatusIssues ::= TEXTUAL-CONVENTION
    STATUS        current
    DESCRIPTION
        ""
    SYNTAX        BITS
    {
        testFailure(0),
        runCancelled(1),
        componentError(2),
        stagesCompleted(3),
        stageFailed(4)
    }

CucsDiagSuccessAction ::= TEXTUAL-CONVENTION
    STATUS        current
    DESCRIPTION
        ""
    SYNTAX        BITS
    {
        techSupport(0),
        waitDebug(1)
    }

CucsDiagTestOrder ::= TEXTUAL-CONVENTION
    STATUS        current
    DESCRIPTION
        ""
    SYNTAX        Gauge32 (1..64)

CucsDiagTestType ::= TEXTUAL-CONVENTION
    STATUS        current
    DESCRIPTION
        ""
    SYNTAX        INTEGER
    {
        disk(0),
        processor(1),
        pmem2(2),
        memtest(3),
        stress(4),
        pci(5)
    }

CucsDomainFeatureType ::= TEXTUAL-CONVENTION
    STATUS        current
    DESCRIPTION
        ""
    SYNTAX        INTEGER
    {
        major(0),
        minor(1)
    }

CucsDomainFunctionalState ::= TEXTUAL-CONVENTION
    STATUS        current
    DESCRIPTION
        ""
    SYNTAX        INTEGER
    {
        enabled(0),
        disabled(1)
    }

CucsDomainProductFamily ::= TEXTUAL-CONVENTION
    STATUS        current
    DESCRIPTION
        ""
    SYNTAX        INTEGER
    {
        ucsClassic(0),
        ucsMini(1),
        ucsClassic3gen(2)
    }

CucsDomainProfileFsmCurrentFsm ::= TEXTUAL-CONVENTION
    STATUS        current
    DESCRIPTION
        ""
    SYNTAX        INTEGER
    {
        nop(0),
        configure(635)
    }

CucsDomainProfileFsmStageName ::= TEXTUAL-CONVENTION
    STATUS        current
    DESCRIPTION
        ""
    SYNTAX        INTEGER
    {
        nop(0),
        configureBegin(635),
        configureConsumerVxanDeployment(636),
        configureWaitForConsumerReceivingVxan(637),
        configurePushPolicies(638),
        configureConfigure(639),
        configureFail(654),
        configureSuccess(655)
    }

CucsDomainProfileFsmTaskItem ::= TEXTUAL-CONVENTION
    STATUS        current
    DESCRIPTION
        ""
    SYNTAX        INTEGER
    {
        nop(0),
        configure(635)
    }

CucsDomainType ::= TEXTUAL-CONVENTION
    STATUS        current
    DESCRIPTION
        ""
    SYNTAX        INTEGER
    {
        instance(0),
        initialTemplate(1),
        updatingTemplate(2)
    }

CucsDpsecForgedTransmit ::= TEXTUAL-CONVENTION
    STATUS        current
    DESCRIPTION
        ""
    SYNTAX        INTEGER
    {
        allow(0),
        deny(1)
    }

CucsDupeChangeTrackerEpFsmCurrentFsm ::= TEXTUAL-CONVENTION
    STATUS        current
    DESCRIPTION
        ""
    SYNTAX        INTEGER
    {
        nop(0),
        configure(395)
    }

CucsDupeChangeTrackerEpFsmStageName ::= TEXTUAL-CONVENTION
    STATUS        current
    DESCRIPTION
        ""
    SYNTAX        INTEGER
    {
        nop(0),
        configureBegin(395),
        configureSendChange(396),
        configureFail(397),
        configureSuccess(398)
    }

CucsDupeChangeTrackerEpFsmTaskItem ::= TEXTUAL-CONVENTION
    STATUS        current
    DESCRIPTION
        ""
    SYNTAX        INTEGER
    {
        nop(0),
        configure(395)
    }

CucsDupeOperation ::= TEXTUAL-CONVENTION
    STATUS        current
    DESCRIPTION
        ""
    SYNTAX        INTEGER
    {
        create(0),
        delete(1)
    }

CucsDupeStatus ::= TEXTUAL-CONVENTION
    STATUS        current
    DESCRIPTION
        ""
    SYNTAX        INTEGER
    {
        failure(0),
        success(1)
    }

CucsEpqosDefinitionDelTaskFsmCurrentFsm ::= TEXTUAL-CONVENTION
    STATUS        current
    DESCRIPTION
        ""
    SYNTAX        INTEGER
    {
        nop(0),
        remove(319)
    }

CucsEpqosDefinitionDelTaskFsmStageName ::= TEXTUAL-CONVENTION
    STATUS        current
    DESCRIPTION
        ""
    SYNTAX        INTEGER
    {
        nop(0),
        removeBegin(319),
        removeLocal(320),
        removePeer(321),
        removeFail(370),
        removeSuccess(371)
    }

CucsEpqosDefinitionDelTaskFsmTaskItem ::= TEXTUAL-CONVENTION
    STATUS        current
    DESCRIPTION
        ""
    SYNTAX        INTEGER
    {
        nop(0),
        remove(319)
    }

CucsEpqosDefinitionFsmCurrentFsm ::= TEXTUAL-CONVENTION
    STATUS        current
    DESCRIPTION
        ""
    SYNTAX        INTEGER
    {
        nop(0),
        deploy(316)
    }

CucsEpqosDefinitionFsmStageName ::= TEXTUAL-CONVENTION
    STATUS        current
    DESCRIPTION
        ""
    SYNTAX        INTEGER
    {
        nop(0),
        deployBegin(316),
        deployLocal(317),
        deployPeer(318),
        deployFail(372),
        deploySuccess(373)
    }

CucsEpqosDefinitionFsmTaskItem ::= TEXTUAL-CONVENTION
    STATUS        current
    DESCRIPTION
        ""
    SYNTAX        INTEGER
    {
        nop(0),
        deploy(316)
    }

CucsEquipmentActiveStatus ::= TEXTUAL-CONVENTION
    STATUS        current
    DESCRIPTION
        ""
    SYNTAX        INTEGER
    {
        unknown(0),
        activated(1),
        deactivated(2)
    }

CucsEquipmentAdminActionType ::= TEXTUAL-CONVENTION
    STATUS        current
    DESCRIPTION
        ""
    SYNTAX        INTEGER
    {
        unspecified(0),
        clearConfig(1)
    }

CucsEquipmentAdminPowerState ::= TEXTUAL-CONVENTION
    STATUS        current
    DESCRIPTION
        ""
    SYNTAX        INTEGER
    {
        policy(1),
        cycleImmediate(2),
        cycleWait(3)
    }

CucsEquipmentAirflowDirection ::= TEXTUAL-CONVENTION
    STATUS        current
    DESCRIPTION
        ""
    SYNTAX        INTEGER
    {
        unknown(0),
        frontToBack(1),
        backToFront(2)
    }

CucsEquipmentApply ::= TEXTUAL-CONVENTION
    STATUS        current
    DESCRIPTION
        ""
    SYNTAX        INTEGER
    {
        onAssociation(1),
        runTime(2)
    }

CucsEquipmentAsicType ::= TEXTUAL-CONVENTION
    STATUS        current
    DESCRIPTION
        ""
    SYNTAX        INTEGER
    {
        unknown(0),
        gatos(1),
        carmel(2),
        trident2(3),
        homewood(4),
        heavenly(5),
        ararat(6)
    }

CucsEquipmentAssignment ::= TEXTUAL-CONVENTION
    STATUS        current
    DESCRIPTION
        ""
    SYNTAX        INTEGER
    {
        unassigned(0),
        assigned(1),
        failed(2)
    }

CucsEquipmentAssociation ::= TEXTUAL-CONVENTION
    STATUS        current
    DESCRIPTION
        ""
    SYNTAX        INTEGER
    {
        none(0),
        establishing(1),
        associated(2),
        removing(3),
        failed(4),
        throttled(5)
    }

CucsEquipmentAvailability ::= TEXTUAL-CONVENTION
    STATUS        current
    DESCRIPTION
        ""
    SYNTAX        INTEGER
    {
        unavailable(0),
        available(1)
    }

CucsEquipmentBatteryCapacity ::= TEXTUAL-CONVENTION
    STATUS        current
    DESCRIPTION
        ""
    SYNTAX        INTEGER
    {
        unknown(0),
        ready(1),
        insufficientCharge(2),
        identify(3)
    }

CucsEquipmentBeaconLedFsmCurrentFsm ::= TEXTUAL-CONVENTION
    STATUS        current
    DESCRIPTION
        ""
    SYNTAX        INTEGER
    {
        nop(0),
        illuminate(1135)
    }

CucsEquipmentBeaconLedFsmStageName ::= TEXTUAL-CONVENTION
    STATUS        current
    DESCRIPTION
        ""
    SYNTAX        INTEGER
    {
        nop(0),
        illuminateBegin(1135),
        illuminateExecuteA(1136),
        illuminateExecuteB(1137),
        illuminateFail(1138),
        illuminateSuccess(1139)
    }

CucsEquipmentBeaconLedFsmTaskItem ::= TEXTUAL-CONVENTION
    STATUS        current
    DESCRIPTION
        ""
    SYNTAX        INTEGER
    {
        nop(0),
        illuminate(1089)
    }

CucsEquipmentBeaconLedState ::= TEXTUAL-CONVENTION
    STATUS        current
    DESCRIPTION
        ""
    SYNTAX        INTEGER
    {
        on(1),
        off(2),
        blinking(3),
        eth(4),
        fc(5)
    }

CucsEquipmentBiosTokenType ::= TEXTUAL-CONVENTION
    STATUS        current
    DESCRIPTION
        ""
    SYNTAX        INTEGER
    {
        none(0),
        optionRom(1),
        memoryMappedAbove4gb(2),
        biosVftpm(3),
        psata(4)
    }

CucsEquipmentBiosUpdateMethod ::= TEXTUAL-CONVENTION
    STATUS        current
    DESCRIPTION
        ""
    SYNTAX        INTEGER
    {
        unknown(0),
        managementController(1),
        pnuos(2)
    }

CucsEquipmentBoardAggregationRole ::= TEXTUAL-CONVENTION
    STATUS        current
    DESCRIPTION
        ""
    SYNTAX        INTEGER
    {
        none(0),
        single(1),
        multiMaster(2),
        multiSlave(3)
    }

CucsEquipmentBoardConnectorType ::= TEXTUAL-CONVENTION
    STATUS        current
    DESCRIPTION
        ""
    SYNTAX        INTEGER
    {
        connUnlinked(1),
        connLinked(2)
    }

CucsEquipmentBootDeviceType ::= TEXTUAL-CONVENTION
    STATUS        current
    DESCRIPTION
        ""
    SYNTAX        INTEGER
    {
        localLunAny(0),
        localStorageAny(1)
    }

CucsEquipmentCPMetaCpRefresh ::= TEXTUAL-CONVENTION
    STATUS        current
    DESCRIPTION
        ""
    SYNTAX        INTEGER
    {
        enabled(1),
        disabled(2)
    }

CucsEquipmentCPMetaOperationCodeClearance ::= TEXTUAL-CONVENTION
    STATUS        current
    DESCRIPTION
        ""
    SYNTAX        INTEGER
    {
        enabled(1),
        disabled(2)
    }

CucsEquipmentCPNeedIdReEvaluate ::= TEXTUAL-CONVENTION
    STATUS        current
    DESCRIPTION
        ""
    SYNTAX        INTEGER
    {
        no(0),
        yes(1)
    }

CucsEquipmentCPOperationType ::= TEXTUAL-CONVENTION
    STATUS        current
    DESCRIPTION
        ""
    SYNTAX        INTEGER
    {
        noOp(0),
        rename(1),
        associate(2),
        disassociate(3),
        deletion(4)
    }

CucsEquipmentCPOwnershipLC ::= TEXTUAL-CONVENTION
    STATUS        current
    DESCRIPTION
        ""
    SYNTAX        INTEGER
    {
        globalControlled(0),
        disassocPending(1),
        deletePending(2),
        localized(3)
    }

CucsEquipmentChassisFanSpeedConfigState ::= TEXTUAL-CONVENTION
    STATUS        current
    DESCRIPTION
        ""
    SYNTAX        INTEGER
    {
        balanced(0),
        lowPower(1),
        performance(2),
        highPower(3),
        maxPower(4),
        acoustic(5)
    }

CucsEquipmentChassisId ::= TEXTUAL-CONVENTION
    STATUS        current
    DESCRIPTION
        ""
    SYNTAX        Gauge32 (1..255)

CucsEquipmentChassisAdminState ::= TEXTUAL-CONVENTION
    STATUS        current
    DESCRIPTION
        ""
    SYNTAX        INTEGER
    {
        acknowledged(1),
        reAcknowledge(2),
        decommission(3),
        remove(4),
        enablePortChannel(5),
        disablePortChannel(6),
        autoAcknowledge(7)
    }

CucsEquipmentChassisAssocState ::= TEXTUAL-CONVENTION
    STATUS        current
    DESCRIPTION
        ""
    SYNTAX        INTEGER
    {
        unassociated(0),
        associating(1),
        associated(2),
        disassociating(3),
        failed(4)
    }

CucsEquipmentChassisConfigIssues ::= TEXTUAL-CONVENTION
    STATUS        current
    DESCRIPTION
        ""
    SYNTAX        BITS
    {
        insufficientResources(0),
        chassisUndiscovered(1),
        chassisUnavailable(2),
        insufficientPowerBudget(3),
        nonInterruptFsmRunning(4),
        resourceOwnershipConflict(5),
        missingFirmwareImage(6),
        migration(7),
        physicalRequirement(8),
        invalidChassisPack(9),
        chassisProfileNotSupported(10),
        firmwareVersionMismatch(11),
        computeConnUnsupportedCmcVersion(12),
        computeSecondControllerUnsupportedCmcVersion(13),
        chassisFeatureCapabilityMismatch(15),
        chassisFeatureCapabilityMismatchNonFatal(16),
        singlePathUnsupportedCmcVersion(17),
        singlePathExpanderInoperable(18),
        singlePathInvalidConfiguration(19),
        singlePathNotSupported(20),
        connectionManagementUnsupportedCmcVersion(21),
        connectionManagementExpanderInoperable(22),
        connectionManagementNotSupported(23),
        invalidSasExpConfigPolicyReference(24),
        unsupportedSasExpConfigSettings(25),
        singlePathFeatureNotSupported(26),
        singlePathOperationNotSupported(27),
        connectionManagementFeatureNotSupported(28),
        connectionManagementOperationNotSupported(29),
        invalidCmcVersion(30)
    }

CucsEquipmentChassisConfigProgressIndicator ::= TEXTUAL-CONVENTION
    STATUS        current
    DESCRIPTION
        ""
    SYNTAX        INTEGER
    {
        ackNotInProgress(0),
        ackInProgress(1)
    }

CucsEquipmentChassisConfigState ::= TEXTUAL-CONVENTION
    STATUS        current
    DESCRIPTION
        ""
    SYNTAX        INTEGER
    {
        unInitialized(0),
        unAcknowledged(1),
        unsupportedConnectivity(2),
        ok(3),
        removing(4),
        ackInProgress(6),
        evaluation(7),
        acknowledged(8),
        autoAck(9)
    }

CucsEquipmentChassisFsmCurrentFsm ::= TEXTUAL-CONVENTION
    STATUS        current
    DESCRIPTION
        ""
    SYNTAX        INTEGER
    {
        nop(0),
        removeChassis(9),
        psuPolicyConfig(140),
        powerCap(643),
        dynamicReallocation(1048),
        oobStorageAdminCfg(1883),
        associate(2067),
        disassociate(2098),
        chassisUpgrade(2115),
        fwUpgrade(2279),
        fanPolicyConfig(2342),
        powerSavePolicyConfig(2379),
        powerExtendedPolicyConfig(2431)
    }

CucsEquipmentChassisFsmStageName ::= TEXTUAL-CONVENTION
    STATUS        current
    DESCRIPTION
        ""
    SYNTAX        INTEGER
    {
        nop(0),
        removeChassisBegin(9),
        removeChassisDecomission(10),
        removeChassisDisableEndPoint(11),
        removeChassisUnIdentifyLocal(12),
        removeChassisUnIdentifyPeer(13),
        removeChassisWait(14),
        psuPolicyConfigBegin(140),
        psuPolicyConfigExecute(141),
        psuPolicyConfigFail(374),
        psuPolicyConfigSuccess(375),
        removeChassisFail(376),
        removeChassisSuccess(377),
        powerCapBegin(643),
        powerCapConfig(644),
        powerCapFail(980),
        powerCapSuccess(981),
        dynamicReallocationBegin(1048),
        dynamicReallocationConfig(1049),
        dynamicReallocationFail(1051),
        dynamicReallocationSuccess(1052),
        oobStorageAdminCfgBegin(1883),
        oobStorageAdminCfgOobStorageConfig(1884),
        removeChassisCleanupVnicsLocal(1905),
        removeChassisCleanupVnicsPeer(1906),
        oobStorageAdminCfgFail(1915),
        oobStorageAdminCfgSuccess(1916),
        oobStorageAdminCfgOobStorageInventory(2042),
        associateBegin(2067),
        associateDownloadImages(2068),
        associateCopyRemote(2069),
        associateWaitBeforeInstallation(2070),
        associateUpdateCmc(2071),
        associatePollUpdateCmc(2072),
        associateUpdateAdaptor(2073),
        associatePollUpdateAdaptor(2074),
        associateUpdateSasExpander(2075),
        associatePollUpdateSasExpander(2076),
        associateActivateSasExpander(2077),
        associatePollSasExpanderActivate(2078),
        associateActivateCmc(2079),
        associatePollCmcActivation(2080),
        associatePowerOffServers(2081),
        associateWaitForPowerOff(2082),
        associateActivateAdaptor(2083),
        associatePollAdaptorActivation(2084),
        associateActivateStorageCtlr(2085),
        associatePollStorageCtlrActivation(2086),
        associateActivateBrdCtlr(2087),
        associatePollBrdCtlrActivation(2088),
        associateActivateLocalDisk(2089),
        associatePowerOnServers(2090),
        associateDiskZoningConfig(2091),
        associatePostDiskZoneStorageInvCMC(2092),
        associatePostDiskZoneStorageInvCIMC(2093),
        associatePollPostDiskZoneStorageInvCIMC(2094),
        associateDeleteCurlDownloadedImages(2095),
        associateDeleteImagesRemote(2096),
        associateUnlockFirmwareImage(2097),
        disassociateBegin(2098),
        disassociateComplete(2099),
        chassisUpgradeBegin(2115),
        chassisUpgradeUpdateRequest(2116),
        chassisUpgradePollUpdateStatus(2117),
        chassisUpgradeActivateCmc(2118),
        chassisUpgradePollCmcActivation(2119),
        chassisUpgradePowerOffServers(2120),
        chassisUpgradeWaitForPowerOff(2121),
        chassisUpgradeActivateStorageCtlr(2122),
        chassisUpgradePollStorageCtlrActivation(2123),
        chassisUpgradeActivateAdaptor(2124),
        chassisUpgradePollAdaptorActivation(2125),
        chassisUpgradeActivateBrdCtlr(2126),
        chassisUpgradePollBrdCtlrActivation(2127),
        chassisUpgradeActivateSasExpander(2128),
        chassisUpgradePollSasExpanderActivate(2129),
        chassisUpgradeResetSasExpander(2130),
        chassisUpgradeActivateLocalDisk(2131),
        chassisUpgradePollLocalDiskActivate(2132),
        chassisUpgradePowerOnServers(2133),
        associateFail(2163),
        associateSuccess(2164),
        chassisUpgradeFail(2165),
        chassisUpgradeSuccess(2166),
        disassociateFail(2167),
        disassociateSuccess(2168),
        associateConfigChassisAdapterConnectivity(2246),
        powerCapWait(2276),
        associateSasExpanderConfig(2277),
        associatePollSasExpanderConfig(2278),
        fwUpgradeBegin(2279),
        fwUpgradeDownloadImages(2280),
        fwUpgradeCopyRemote(2281),
        fwUpgradeWaitBeforeInstallation(2282),
        fwUpgradeUpdateCmc(2283),
        fwUpgradePollUpdateCmc(2284),
        fwUpgradeUpdateAdaptor(2285),
        fwUpgradePollUpdateAdaptor(2286),
        fwUpgradeUpdateSasExpander(2287),
        fwUpgradePollUpdateSasExpander(2288),
        fwUpgradeDeleteCurlDownloadedImages(2289),
        fwUpgradeDeleteImagesRemote(2290),
        fwUpgradeUnlockFirmwareImage(2291),
        fwUpgradeFail(2310),
        fwUpgradeSuccess(2311),
        associateChassisPeerAdapterReboot(2329),
        fanPolicyConfigBegin(2342),
        fanPolicyConfigExecute(2343),
        fanPolicyConfigFail(2367),
        fanPolicyConfigSuccess(2368),
        powerSavePolicyConfigBegin(2379),
        powerSavePolicyConfigExecute(2380),
        powerSavePolicyConfigFail(2391),
        powerSavePolicyConfigSuccess(2392),
        powerExtendedPolicyConfigBegin(2431),
        powerExtendedPolicyConfigExecute(2432),
        powerExtendedPolicyConfigFail(2442),
        powerExtendedPolicyConfigSuccess(2443)
    }

CucsEquipmentChassisFsmTaskFlags ::= TEXTUAL-CONVENTION
    STATUS        current
    DESCRIPTION
        ""
    SYNTAX        BITS
    {
        samDmeEquipmentChassisAssociateConfigServerSiocConnState(19),
        samDmeEquipmentChassisAssociateSasExpanderSettingsConfig(22),
        samDmeEquipmentChassisOobStorageAdminCfgOobStorageConfig(36),
        samDmeEquipmentChassisAssociateCpRename(49),
        samDmeEquipmentChassisAssociateDiskZoningConfig(50),
        samDmeEquipmentChassisAssociateCmcUpdate(51),
        samDmeEquipmentChassisAssociateCruzUpdate(52),
        samDmeEquipmentChassisAssociateSasUpdate(53),
        samDmeEquipmentChassisAssociateDiskActivate(54),
        samDmeEquipmentChassisAssociateStorctrlUpdate(55),
        samDmeEquipmentChassisAssociateHostReboot(56),
        samDmeEquipmentChassisAssociatePrepareForUpdate(57),
        samDmeEquipmentChassisAssociateFwUpdate(58),
        samDmeEquipmentChassisDisassociateSwitchUnconfig(59)
    }

CucsEquipmentChassisFsmTaskItem ::= TEXTUAL-CONVENTION
    STATUS        current
    DESCRIPTION
        ""
    SYNTAX        INTEGER
    {
        nop(0),
        removeChassis(9),
        psuPolicyConfig(140),
        powerCap(829),
        dynamicReallocation(1048),
        oobStorageAdminCfg(1883),
        associate(2067),
        disassociate(2098),
        chassisUpgrade(2115),
        fwUpgrade(2279),
        fanPolicyConfig(2342),
        powerSavePolicyConfig(2379),
        powerExtendedPolicyConfig(2431)
    }

CucsEquipmentChassisIssues ::= TEXTUAL-CONVENTION
    STATUS        current
    DESCRIPTION
        ""
    SYNTAX        BITS
    {
        chassisThermal(0),
        chassisInoperable(1),
        chassisVoltage(2),
        chassisPerf(3),
        chassisPower(4),
        removed(5),
        config(6),
        chassisPostFailure(7),
        psuThermal(8),
        psuInoperable(9),
        psuVoltage(10),
        psuPerf(11),
        psuPower(12),
        fanThermal(13),
        fanInoperable(14),
        fanVoltage(15),
        fanPerf(16),
        fanPower(17),
        iocardThermal(18),
        iocardInoperable(19),
        iocardVoltage(20),
        iocardPerf(21),
        iocardPower(22),
        computeThermal(23),
        computeInoperable(24),
        computeVoltage(25),
        computePerf(26),
        computePower(27),
        iocardInaccessible(28),
        fabricConnProblem(29),
        fabricUnsupportedConn(30),
        chassisLimitExceeded(31),
        chassisVifCapacityReduced(32),
        chassisPortChannelEnabled(33),
        chassisUnsupported(34),
        backplanePortProblem(35),
        chassisDiscoveryPolicyUnsupported(36)
    }

CucsEquipmentChassisPowerOperState ::= TEXTUAL-CONVENTION
    STATUS        current
    DESCRIPTION
        ""
    SYNTAX        INTEGER
    {
        unknown(0),
        ok(1),
        failed(2),
        inputFailed(3),
        inputDegraded(4),
        outputFailed(5),
        outputDegraded(6),
        redundancyFailed(7),
        redundancyDegraded(8)
    }

CucsEquipmentChassisProfileBindingOperState ::= TEXTUAL-CONVENTION
    STATUS        current
    DESCRIPTION
        ""
    SYNTAX        INTEGER
    {
        unused(0),
        used(1),
        failedToApply(2)
    }

CucsEquipmentChassisProfileConfigState ::= TEXTUAL-CONVENTION
    STATUS        current
    DESCRIPTION
        ""
    SYNTAX        INTEGER
    {
        notApplied(0),
        applying(1),
        failedToApply(2),
        applied(3)
    }

CucsEquipmentChassisProfileFsmCurrentFsm ::= TEXTUAL-CONVENTION
    STATUS        current
    DESCRIPTION
        ""
    SYNTAX        INTEGER
    {
        nop(0),
        configure(566)
    }

CucsEquipmentChassisProfileFsmStageName ::= TEXTUAL-CONVENTION
    STATUS        current
    DESCRIPTION
        ""
    SYNTAX        INTEGER
    {
        nop(0),
        configureBegin(566),
        configureApplyTemplate(567),
        configureApplyThrottle(568),
        configureThrottleWait(569),
        configureEvaluateAssociation(570),
        configureAnalyzeImpact(571),
        configureApplyRename(572),
        configureApplyConfig(573),
        configureWaitForAssocCompletion(574),
        configureFail(575),
        configureSuccess(576),
        configureResolvePolicies(2055),
        configureResolveDistributableNames(2056),
        configureResolveDistributable(2057),
        configureResolveImages(2058),
        configureResolveSchedule(2059),
        configureValidatePolicyOwnership(2060),
        configureApplyPolicies(2061),
        configureWaitForMaintPermission(2064)
    }

CucsEquipmentChassisProfileFsmTaskFlags ::= TEXTUAL-CONVENTION
    STATUS        current
    DESCRIPTION
        ""
    SYNTAX        BITS
    {
        samDmeEquipmentChassisProfileConfigureModification(15),
        samDmeEquipmentChassisProfileConfigureFinalDisassoc(16),
        samDmeEquipmentChassisProfileConfigureChassisRename(17),
        samDmeEquipmentChassisProfileConfigureDomainSync(18)
    }

CucsEquipmentChassisProfileFsmTaskItem ::= TEXTUAL-CONVENTION
    STATUS        current
    DESCRIPTION
        ""
    SYNTAX        INTEGER
    {
        nop(0),
        configure(566)
    }

CucsEquipmentChassisProfileOperState ::= TEXTUAL-CONVENTION
    STATUS        current
    DESCRIPTION
        ""
    SYNTAX        INTEGER
    {
        indeterminate(0),
        unassociated(1),
        operable(5),
        ok(10),
        discovery(11),
        config(12),
        unconfig(13),
        powerOff(14),
        restart(15),
        maintenance(20),
        test(21),
        chassisMismatch(29),
        chassisFailed(30),
        degraded(31),
        discoveryFailed(32),
        configFailure(33),
        unconfigFailed(34),
        testFailed(35),
        maintenanceFailed(36),
        removed(40),
        disabled(41),
        inaccessible(50),
        inoperable(63),
        decomissioning(101),
        diagnostics(203),
        diagnosticsFailed(204),
        pendingReboot(210),
        pendingReassociation(211)
    }

CucsEquipmentChassisQualMaxId ::= TEXTUAL-CONVENTION
    STATUS        current
    DESCRIPTION
        ""
    SYNTAX        Gauge32 (1..255)

CucsEquipmentChassisQualMinId ::= TEXTUAL-CONVENTION
    STATUS        current
    DESCRIPTION
        ""
    SYNTAX        Gauge32 (1..255)

CucsEquipmentChassisStatsThresholded ::= TEXTUAL-CONVENTION
    STATUS        current
    DESCRIPTION
        ""
    SYNTAX        BITS
    {
        inputPower(0),
        inputPowerAvg(1),
        inputPowerMax(2),
        inputPowerMin(3),
        outputPower(4),
        outputPowerAvg(5),
        outputPowerMax(6),
        outputPowerMin(7)
    }

CucsEquipmentChassisStatsHistThresholded ::= TEXTUAL-CONVENTION
    STATUS        current
    DESCRIPTION
        ""
    SYNTAX        BITS
    {
        inputPower(0),
        inputPowerAvg(1),
        inputPowerMax(2),
        inputPowerMin(3),
        outputPower(4),
        outputPowerAvg(5),
        outputPowerMax(6),
        outputPowerMin(7)
    }

CucsEquipmentChassisTypeCapType ::= TEXTUAL-CONVENTION
    STATUS        current
    DESCRIPTION
        ""
    SYNTAX        INTEGER
    {
        generalPurpose(0),
        xSeries(1)
    }

CucsEquipmentCommStatus ::= TEXTUAL-CONVENTION
    STATUS        current
    DESCRIPTION
        ""
    SYNTAX        INTEGER
    {
        unknown(0),
        connected(1),
        disconnected(2)
    }

CucsEquipmentConfigIssues ::= TEXTUAL-CONVENTION
    STATUS        current
    DESCRIPTION
        ""
    SYNTAX        INTEGER
    {
        notApplicable(0),
        uncleanConfiguration(1)
    }

CucsEquipmentConfigState ::= TEXTUAL-CONVENTION
    STATUS        current
    DESCRIPTION
        ""
    SYNTAX        INTEGER
    {
        notApplied(0),
        applying(1),
        applied(2),
        applyFailed(3)
    }

CucsEquipmentConfigWarnings ::= TEXTUAL-CONVENTION
    STATUS        current
    DESCRIPTION
        ""
    SYNTAX        BITS
    {
        fwUpdateNotSupported(0)
    }

CucsEquipmentConnectionStatus ::= TEXTUAL-CONVENTION
    STATUS        current
    DESCRIPTION
        ""
    SYNTAX        BITS
    {
        a(0),
        b(1)
    }

CucsEquipmentContType ::= TEXTUAL-CONVENTION
    STATUS        current
    DESCRIPTION
        ""
    SYNTAX        INTEGER
    {
        internal(0),
        external(1)
    }

CucsEquipmentControllerDefType ::= TEXTUAL-CONVENTION
    STATUS        current
    DESCRIPTION
        ""
    SYNTAX        INTEGER
    {
        none(0),
        embedded(1),
        slotBased(2),
        nvme(3),
        nvmeHhhl(4),
        nvmeMezz(5),
        dual(6),
        m2(7),
        pt(8)
    }

CucsEquipmentControllerForm ::= TEXTUAL-CONVENTION
    STATUS        current
    DESCRIPTION
        ""
    SYNTAX        INTEGER
    {
        none(0),
        onBoard(1),
        mezzanine(2),
        pci(3),
        embedded(4)
    }

CucsEquipmentControllerSubType ::= TEXTUAL-CONVENTION
    STATUS        current
    DESCRIPTION
        ""
    SYNTAX        INTEGER
    {
        none(0),
        ssata(1),
        psata(2)
    }

CucsEquipmentCpuType ::= TEXTUAL-CONVENTION
    STATUS        current
    DESCRIPTION
        ""
    SYNTAX        INTEGER
    {
        other(0),
        ivyBridge(1),
        sandyBridge(2)
    }

CucsEquipmentCrossFabricModuleId ::= TEXTUAL-CONVENTION
    STATUS        current
    DESCRIPTION
        ""
    SYNTAX        Gauge32 (1..2)

CucsEquipmentCrossFabricModuleFanStatsThresholded ::= TEXTUAL-CONVENTION
    STATUS        current
    DESCRIPTION
        ""
    SYNTAX        BITS
    {
        speed(0),
        speedAvg(1),
        speedMax(2),
        speedMin(3)
    }

CucsEquipmentCrossFabricModuleFanStatsHistThresholded ::= TEXTUAL-CONVENTION
    STATUS        current
    DESCRIPTION
        ""
    SYNTAX        BITS
    {
        speed(0),
        speedAvg(1),
        speedMax(2),
        speedMin(3)
    }

CucsEquipmentCrossFabricModuleStatsThresholded ::= TEXTUAL-CONVENTION
    STATUS        current
    DESCRIPTION
        ""
    SYNTAX        BITS
    {
        ambientTemp(0),
        ambientTempAvg(1),
        ambientTempMax(2),
        ambientTempMin(3)
    }

CucsEquipmentCrossFabricModuleStatsHistThresholded ::= TEXTUAL-CONVENTION
    STATUS        current
    DESCRIPTION
        ""
    SYNTAX        BITS
    {
        ambientTemp(0),
        ambientTempAvg(1),
        ambientTempMax(2),
        ambientTempMin(3)
    }

CucsEquipmentDevicePresence ::= TEXTUAL-CONVENTION
    STATUS        current
    DESCRIPTION
        ""
    SYNTAX        INTEGER
    {
        required(0),
        optional(1)
    }

CucsEquipmentDeviceType ::= TEXTUAL-CONVENTION
    STATUS        current
    DESCRIPTION
        ""
    SYNTAX        INTEGER
    {
        unknown(0),
        broadcom57712Nic(1),
        broadcomNic(2),
        emulexNic(3),
        intelNic(4),
        pciEverestNic(5),
        pciIntelX520Nic(6),
        pciMPCiscoNic(7),
        pciNianticNic(8),
        qlogicNic(9),
        menloEmulexHba(10),
        menloQlogicFcHba(11),
        mezzDublinQlogicFcHba(12),
        mezzSchulzQlogicFcHba(13),
        mezzTigerSharkHba(14),
        pciDublinQlogicFcHba(15),
        pciQlogic8362FcHba(16),
        pciSchulzQlogicFcHba(17),
        pciTigerSharkHba(18),
        fusionHba(19),
        intelICH10RHba(20),
        lsi1064EHba(21),
        lsi1068EHba(22),
        lsiExternalMegaRaidHba(23),
        lsimegaRaid3008(24),
        lsiMegaRaidHba(25),
        lsiWalnutCreekHba(26),
        lodiHba(27),
        sataHba(28),
        nvmeHba(29),
        wellsburgHba(30),
        nvmeMezz(31),
        qlogicFC(32),
        emulexFC(33),
        pciIntelX550Nic(34),
        lagunaBeach(35),
        lagunaBeachPlus(36),
        lagunaRock(37),
        lagunaRockPlus(38),
        lewisburgPSata(39),
        lewisburgSSataSwRaid(40),
        talladega(41),
        pciIntelX710Nic(42),
        pciQlogicBigBear(43),
        nvmeIntelHba(44),
        gpuAmd(45),
        gpuNvidia(46),
        pciPlxSwitch(47),
        m2hwRaidMarvellHba(48),
        mellanoxNic(49),
        nvmeWdHba(50),
        pismoBeach(51),
        zumaBeach(52),
        pismoRock(53),
        zumaRock(54),
        lewisburgPSataAhci(55),
        pciIntelE810Nic(56),
        gpuIntel(57),
        miamiBeach(58),
        miamiRock(59),
        gpuAmdMi(60)
    }

CucsEquipmentDiagFeatureSupportIsSupported ::= TEXTUAL-CONVENTION
    STATUS        current
    DESCRIPTION
        ""
    SYNTAX        INTEGER
    {
        no(0),
        yes(1)
    }

CucsEquipmentDiscovery ::= TEXTUAL-CONVENTION
    STATUS        current
    DESCRIPTION
        ""
    SYNTAX        INTEGER
    {
        undiscovered(0),
        inProgress(1),
        malformedFruInfo(2),
        fruNotReady(3),
        insufficientlyEquipped(4),
        invalidAdaptorIocard(5),
        failed(8),
        complete(16),
        retry(32),
        throttled(64),
        illegalFru(128),
        fruIdentityIndeterminate(129),
        fruStateIndeterminate(130)
    }

CucsEquipmentDiscoveryCapOperPowerRequirement ::= TEXTUAL-CONVENTION
    STATUS        current
    DESCRIPTION
        ""
    SYNTAX        INTEGER
    {
        none(0),
        standby(1),
        full(2)
    }

CucsEquipmentDiscoveryState ::= TEXTUAL-CONVENTION
    STATUS        current
    DESCRIPTION
        ""
    SYNTAX        INTEGER
    {
        unknown(0),
        online(1),
        offline(2),
        discovered(3),
        unsupportedConnectivity(4),
        autoUpgrading(5),
        pinglost(6),
        unsecure(7)
    }

CucsEquipmentDriveSecCapIsHxSecCap ::= TEXTUAL-CONVENTION
    STATUS        current
    DESCRIPTION
        ""
    SYNTAX        INTEGER
    {
        no(0),
        yes(1)
    }

CucsEquipmentDriveSecCapIsSupported ::= TEXTUAL-CONVENTION
    STATUS        current
    DESCRIPTION
        ""
    SYNTAX        INTEGER
    {
        no(0),
        yes(1)
    }

CucsEquipmentEnabledStatus ::= TEXTUAL-CONVENTION
    STATUS        current
    DESCRIPTION
        ""
    SYNTAX        INTEGER
    {
        unknown(0),
        enabled(1),
        disabled(2)
    }

CucsEquipmentEvacState ::= TEXTUAL-CONVENTION
    STATUS        current
    DESCRIPTION
        ""
    SYNTAX        INTEGER
    {
        drain(0),
        fill(1),
        unknown(2)
    }

CucsEquipmentFanId ::= TEXTUAL-CONVENTION
    STATUS        current
    DESCRIPTION
        ""
    SYNTAX        Gauge32 (1..8)

CucsEquipmentFanModule ::= TEXTUAL-CONVENTION
    STATUS        current
    DESCRIPTION
        ""
    SYNTAX        Gauge32 (1..8)

CucsEquipmentFanTray ::= TEXTUAL-CONVENTION
    STATUS        current
    DESCRIPTION
        ""
    SYNTAX        Gauge32 (1..8)

CucsEquipmentFanModuleId ::= TEXTUAL-CONVENTION
    STATUS        current
    DESCRIPTION
        ""
    SYNTAX        Gauge32 (1..8)

CucsEquipmentFanModuleTray ::= TEXTUAL-CONVENTION
    STATUS        current
    DESCRIPTION
        ""
    SYNTAX        Gauge32 (1..1)

CucsEquipmentFanModuleStatsThresholded ::= TEXTUAL-CONVENTION
    STATUS        current
    DESCRIPTION
        ""
    SYNTAX        BITS
    {
        fanModuleI2CErrors(0),
        fanModuleI2CErrorsAvg(1),
        fanModuleI2CErrorsMax(2),
        fanModuleI2CErrorsMin(3)
    }

CucsEquipmentFanModuleStatsHistThresholded ::= TEXTUAL-CONVENTION
    STATUS        current
    DESCRIPTION
        ""
    SYNTAX        BITS
    {
        fanModuleI2CErrors(0),
        fanModuleI2CErrorsAvg(1),
        fanModuleI2CErrorsMax(2),
        fanModuleI2CErrorsMin(3)
    }

CucsEquipmentFanSpeedPolicyFault ::= TEXTUAL-CONVENTION
    STATUS        current
    DESCRIPTION
        ""
    SYNTAX        INTEGER
    {
        yes(0),
        no(1)
    }

CucsEquipmentFanStatsThresholded ::= TEXTUAL-CONVENTION
    STATUS        current
    DESCRIPTION
        ""
    SYNTAX        BITS
    {
        speed(0),
        speedAvg(1),
        speedMax(2),
        speedMin(3)
    }

CucsEquipmentFanStatsHistThresholded ::= TEXTUAL-CONVENTION
    STATUS        current
    DESCRIPTION
        ""
    SYNTAX        BITS
    {
        speed(0),
        speedAvg(1),
        speedMax(2),
        speedMin(3)
    }

CucsEquipmentFexId ::= TEXTUAL-CONVENTION
    STATUS        current
    DESCRIPTION
        ""
    SYNTAX        Gauge32 (1..255)

CucsEquipmentFexCapProviderRole ::= TEXTUAL-CONVENTION
    STATUS        current
    DESCRIPTION
        ""
    SYNTAX        INTEGER
    {
        mgmt(1),
        data(2),
        full(3)
    }

CucsEquipmentFexEnvStatsThresholded ::= TEXTUAL-CONVENTION
    STATUS        current
    DESCRIPTION
        ""
    SYNTAX        BITS
    {
        die1(0),
        die1Avg(1),
        die1Max(2),
        die1Min(3),
        inlet(4),
        inlet1(5),
        inlet1Avg(6),
        inlet1Max(7),
        inlet1Min(8),
        inletAvg(9),
        inletMax(10),
        inletMin(11),
        outlet1(12),
        outlet1Avg(13),
        outlet1Max(14),
        outlet1Min(15),
        outlet2(16),
        outlet2Avg(17),
        outlet2Max(18),
        outlet2Min(19)
    }

CucsEquipmentFexEnvStatsHistThresholded ::= TEXTUAL-CONVENTION
    STATUS        current
    DESCRIPTION
        ""
    SYNTAX        BITS
    {
        die1(0),
        die1Avg(1),
        die1Max(2),
        die1Min(3),
        inlet(4),
        inlet1(5),
        inlet1Avg(6),
        inlet1Max(7),
        inlet1Min(8),
        inletAvg(9),
        inletMax(10),
        inletMin(11),
        outlet1(12),
        outlet1Avg(13),
        outlet1Max(14),
        outlet1Min(15),
        outlet2(16),
        outlet2Avg(17),
        outlet2Max(18),
        outlet2Min(19)
    }

CucsEquipmentFexFsmCurrentFsm ::= TEXTUAL-CONVENTION
    STATUS        current
    DESCRIPTION
        ""
    SYNTAX        INTEGER
    {
        nop(0),
        removeFex(636)
    }

CucsEquipmentFexFsmStageName ::= TEXTUAL-CONVENTION
    STATUS        current
    DESCRIPTION
        ""
    SYNTAX        INTEGER
    {
        nop(0),
        removeFexBegin(636),
        removeFexDecomission(637),
        removeFexUnIdentifyLocal(638),
        removeFexCleanupEntries(639),
        removeFexWait(640),
        removeFexFail(982),
        removeFexSuccess(983),
        removeFexCleanUpVIfs(1997)
    }

CucsEquipmentFexFsmTaskItem ::= TEXTUAL-CONVENTION
    STATUS        current
    DESCRIPTION
        ""
    SYNTAX        INTEGER
    {
        nop(0),
        removeFex(887)
    }

CucsEquipmentFexPowerSummaryThresholded ::= TEXTUAL-CONVENTION
    STATUS        current
    DESCRIPTION
        ""
    SYNTAX        BITS
    {
        modulePower(0),
        modulePowerAvg(1),
        modulePowerMax(2),
        modulePowerMin(3),
        availablePower(4),
        availablePowerAvg(5),
        availablePowerMax(6),
        availablePowerMin(7),
        reservedPower(8),
        reservedPowerAvg(9),
        reservedPowerMax(10),
        reservedPowerMin(11),
        totalPower(12),
        totalPowerAvg(13),
        totalPowerMax(14),
        totalPowerMin(15)
    }

CucsEquipmentFexPowerSummaryHistThresholded ::= TEXTUAL-CONVENTION
    STATUS        current
    DESCRIPTION
        ""
    SYNTAX        BITS
    {
        modulePower(0),
        modulePowerAvg(1),
        modulePowerMax(2),
        modulePowerMin(3),
        availablePower(4),
        availablePowerAvg(5),
        availablePowerMax(6),
        availablePowerMin(7),
        reservedPower(8),
        reservedPowerAvg(9),
        reservedPowerMax(10),
        reservedPowerMin(11),
        totalPower(12),
        totalPowerAvg(13),
        totalPowerMax(14),
        totalPowerMin(15)
    }

CucsEquipmentFexPsuInputStatsThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CucsEquipmentFexPsuInputStatsHistThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CucsEquipmentFexSystemStatsThresholded ::= TEXTUAL-CONVENTION
    STATUS        current
    DESCRIPTION
        ""
    SYNTAX        BITS
    {
        kernelMemFree(0),
        kernelMemFreeAvg(1),
        kernelMemFreeMax(2),
        kernelMemFreeMin(3),
        kernelMemTotal(4),
        kernelMemTotalAvg(5),
        kernelMemTotalMax(6),
        kernelMemTotalMin(7),
        load(8),
        loadAvg(9),
        loadMax(10),
        loadMin(11),
        memAvailable(12),
        memAvailableAvg(13),
        memAvailableMax(14),
        memAvailableMin(15),
        memCached(16),
        memCachedAvg(17),
        memCachedMax(18),
        memCachedMin(19)
    }

CucsEquipmentFexSystemStatsHistThresholded ::= TEXTUAL-CONVENTION
    STATUS        current
    DESCRIPTION
        ""
    SYNTAX        BITS
    {
        kernelMemFree(0),
        kernelMemFreeAvg(1),
        kernelMemFreeMax(2),
        kernelMemFreeMin(3),
        kernelMemTotal(4),
        kernelMemTotalAvg(5),
        kernelMemTotalMax(6),
        kernelMemTotalMin(7),
        load(8),
        loadAvg(9),
        loadMax(10),
        loadMin(11),
        memAvailable(12),
        memAvailableAvg(13),
        memAvailableMax(14),
        memAvailableMin(15),
        memCached(16),
        memCachedAvg(17),
        memCachedMax(18),
        memCachedMin(19)
    }

CucsEquipmentFormFactor ::= TEXTUAL-CONVENTION
    STATUS        current
    DESCRIPTION
        ""
    SYNTAX        INTEGER
    {
        unknown(0),
        pci(1),
        onBoard(2)
    }

CucsEquipmentFruCompType ::= TEXTUAL-CONVENTION
    STATUS        current
    DESCRIPTION
        ""
    SYNTAX        INTEGER
    {
        unknown(0),
        retimer(1),
        ubm(2),
        cpld(3),
        intelAmc(4)
    }

CucsEquipmentFruComponentId ::= TEXTUAL-CONVENTION
    STATUS        current
    DESCRIPTION
        ""
    SYNTAX        Gauge32 (1..5)

CucsEquipmentGlobalConfigIssues ::= TEXTUAL-CONVENTION
    STATUS        current
    DESCRIPTION
        ""
    SYNTAX        BITS
    {
        unused(1)
    }

CucsEquipmentHealthLedState ::= TEXTUAL-CONVENTION
    STATUS        current
    DESCRIPTION
        ""
    SYNTAX        INTEGER
    {
        normal(0),
        minor(1),
        critical(2)
    }

CucsEquipmentHostMgmtControllerCapCommMethod ::= TEXTUAL-CONVENTION
    STATUS        current
    DESCRIPTION
        ""
    SYNTAX        INTEGER
    {
        unknown(0),
        serial(1),
        usbNic(2)
    }

CucsEquipmentHostMgmtControllerCapCommType ::= TEXTUAL-CONVENTION
    STATUS        current
    DESCRIPTION
        ""
    SYNTAX        INTEGER
    {
        bridge(0),
        ipForward(1)
    }

CucsEquipmentHwType ::= TEXTUAL-CONVENTION
    STATUS        current
    DESCRIPTION
        ""
    SYNTAX        INTEGER
    {
        storageController(0),
        localDisk(1)
    }

CucsEquipmentHxCapIsSedSupported ::= TEXTUAL-CONVENTION
    STATUS        current
    DESCRIPTION
        ""
    SYNTAX        INTEGER
    {
        no(0),
        yes(1)
    }

CucsEquipmentHxCapIsUsbNicSupported ::= TEXTUAL-CONVENTION
    STATUS        current
    DESCRIPTION
        ""
    SYNTAX        INTEGER
    {
        no(0),
        yes(1)
    }

CucsEquipmentIOCardId ::= TEXTUAL-CONVENTION
    STATUS        current
    DESCRIPTION
        ""
    SYNTAX        Gauge32 (1..2)

CucsEquipmentIOCardBaseFsmCurrentFsm ::= TEXTUAL-CONVENTION
    STATUS        current
    DESCRIPTION
        ""
    SYNTAX        INTEGER
    {
        nop(0),
        fePresence(1732),
        feConn(1736)
    }

CucsEquipmentIOCardBaseFsmStageName ::= TEXTUAL-CONVENTION
    STATUS        current
    DESCRIPTION
        ""
    SYNTAX        INTEGER
    {
        nop(0),
        fePresenceBegin(1732),
        fePresenceCheckLicense(1733),
        fePresenceIdentify(1734),
        fePresenceConfigChassisId(1735),
        feConnBegin(1736),
        feConnConfigureSwMgmtEndPoint(1737),
        feConnConfigureVifNs(1738),
        feConnConfigureEndPoint(1739),
        feConnDiscoverChassis(1740),
        feConnEnableChassis(1741),
        feConnFail(1815),
        feConnSuccess(1816),
        fePresenceFail(1817),
        fePresenceSuccess(1818)
    }

CucsEquipmentIOCardBaseFsmTaskFlags ::= TEXTUAL-CONVENTION
    STATUS        current
    DESCRIPTION
        ""
    SYNTAX        BITS
    {
        samDmeEquipmentIOCardBaseFePresenceUcsConfig(26),
        samDmeEquipmentIOCardBaseFePresenceMiniUcsConfig(27)
    }

CucsEquipmentIOCardBaseFsmTaskItem ::= TEXTUAL-CONVENTION
    STATUS        current
    DESCRIPTION
        ""
    SYNTAX        INTEGER
    {
        nop(0),
        fePresence(1732),
        feConn(1736)
    }

CucsEquipmentIOCardFanModuleStatsThresholded ::= TEXTUAL-CONVENTION
    STATUS        current
    DESCRIPTION
        ""
    SYNTAX        BITS
    {
        ambientTemp(0),
        ambientTempAvg(1),
        ambientTempMax(2),
        ambientTempMin(3)
    }

CucsEquipmentIOCardFanModuleStatsHistThresholded ::= TEXTUAL-CONVENTION
    STATUS        current
    DESCRIPTION
        ""
    SYNTAX        BITS
    {
        ambientTemp(0),
        ambientTempAvg(1),
        ambientTempMax(2),
        ambientTempMin(3)
    }

CucsEquipmentIOCardFanStatsThresholded ::= TEXTUAL-CONVENTION
    STATUS        current
    DESCRIPTION
        ""
    SYNTAX        BITS
    {
        speed(0),
        speedAvg(1),
        speedMax(2),
        speedMin(3)
    }

CucsEquipmentIOCardFanStatsHistThresholded ::= TEXTUAL-CONVENTION
    STATUS        current
    DESCRIPTION
        ""
    SYNTAX        BITS
    {
        speed(0),
        speedAvg(1),
        speedMax(2),
        speedMin(3)
    }

CucsEquipmentIOCardFsmCurrentFsm ::= TEXTUAL-CONVENTION
    STATUS        current
    DESCRIPTION
        ""
    SYNTAX        INTEGER
    {
        nop(0),
        fePresence(1),
        feConn(3),
        resetCmc(461),
        muxOffline(645),
        resetIom(817),
        evacuate(1939),
        resetEvacuate(1941),
        resetPeerCmc(1980)
    }

CucsEquipmentIOCardFsmStageName ::= TEXTUAL-CONVENTION
    STATUS        current
    DESCRIPTION
        ""
    SYNTAX        INTEGER
    {
        nop(0),
        fePresenceBegin(1),
        fePresenceIdentify(2),
        feConnBegin(3),
        feConnConfigureSwMgmtEndPoint(4),
        feConnConfigureVifNs(5),
        feConnConfigureEndPoint(6),
        feConnDiscoverChassis(7),
        feConnEnableChassis(8),
        feConnFail(378),
        feConnSuccess(379),
        fePresenceFail(380),
        fePresenceSuccess(381),
        resetCmcBegin(461),
        resetCmcExecute(462),
        resetCmcFail(465),
        resetCmcSuccess(466),
        fePresenceCheckLicense(544),
        muxOfflineBegin(645),
        muxOfflineCleanupEntries(646),
        resetIomBegin(817),
        resetIomExecute(818),
        muxOfflineFail(984),
        muxOfflineSuccess(985),
        resetIomFail(986),
        resetIomSuccess(987),
        fePresenceConfigChassisId(1735),
        evacuateBegin(1939),
        evacuateExecute(1940),
        resetEvacuateBegin(1941),
        resetEvacuateExecute(1942),
        evacuateFail(1959),
        evacuateSuccess(1960),
        resetEvacuateFail(1961),
        resetEvacuateSuccess(1962),
        resetPeerCmcBegin(1980),
        resetPeerCmcExecute(1981),
        resetPeerCmcFail(1993),
        resetPeerCmcSuccess(1994)
    }

CucsEquipmentIOCardFsmTaskItem ::= TEXTUAL-CONVENTION
    STATUS        current
    DESCRIPTION
        ""
    SYNTAX        INTEGER
    {
        nop(0),
        fePresence(1),
        feConn(3),
        resetCmc(461),
        resetIom(961),
        muxOffline(978),
        evacuate(1939),
        resetEvacuate(1941),
        resetPeerCmc(1980)
    }

CucsEquipmentIOCardIssues ::= TEXTUAL-CONVENTION
    STATUS        current
    DESCRIPTION
        ""
    SYNTAX        BITS
    {
        thermal(0),
        inoperable(1),
        voltage(2),
        perf(3),
        power(4),
        removed(5),
        fabricPortProblem(6),
        postFailure(7),
        serverPortProblem(8),
        vifCapacityReduced(9),
        fabricpcLinkAutoAckFailed(10)
    }

CucsEquipmentIOCardStatsThresholded ::= TEXTUAL-CONVENTION
    STATUS        current
    DESCRIPTION
        ""
    SYNTAX        BITS
    {
        iomI2CErrorsDelta(0),
        iomI2CErrorsDeltaAvg(1),
        iomI2CErrorsMax(2),
        iomI2CErrorsMin(3),
        temp(4),
        tempAvg(5),
        tempMax(6),
        tempMin(7),
        procTemp(8),
        procTempAvg(9),
        procTempMax(10),
        procTempMin(11)
    }

CucsEquipmentIOCardStatsHistThresholded ::= TEXTUAL-CONVENTION
    STATUS        current
    DESCRIPTION
        ""
    SYNTAX        BITS
    {
        iomI2CErrorsDelta(0),
        iomI2CErrorsDeltaAvg(1),
        iomI2CErrorsMax(2),
        iomI2CErrorsMin(3),
        temp(4),
        tempAvg(5),
        tempMax(6),
        tempMin(7),
        procTemp(8),
        procTempAvg(9),
        procTempMax(10),
        procTempMin(11)
    }

CucsEquipmentInternalFanType ::= TEXTUAL-CONVENTION
    STATUS        current
    DESCRIPTION
        ""
    SYNTAX        INTEGER
    {
        chassis(0),
        switch(1),
        fex(2)
    }

CucsEquipmentIsSupported ::= TEXTUAL-CONVENTION
    STATUS        current
    DESCRIPTION
        ""
    SYNTAX        INTEGER
    {
        no(0),
        yes(1)
    }

CucsEquipmentLedColor ::= TEXTUAL-CONVENTION
    STATUS        current
    DESCRIPTION
        ""
    SYNTAX        INTEGER
    {
        unknown(0),
        green(1),
        amber(2),
        red(3),
        blue(4)
    }

CucsEquipmentLedLocatorState ::= TEXTUAL-CONVENTION
    STATUS        current
    DESCRIPTION
        ""
    SYNTAX        INTEGER
    {
        inactive(0),
        off(1),
        on(2)
    }

CucsEquipmentLedOperState ::= TEXTUAL-CONVENTION
    STATUS        current
    DESCRIPTION
        ""
    SYNTAX        INTEGER
    {
        unknown(0),
        on(1),
        off(2),
        blinking(3),
        eth(4),
        fc(5),
        unsupported(6)
    }

CucsEquipmentLocalDiskControllerDefOobControllerClassIdentifier ::= TEXTUAL-CONVENTION
    STATUS        current
    DESCRIPTION
        ""
    SYNTAX        INTEGER
    {
        none(0),
        nvme(1),
        avilaRock(2),
        aeroMr(3),
        avengerRio(4),
        knox(5)
    }

CucsEquipmentLocatorLedFsmCurrentFsm ::= TEXTUAL-CONVENTION
    STATUS        current
    DESCRIPTION
        ""
    SYNTAX        INTEGER
    {
        nop(0),
        setLocatorLed(15),
        setFeLocatorLed(641),
        setFiLocatorLed(1090),
        setDiskLocatorLed(1744)
    }

CucsEquipmentLocatorLedFsmStageName ::= TEXTUAL-CONVENTION
    STATUS        current
    DESCRIPTION
        ""
    SYNTAX        INTEGER
    {
        nop(0),
        setLocatorLedBegin(15),
        setLocatorLedExecute(16),
        setLocatorLedFail(382),
        setLocatorLedSuccess(383),
        setFeLocatorLedBegin(641),
        setFeLocatorLedExecute(642),
        setFeLocatorLedFail(988),
        setFeLocatorLedSuccess(989),
        setFiLocatorLedBegin(1090),
        setFiLocatorLedExecute(1091),
        setFiLocatorLedFail(1140),
        setFiLocatorLedSuccess(1141),
        setDiskLocatorLedBegin(1744),
        setDiskLocatorLedSetLocatorLedLocal(1745),
        setDiskLocatorLedSetLocatorLedPeer(1746),
        setDiskLocatorLedFail(1819),
        setDiskLocatorLedSuccess(1820)
    }

CucsEquipmentLocatorLedFsmTaskItem ::= TEXTUAL-CONVENTION
    STATUS        current
    DESCRIPTION
        ""
    SYNTAX        INTEGER
    {
        nop(0),
        setLocatorLed(15),
        setFeLocatorLed(641),
        setFiLocatorLed(1119),
        setDiskLocatorLed(1744)
    }

CucsEquipmentMemoryUnitDiscoveryModifierAction ::= TEXTUAL-CONVENTION
    STATUS        current
    DESCRIPTION
        ""
    SYNTAX        INTEGER
    {
        unknown(0),
        setRevToOne(1),
        setRev(2),
        setRevStrict(3)
    }

CucsEquipmentMethod ::= TEXTUAL-CONVENTION
    STATUS        current
    DESCRIPTION
        ""
    SYNTAX        BITS
    {
        post(0),
        configCheck(1),
        diagCheck(2),
        selCheck(3)
    }

CucsEquipmentMmuPercent ::= TEXTUAL-CONVENTION
    STATUS        current
    DESCRIPTION
        ""
    SYNTAX        Gauge32 (0..100)

CucsEquipmentNetworkElementFanStatsThresholded ::= TEXTUAL-CONVENTION
    STATUS        current
    DESCRIPTION
        ""
    SYNTAX        BITS
    {
        drivePercentage(0),
        drivePercentageAvg(1),
        drivePercentageMax(2),
        drivePercentageMin(3),
        speed(4),
        speedAvg(5),
        speedMax(6),
        speedMin(7)
    }

CucsEquipmentNetworkElementFanStatsHistThresholded ::= TEXTUAL-CONVENTION
    STATUS        current
    DESCRIPTION
        ""
    SYNTAX        BITS
    {
        drivePercentage(0),
        drivePercentageAvg(1),
        drivePercentageMax(2),
        drivePercentageMin(3),
        speed(4),
        speedAvg(5),
        speedMax(6),
        speedMin(7)
    }

CucsEquipmentOperability ::= TEXTUAL-CONVENTION
    STATUS        current
    DESCRIPTION
        ""
    SYNTAX        INTEGER
    {
        unknown(0),
        operable(1),
        inoperable(2),
        degraded(3),
        poweredOff(4),
        powerProblem(5),
        removed(6),
        voltageProblem(7),
        thermalProblem(8),
        performanceProblem(9),
        accessibilityProblem(10),
        identityUnestablishable(11),
        biosPostTimeout(12),
        disabled(13),
        malformedFru(14),
        backplanePortProblem(15),
        chassisIntrusion(16),
        nonOptimal(17),
        unsupportedConfig(18),
        nonOptimalSevere(20),
        peerDimmDisabled(21),
        dimmDisabled(22),
        fabricConnProblem(51),
        fabricUnsupportedConn(52),
        config(81),
        equipmentProblem(82),
        decomissioning(83),
        chassisLimitExceeded(84),
        notSupported(100),
        discovery(101),
        discoveryFailed(102),
        identify(103),
        postFailure(104),
        upgradeProblem(105),
        peerCommProblem(106),
        autoUpgrade(107),
        linkActivateBlocked(108)
    }

CucsEquipmentOrientation ::= TEXTUAL-CONVENTION
    STATUS        current
    DESCRIPTION
        ""
    SYNTAX        INTEGER
    {
        right(0),
        down(1),
        left(2),
        up(3)
    }

CucsEquipmentOwner ::= TEXTUAL-CONVENTION
    STATUS        current
    DESCRIPTION
        ""
    SYNTAX        INTEGER
    {
        management(1),
        policy(2),
        tier(4)
    }

CucsEquipmentOwnership ::= TEXTUAL-CONVENTION
    STATUS        current
    DESCRIPTION
        ""
    SYNTAX        INTEGER
    {
        unknown(0),
        owned(1),
        unowned(2)
    }

CucsEquipmentPOSTRecoverability ::= TEXTUAL-CONVENTION
    STATUS        current
    DESCRIPTION
        ""
    SYNTAX        INTEGER
    {
        unknown(0),
        recoverable(1),
        nonRecoverable(2)
    }

CucsEquipmentPasswordState ::= TEXTUAL-CONVENTION
    STATUS        current
    DESCRIPTION
        ""
    SYNTAX        INTEGER
    {
        unknown(0),
        set(1),
        notSet(2)
    }

CucsEquipmentPcieNodeFaultValue ::= TEXTUAL-CONVENTION
    STATUS        current
    DESCRIPTION
        ""
    SYNTAX        BITS
    {
        riser1absentCpu1present(0),
        riserMismatch(1),
        riser2presentCpu2absent(2),
        pcieLinkConfigissue(3),
        powerfault(4),
        riser1Powerfault(5),
        riser2Powerfault(6),
        unknownPcienodePresent(7),
        unsupportedPcienodePresent(8),
        unsupportedPcienodePresentOnRiser1(9),
        unsupportedPcienodePresentOnRiser2(10),
        unknownPcienodePresentOnRiser1(11),
        unknownPcienodePresentOnRiser2(12),
        pcienodePresentXfm1Absent(13),
        retimerVersionMismatch(14)
    }

CucsEquipmentPcieNodeSlotId ::= TEXTUAL-CONVENTION
    STATUS        current
    DESCRIPTION
        ""
    SYNTAX        Gauge32 (1..8)

CucsEquipmentPcieNodeType ::= TEXTUAL-CONVENTION
    STATUS        current
    DESCRIPTION
        ""
    SYNTAX        INTEGER
    {
        gpu(1)
    }

CucsEquipmentPhysicalSecurityState ::= TEXTUAL-CONVENTION
    STATUS        current
    DESCRIPTION
        ""
    SYNTAX        INTEGER
    {
        chassisClose(1),
        chassisOpen(2)
    }

CucsEquipmentPictureType ::= TEXTUAL-CONVENTION
    STATUS        current
    DESCRIPTION
        ""
    SYNTAX        INTEGER
    {
        unknown(0),
        front(1),
        back(2),
        top(3),
        bottom(4),
        left(5),
        right(6),
        topScaled(7),
        frontTopScaled(8),
        frontBottomScaled(9)
    }

CucsEquipmentPnuosBootType ::= TEXTUAL-CONVENTION
    STATUS        current
    DESCRIPTION
        ""
    SYNTAX        INTEGER
    {
        legacy(0),
        uefi(1)
    }

CucsEquipmentPortAttribute ::= TEXTUAL-CONVENTION
    STATUS        current
    DESCRIPTION
        ""
    SYNTAX        INTEGER
    {
        none(0),
        scalability(1)
    }

CucsEquipmentPortGroupAggregationDefAutoNeg ::= TEXTUAL-CONVENTION
    STATUS        current
    DESCRIPTION
        ""
    SYNTAX        INTEGER
    {
        on(0),
        off(1),
        n25g(2)
    }

CucsEquipmentPowerCapDefProfileMethod ::= TEXTUAL-CONVENTION
    STATUS        current
    DESCRIPTION
        ""
    SYNTAX        INTEGER
    {
        unknown(0),
        default(1),
        static(2),
        pnuos(3),
        nodemgr(4)
    }

CucsEquipmentPowerState ::= TEXTUAL-CONVENTION
    STATUS        current
    DESCRIPTION
        ""
    SYNTAX        INTEGER
    {
        unknown(0),
        on(1),
        test(2),
        off(3),
        online(4),
        offline(5),
        offduty(6),
        degraded(7),
        powerSave(8),
        error(9),
        ok(10),
        failed(11),
        notSupported(100)
    }

CucsEquipmentPresence ::= TEXTUAL-CONVENTION
    STATUS        current
    DESCRIPTION
        ""
    SYNTAX        INTEGER
    {
        unknown(0),
        empty(1),
        equipped(10),
        missing(11),
        mismatch(12),
        equippedNotPrimary(13),
        equippedSlave(14),
        mismatchSlave(15),
        missingSlave(16),
        equippedIdentityUnestablishable(20),
        mismatchIdentityUnestablishable(21),
        equippedWithMalformedFru(22),
        inaccessible(30),
        unauthorized(40),
        notSupported(100),
        equippedUnsupported(101),
        equippedDiscNotStarted(102),
        equippedDiscInProgress(103),
        equippedDiscError(104),
        equippedDiscUnknown(105)
    }

CucsEquipmentPsuType ::= TEXTUAL-CONVENTION
    STATUS        current
    DESCRIPTION
        ""
    SYNTAX        INTEGER
    {
        ac(1),
        dc(2)
    }

CucsEquipmentPsuId ::= TEXTUAL-CONVENTION
    STATUS        current
    DESCRIPTION
        ""
    SYNTAX        Gauge32 (1..8)

CucsEquipmentPsuFsmCurrentFsm ::= TEXTUAL-CONVENTION
    STATUS        current
    DESCRIPTION
        ""
    SYNTAX        INTEGER
    {
        nop(0),
        updatePSU(1808)
    }

CucsEquipmentPsuFsmStageName ::= TEXTUAL-CONVENTION
    STATUS        current
    DESCRIPTION
        ""
    SYNTAX        INTEGER
    {
        nop(0),
        updatePSUBegin(1808),
        updatePSUUpdateRequest(1809),
        updatePSUPollUpdateStatus(1810),
        updatePSUActivatePsu(1811),
        updatePSUPollActivateStatus(1812),
        updatePSUFail(1821),
        updatePSUSuccess(1822)
    }

CucsEquipmentPsuFsmTaskFlags ::= TEXTUAL-CONVENTION
    STATUS        current
    DESCRIPTION
        ""
    SYNTAX        BITS
    {
        samDmeEquipmentPsuUpdatePSUFwUpdate(32),
        samDmeEquipmentPsuUpdatePSUFwActivate(33)
    }

CucsEquipmentPsuFsmTaskItem ::= TEXTUAL-CONVENTION
    STATUS        current
    DESCRIPTION
        ""
    SYNTAX        INTEGER
    {
        nop(0),
        updatePSU(1808)
    }

CucsEquipmentPsuInputSrc ::= TEXTUAL-CONVENTION
    STATUS        current
    DESCRIPTION
        ""
    SYNTAX        INTEGER
    {
        unknown(0),
        n210AC50380DC(1),
        n110AC(2),
        undetermined(3),
        nA(4)
    }

CucsEquipmentPsuInputStatsThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CucsEquipmentPsuInputStatsHistThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CucsEquipmentPsuOutputStatsThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CucsEquipmentPsuOutputStatsHistThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CucsEquipmentPsuStateQualifier ::= TEXTUAL-CONVENTION
    STATUS        current
    DESCRIPTION
        ""
    SYNTAX        INTEGER
    {
        unknown(0),
        failure(1),
        overCurrent(2),
        overTemperature(3),
        inputLoss(4),
        fanFailure(5),
        inputCurrentWarning(6),
        inputVoltageWarning(7),
        ambientTemperatureWarning(8),
        outputCurrentWarning(9)
    }

CucsEquipmentPsuStatsThresholded ::= TEXTUAL-CONVENTION
    STATUS        current
    DESCRIPTION
        ""
    SYNTAX        BITS
    {
        psuI2CErrorsDelta(0),
        psuI2CErrorsDeltaAvg(1),
        psuI2CErrorsMax(2),
        psuI2CErrorsMin(3),
        input210v(4),
        input210vAvg(5),
        input210vMax(6),
        input210vMin(7),
        output12v(8),
        output12vAvg(9),
        output12vMax(10),
        output12vMin(11),
        output3v3(12),
        output3v3Avg(13),
        output3v3Max(14),
        output3v3Min(15),
        outputCurrent(16),
        outputCurrentAvg(17),
        outputCurrentMax(18),
        outputCurrentMin(19),
        outputPower(20),
        outputPowerAvg(21),
        outputPowerMax(22),
        outputPowerMin(23)
    }

CucsEquipmentPsuStatsHistThresholded ::= TEXTUAL-CONVENTION
    STATUS        current
    DESCRIPTION
        ""
    SYNTAX        BITS
    {
        psuI2CErrorsDelta(0),
        psuI2CErrorsDeltaAvg(1),
        psuI2CErrorsMax(2),
        psuI2CErrorsMin(3),
        input210v(4),
        input210vAvg(5),
        input210vMax(6),
        input210vMin(7),
        output12v(8),
        output12vAvg(9),
        output12vMax(10),
        output12vMin(11),
        output3v3(12),
        output3v3Avg(13),
        output3v3Max(14),
        output3v3Min(15),
        outputCurrent(16),
        outputCurrentAvg(17),
        outputCurrentMax(18),
        outputCurrentMin(19),
        outputPower(20),
        outputPowerAvg(21),
        outputPowerMax(22),
        outputPowerMin(23)
    }

CucsEquipmentPsuVoltageType ::= TEXTUAL-CONVENTION
    STATUS        current
    DESCRIPTION
        ""
    SYNTAX        INTEGER
    {
        unknown(0),
        ac(1),
        dc(2),
        dv(3),
        hvdc(4),
        nA(5)
    }

CucsEquipmentRackServerForm ::= TEXTUAL-CONVENTION
    STATUS        current
    DESCRIPTION
        ""
    SYNTAX        INTEGER
    {
        rackMount(0),
        enclosureMount(1)
    }

CucsEquipmentRackUnitFanStatsThresholded ::= TEXTUAL-CONVENTION
    STATUS        current
    DESCRIPTION
        ""
    SYNTAX        BITS
    {
        speed(0),
        speedAvg(1),
        speedMax(2),
        speedMin(3)
    }

CucsEquipmentRackUnitFanStatsHistThresholded ::= TEXTUAL-CONVENTION
    STATUS        current
    DESCRIPTION
        ""
    SYNTAX        BITS
    {
        speed(0),
        speedAvg(1),
        speedMax(2),
        speedMin(3)
    }

CucsEquipmentRackUnitPsuStatsThresholded ::= TEXTUAL-CONVENTION
    STATUS        current
    DESCRIPTION
        ""
    SYNTAX        BITS
    {
        ambientTemp(0),
        ambientTempAvg(1),
        ambientTempMax(2),
        ambientTempMin(3),
        inputPower(4),
        inputPowerAvg(5),
        inputPowerMax(6),
        inputPowerMin(7),
        inputVoltage(8),
        inputVoltageAvg(9),
        inputVoltageMax(10),
        inputVoltageMin(11),
        outputCurrent(12),
        outputCurrentAvg(13),
        outputCurrentMax(14),
        outputCurrentMin(15),
        outputPower(16),
        outputPowerAvg(17),
        outputPowerMax(18),
        outputPowerMin(19),
        outputVoltage(20),
        outputVoltageAvg(21),
        outputVoltageMax(22),
        outputVoltageMin(23)
    }

CucsEquipmentRackUnitPsuStatsHistThresholded ::= TEXTUAL-CONVENTION
    STATUS        current
    DESCRIPTION
        ""
    SYNTAX        BITS
    {
        ambientTemp(0),
        ambientTempAvg(1),
        ambientTempMax(2),
        ambientTempMin(3),
        inputPower(4),
        inputPowerAvg(5),
        inputPowerMax(6),
        inputPowerMin(7),
        inputVoltage(8),
        inputVoltageAvg(9),
        inputVoltageMax(10),
        inputVoltageMin(11),
        outputCurrent(12),
        outputCurrentAvg(13),
        outputCurrentMax(14),
        outputCurrentMin(15),
        outputPower(16),
        outputPowerAvg(17),
        outputPowerMax(18),
        outputPowerMin(19),
        outputVoltage(20),
        outputVoltageAvg(21),
        outputVoltageMax(22),
        outputVoltageMin(23)
    }

CucsEquipmentRemoteAdminPowerState ::= TEXTUAL-CONVENTION
    STATUS        current
    DESCRIPTION
        ""
    SYNTAX        INTEGER
    {
        remoteAdminPowerTrigger(0),
        policy(1),
        cycleImmediate(2),
        cycleWait(3)
    }

CucsEquipmentRemoteChassisAdminState ::= TEXTUAL-CONVENTION
    STATUS        current
    DESCRIPTION
        ""
    SYNTAX        INTEGER
    {
        remoteTrigger(0),
        acknowledged(1),
        reAcknowledge(2),
        decommission(3),
        remove(4),
        enablePortChannel(5),
        disablePortChannel(6),
        autoAcknowledge(7)
    }

CucsEquipmentRemovalConditions ::= TEXTUAL-CONVENTION
    STATUS        current
    DESCRIPTION
        ""
    SYNTAX        INTEGER
    {
        unknown(0),
        notApplicable(2),
        removableWhenOff(3),
        removableWhenOnOrOff(4)
    }

CucsEquipmentResetOn ::= TEXTUAL-CONVENTION
    STATUS        current
    DESCRIPTION
        ""
    SYNTAX        INTEGER
    {
        unknown(0),
        update(1),
        activate(2)
    }

CucsEquipmentResolveFromRemoteServer ::= TEXTUAL-CONVENTION
    STATUS        current
    DESCRIPTION
        ""
    SYNTAX        INTEGER
    {
        no(0),
        yes(1)
    }

CucsEquipmentSecureBios ::= TEXTUAL-CONVENTION
    STATUS        current
    DESCRIPTION
        ""
    SYNTAX        INTEGER
    {
        unknown(0),
        notSupported(1),
        supported(2)
    }

CucsEquipmentSensorThresholdStatus ::= TEXTUAL-CONVENTION
    STATUS        current
    DESCRIPTION
        ""
    SYNTAX        INTEGER
    {
        unknown(0),
        ok(1),
        upperNonRecoverable(2),
        upperCritical(3),
        upperNonCritical(4),
        lowerNonCritical(5),
        lowerCritical(6),
        lowerNonRecoverable(7),
        notSupported(100)
    }

CucsEquipmentServerSiocConnState ::= TEXTUAL-CONVENTION
    STATUS        current
    DESCRIPTION
        ""
    SYNTAX        INTEGER
    {
        singleServerSingleSioc(0),
        singleServerDualSioc(1)
    }

CucsEquipmentServiceState ::= TEXTUAL-CONVENTION
    STATUS        current
    DESCRIPTION
        ""
    SYNTAX        INTEGER
    {
        inService(1),
        outOfService(2),
        inMaintenance(3)
    }

CucsEquipmentSharedIOModuleId ::= TEXTUAL-CONVENTION
    STATUS        current
    DESCRIPTION
        ""
    SYNTAX        Gauge32 (1..2)

CucsEquipmentSiocRole ::= TEXTUAL-CONVENTION
    STATUS        current
    DESCRIPTION
        ""
    SYNTAX        INTEGER
    {
        unknown(0),
        active(1),
        standby(2)
    }

CucsEquipmentSiocTempStatsThresholded ::= TEXTUAL-CONVENTION
    STATUS        current
    DESCRIPTION
        ""
    SYNTAX        BITS
    {
        cmcTemp(0),
        cmcTempAvg(1),
        cmcTempMax(2),
        cmcTempMin(3),
        frontTemp(4),
        frontTempAvg(5),
        frontTempMax(6),
        frontTempMin(7),
        midTemp(8),
        midTempAvg(9),
        midTempMax(10),
        midTempMin(11),
        rearTemp(12),
        rearTempAvg(13),
        rearTempMax(14),
        rearTempMin(15),
        vicTemp(16),
        vicTempAvg(17),
        vicTempMax(18),
        vicTempMin(19)
    }

CucsEquipmentSiocTempStatsHistThresholded ::= TEXTUAL-CONVENTION
    STATUS        current
    DESCRIPTION
        ""
    SYNTAX        BITS
    {
        cmcTemp(0),
        cmcTempAvg(1),
        cmcTempMax(2),
        cmcTempMin(3),
        frontTemp(4),
        frontTempAvg(5),
        frontTempMax(6),
        frontTempMin(7),
        midTemp(8),
        midTempAvg(9),
        midTempMax(10),
        midTempMin(11),
        rearTemp(12),
        rearTempAvg(13),
        rearTempMax(14),
        rearTempMin(15),
        vicTemp(16),
        vicTempAvg(17),
        vicTempMax(18),
        vicTempMin(19)
    }

CucsEquipmentSlotArrayLocation ::= TEXTUAL-CONVENTION
    STATUS        current
    DESCRIPTION
        ""
    SYNTAX        INTEGER
    {
        unknown(0),
        front(1),
        back(2),
        top(3),
        bottom(4),
        left(5),
        right(6)
    }

CucsEquipmentSlotArrayOrientation ::= TEXTUAL-CONVENTION
    STATUS        current
    DESCRIPTION
        ""
    SYNTAX        INTEGER
    {
        unknown(0),
        vertical(1),
        horizontal(2)
    }

CucsEquipmentSlotArraySelector ::= TEXTUAL-CONVENTION
    STATUS        current
    DESCRIPTION
        ""
    SYNTAX        INTEGER
    {
        unknown(0),
        psu(1),
        fan(2),
        iocard(3),
        diskSlot(5),
        driveSlot(6),
        usbPort(7),
        ethernetPort(8),
        comPort(9),
        parPort(10),
        vgaPort(11),
        dviPort(12),
        keyboardPort(13),
        mousePort(14),
        gem(15),
        blade(16)
    }

CucsEquipmentSlotEpId ::= TEXTUAL-CONVENTION
    STATUS        current
    DESCRIPTION
        ""
    SYNTAX        Gauge32 (1..4)

CucsEquipmentSlotSpanOrientation ::= TEXTUAL-CONVENTION
    STATUS        current
    DESCRIPTION
        ""
    SYNTAX        INTEGER
    {
        unknown(0),
        inline(1),
        transverse(2)
    }

CucsEquipmentSlotStatus ::= TEXTUAL-CONVENTION
    STATUS        current
    DESCRIPTION
        ""
    SYNTAX        INTEGER
    {
        unknown(0),
        empty(1),
        equipped(10),
        missing(11),
        mismatch(12),
        equippedNotPrimary(13),
        equippedSlave(14),
        mismatchSlave(15),
        missingSlave(16),
        equippedIdentityUnestablishable(20),
        mismatchIdentityUnestablishable(21),
        equippedWithMalformedFru(22),
        inaccessible(30),
        unauthorized(40),
        equippedUnsupported(101),
        equippedDeprecated(102)
    }

CucsEquipmentSlotType ::= TEXTUAL-CONVENTION
    STATUS        current
    DESCRIPTION
        ""
    SYNTAX        INTEGER
    {
        unknown(0),
        compute(1),
        storage(2),
        gpu(3)
    }

CucsEquipmentStorageContainmentMethod ::= TEXTUAL-CONVENTION
    STATUS        current
    DESCRIPTION
        ""
    SYNTAX        INTEGER
    {
        controller(0),
        computeEnclosure(1),
        chassisEnclosure(2),
        storageBlade(3)
    }

CucsEquipmentStorageMethod ::= TEXTUAL-CONVENTION
    STATUS        current
    DESCRIPTION
        ""
    SYNTAX        INTEGER
    {
        unknown(0),
        singleFlash(1),
        dualFlash(2)
    }

CucsEquipmentSwitchIOCardId ::= TEXTUAL-CONVENTION
    STATUS        current
    DESCRIPTION
        ""
    SYNTAX        Gauge32 (1..2)

CucsEquipmentSwitchIOCardFsmCurrentFsm ::= TEXTUAL-CONVENTION
    STATUS        current
    DESCRIPTION
        ""
    SYNTAX        INTEGER
    {
        nop(0),
        fePresence(1732),
        feConn(1736),
        evacuate(2002),
        resetEvacuate(2004)
    }

CucsEquipmentSwitchIOCardFsmStageName ::= TEXTUAL-CONVENTION
    STATUS        current
    DESCRIPTION
        ""
    SYNTAX        INTEGER
    {
        nop(0),
        fePresenceBegin(1732),
        fePresenceCheckLicense(1733),
        fePresenceIdentify(1734),
        fePresenceConfigChassisId(1735),
        feConnBegin(1736),
        feConnConfigureSwMgmtEndPoint(1737),
        feConnConfigureVifNs(1738),
        feConnConfigureEndPoint(1739),
        feConnDiscoverChassis(1740),
        feConnEnableChassis(1741),
        feConnFail(1815),
        feConnSuccess(1816),
        fePresenceFail(1817),
        fePresenceSuccess(1818),
        evacuateBegin(2002),
        evacuateExecute(2003),
        resetEvacuateBegin(2004),
        resetEvacuateExecute(2005),
        evacuateFail(2006),
        evacuateSuccess(2007),
        resetEvacuateFail(2008),
        resetEvacuateSuccess(2009)
    }

CucsEquipmentSwitchIOCardFsmTaskItem ::= TEXTUAL-CONVENTION
    STATUS        current
    DESCRIPTION
        ""
    SYNTAX        INTEGER
    {
        nop(0),
        evacuate(2002),
        resetEvacuate(2004)
    }

CucsEquipmentSystemFruType ::= TEXTUAL-CONVENTION
    STATUS        current
    DESCRIPTION
        ""
    SYNTAX        INTEGER
    {
        unknown(0),
        storageBlade(1)
    }

CucsEquipmentSystemIOControllerId ::= TEXTUAL-CONVENTION
    STATUS        current
    DESCRIPTION
        ""
    SYNTAX        Gauge32 (1..2)

CucsEquipmentSystemIOControllerFsmCurrentFsm ::= TEXTUAL-CONVENTION
    STATUS        current
    DESCRIPTION
        ""
    SYNTAX        INTEGER
    {
        nop(0),
        resetCmc(2035)
    }

CucsEquipmentSystemIOControllerFsmStageName ::= TEXTUAL-CONVENTION
    STATUS        current
    DESCRIPTION
        ""
    SYNTAX        INTEGER
    {
        nop(0),
        resetCmcBegin(2035),
        resetCmcExecute(2036),
        resetCmcFail(2171),
        resetCmcSuccess(2172)
    }

CucsEquipmentSystemIOControllerFsmTaskItem ::= TEXTUAL-CONVENTION
    STATUS        current
    DESCRIPTION
        ""
    SYNTAX        INTEGER
    {
        nop(0),
        resetCmc(2035)
    }

CucsEquipmentTpmConfigSupport ::= TEXTUAL-CONVENTION
    STATUS        current
    DESCRIPTION
        ""
    SYNTAX        INTEGER
    {
        unsupported(0),
        supported(1)
    }

CucsEquipmentTpmType ::= TEXTUAL-CONVENTION
    STATUS        current
    DESCRIPTION
        ""
    SYNTAX        INTEGER
    {
        unknown(0),
        physical(1),
        virtual(2)
    }

CucsEquipmentType ::= TEXTUAL-CONVENTION
    STATUS        current
    DESCRIPTION
        ""
    SYNTAX        INTEGER
    {
        instance(0),
        initialTemplate(1),
        updatingTemplate(2)
    }

CucsEquipmentUnifiedPortAlgorithm ::= TEXTUAL-CONVENTION
    STATUS        current
    DESCRIPTION
        ""
    SYNTAX        INTEGER
    {
        none(0),
        slideRuleEthFirstDoubleRow(1),
        unrestricted(2),
        slideRuleEthFirstSingleRow(3),
        slideRuleFcFirstDoubleRow(4),
        slideRuleFcFirstSingleRow(5),
        slideRuleFcFirst3gfiRow(6),
        slideRuleFcFirst4gfiRow(7),
        slideRuleFcFirst5gfiRow(8),
        slideRuleFcFirstUcsxDirectRow(9),
        slideRuleFcFirst6gfiRow(10)
    }

CucsEquipmentUpLinkConnectivity ::= TEXTUAL-CONVENTION
    STATUS        current
    DESCRIPTION
        ""
    SYNTAX        INTEGER
    {
        inline(0),
        crossConnected(1)
    }

CucsEquipmentUuidFeatureCapUuidSupportMode ::= TEXTUAL-CONVENTION
    STATUS        current
    DESCRIPTION
        ""
    SYNTAX        INTEGER
    {
        none(0),
        loose(1),
        strict(2)
    }

CucsEquipmentXcvrId ::= TEXTUAL-CONVENTION
    STATUS        current
    DESCRIPTION
        ""
    SYNTAX        Gauge32 (1..40)

CucsEquipmentXcvrType ::= TEXTUAL-CONVENTION
    STATUS        current
    DESCRIPTION
        ""
    SYNTAX        INTEGER
    {
        unknown(0),
        h10gcu1m(1),
        h10gcu3m(2),
        h10gcu5m(3),
        h10gcu7m(4),
        h10gusr(5),
        h10glrmsm(6),
        cwdm1471(7),
        cwdm1531(8),
        cwdm1551(9),
        fet(10),
        sfp(11),
        x2(12),
        n10gbasesr(13),
        n10gbaselr(14),
        n10gbaselrm(15),
        n10gbaseer(16),
        h10gacu1m(17),
        h10gacu3m(18),
        h10gacu5m(19),
        h10gacu7m(20),
        h10gacu10m(21),
        h10gacu15m(22),
        qsfp40gsr4(23),
        qsfph40gcu1m(24),
        qsfph40gcu2m(25),
        qsfph40gcu3m(26),
        qsfph40gcu5m(27),
        qsfp40gcr4(28),
        qsfp40glr4(29),
        qsfp4sfp10gcu1m(30),
        qsfp4sfp10gcu3m(31),
        qsfp4sfp10gcu5m(32),
        qsfp4x10gac1m(33),
        qsfp4x10gac3m(34),
        qsfp4x10gac5m(35),
        qsfp4x10gac7m(36),
        qsfp4x10gac10m(37),
        qsfploop(38),
        qsfph40gacu1m(39),
        qsfph40gacu3m(40),
        qsfph40gacu5m(41),
        qsfph40gacu7m(42),
        qsfph40gacu10m(43),
        qsfp4x10glr(44),
        qsfp40gcsr4(45),
        qsfpqsa(46),
        qsfp4sfp10gcu2m(47),
        qsfp40gfet(48),
        qsfp40gsrbd(49),
        qsfph40gaoc1m(50),
        qsfph40gaoc2m(51),
        qsfph40gaoc3m(52),
        qsfph40gaoc5m(53),
        qsfph40gaoc7m(54),
        qsfph40gaoc10m(55),
        qsfph40gaocunknown(56),
        qsfp4x10ga0c1m(57),
        qsfp4x10ga0c2m(58),
        qsfp4x10ga0c3m(59),
        qsfp4x10ga0c5m(60),
        qsfp4x10ga0c7m(61),
        qsfp4x10ga0c10m(62),
        qsfp4x10ga0cunknown(63),
        qsfpunknown(64),
        qsfph40gaoc15m(65),
        n1000basesx(66),
        n1000baselx(67),
        n1000baselh(68),
        n1000basevx(69),
        n1000basezx(70),
        n1000basecx(71),
        n1000basex(72),
        n1000baset(73),
        n1000baseunknown(74),
        h10gacuaoc1m(192),
        h10gacuaoc2m(193),
        h10gacuaoc3m(194),
        h10gacuaoc5m(195),
        h10gacuaoc7m(196),
        h10gacuaoc10m(197),
        h10gacuaoc15m(198),
        h10gaoc1m(199),
        h10gaoc2m(200),
        h10gaoc3m(201),
        h10gaoc5m(202),
        h10gaoc7m(203),
        h10gaoc10m(204),
        h10gcu2m(205),
        h10gcu10m(206),
        n10gbasezr(207),
        dwdmsfp(208),
        n10gbasezrs(209),
        n10gbxdi(210),
        n10gbxui(211),
        n10gbx40di(212),
        n10gbx40ui(213),
        h25gcu1m(214),
        h25gcu2m(215),
        h25gcu3m(216),
        h25gcu5m(217),
        h25gaoc1m(218),
        h25gaoc2m(219),
        h25gaoc3m(220),
        h25gaoc5m(221),
        h25gaoc7m(222),
        h25gaoc10m(223),
        qsfp100gcr4(224),
        qsfp100gcu1m(225),
        qsfp100gcu2m(226),
        qsfp100gcu3m(227),
        qsfp100gaoc1m(228),
        qsfp100gaoc2m(229),
        qsfp100gaoc3m(230),
        qsfp100gaoc5m(231),
        qsfp100gaoc7m(232),
        qsfp100gaoc10m(233),
        qsfp100gaoc15m(234),
        qsfp100gaoc20m(235),
        qsfp100gaoc25m(236),
        qsfp100gaoc30m(237),
        h25gsrs(238),
        qsfp100gsmsr(239),
        qsfp4sfp25gcu1m(240),
        qsfp4sfp25gcu2m(241),
        qsfp4sfp25gcu3m(242),
        qsfp4sfp25gcu5m(243),
        qsfp4sfp25gunknown(244),
        qsfp4x10glrs(245),
        qsfp100g40gbidi(246),
        qsfp40ger4(247),
        qsfp100glr4s(248),
        qsfp100gsr4s(249),
        qsfp100gsr4(250),
        n10gbasesrs(251),
        n10gbaselrs(252),
        h25gcu4m(253),
        h10gcu15m(254),
        h10gcu25m(255),
        h25glrs(256),
        h25gaoc4m(257),
        h10gtx(258),
        n1025Gbase(260),
        n1025Gbaselrs(261),
        qsfp100gsl4(262),
        n4x32gsw(263),
        qsfp40gcsr(264),
        qsfp100gdr(265),
        qsfp100gsr12(267),
        qsfph40gaoc30m(268),
        sfp25gsl(269),
        qsfph40gaoc20m(270),
        qsfp100gpsm4s(271),
        qsfp4sfp10gcu4m(272),
        qsfp40glr4s(273),
        qsfp40gsr4s(274),
        qsfp100gdrs(275),
        qsfp100gfrs(276),
        qsfp100glrs(277),
        n1025Gbasecsrs(278),
        dssfpfc16gsw(280),
        dssfpfc16glw(281),
        dssfpfc32gsw(282),
        dssfpfc32glw(283),
        dssfpfc64gsw(284),
        dssfpfc64glw(285),
        qsfp100ger4ls(286)
    }

CucsEquipmentCType ::= TEXTUAL-CONVENTION
    STATUS        current
    DESCRIPTION
        ""
    SYNTAX        INTEGER
    {
        sas(0),
        flash(1),
        nvme(2),
        m2(3),
        sd(4),
        pt(5)
    }

CucsEquipmentExtPortBitmask ::= TEXTUAL-CONVENTION
    STATUS        current
    DESCRIPTION
        ""
    SYNTAX        BITS
    {
        p55(0),
        p56(1),
        p57(2),
        p58(3),
        p59(4),
        p60(5),
        p61(6),
        p62(7),
        p63(8),
        p64(9),
        p65(10),
        p66(11),
        p67(12),
        p68(13),
        p69(14),
        p70(15),
        p71(16),
        p72(17),
        p73(18),
        p74(19),
        p75(20),
        p76(21),
        p77(22),
        p78(23),
        p79(24),
        p80(25),
        p81(26),
        p82(27),
        p83(28),
        p84(29),
        p85(30),
        p86(31),
        p87(32),
        p88(33),
        p89(34),
        p90(35),
        p91(36),
        p92(37),
        p93(38),
        p94(39),
        p95(40),
        p96(41),
        p97(42),
        p98(43),
        p99(44),
        p100(45),
        p101(46),
        p102(47),
        p103(48),
        p104(49),
        p105(50),
        p106(51),
        p107(52),
        p108(53)
    }

CucsEquipmentFabricEpType ::= TEXTUAL-CONVENTION
    STATUS        current
    DESCRIPTION
        ""
    SYNTAX        INTEGER
    {
        unknown(0),
        chassis(1),
        fex(2),
        blade(3),
        rackUnit(4),
        cartridge(5),
        serverUnit(6)
    }

CucsEquipmentPortBitmask ::= TEXTUAL-CONVENTION
    STATUS        current
    DESCRIPTION
        ""
    SYNTAX        BITS
    {
        p1(0),
        p2(1),
        p3(2),
        p4(3),
        p5(4),
        p6(5),
        p7(6),
        p8(7),
        p9(8),
        p10(9),
        p11(10),
        p12(11),
        p13(12),
        p14(13),
        p15(14),
        p16(15),
        p17(16),
        p18(17),
        p19(18),
        p20(19),
        p21(20),
        p22(21),
        p23(22),
        p24(23),
        p25(24),
        p26(25),
        p27(26),
        p28(27),
        p29(28),
        p30(29),
        p31(30),
        p32(31),
        p33(32),
        p34(33),
        p35(34),
        p36(35),
        p37(36),
        p38(37),
        p39(38),
        p40(39),
        p41(40),
        p42(41),
        p43(42),
        p44(43),
        p45(44),
        p46(45),
        p47(46),
        p48(47),
        p49(48),
        p50(49),
        p51(50),
        p52(51),
        p53(52),
        p54(53)
    }

CucsEtherAdaptorType ::= TEXTUAL-CONVENTION
    STATUS        current
    DESCRIPTION
        ""
    SYNTAX        INTEGER
    {
        cruz(0),
        bodega(1),
        windsor(2)
    }

CucsEtherCIoEpIfType ::= TEXTUAL-CONVENTION
    STATUS        current
    DESCRIPTION
        ""
    SYNTAX        INTEGER
    {
        unknown(0),
        physical(1),
        aggregation(2),
        virtual(3)
    }

CucsEtherCloudType ::= TEXTUAL-CONVENTION
    STATUS        current
    DESCRIPTION
        ""
    SYNTAX        INTEGER
    {
        unclassified(1),
        lan(2),
        san(3)
    }

CucsEtherErrStatsThresholded ::= TEXTUAL-CONVENTION
    STATUS        current
    DESCRIPTION
        ""
    SYNTAX        BITS
    {
        alignDelta(0),
        alignDeltaAvg(1),
        alignDeltaMax(2),
        alignDeltaMin(3),
        deferredTxDelta(4),
        deferredTxDeltaAvg(5),
        deferredTxDeltaMax(6),
        deferredTxDeltaMin(7),
        fcsDelta(8),
        fcsDeltaAvg(9),
        fcsDeltaMax(10),
        fcsDeltaMin(11),
        intMacRxDelta(12),
        intMacRxDeltaAvg(13),
        intMacRxDeltaMax(14),
        intMacRxDeltaMin(15),
        intMacTxDelta(16),
        intMacTxDeltaAvg(17),
        intMacTxDeltaMax(18),
        intMacTxDeltaMin(19),
        outDiscardDelta(20),
        outDiscardDeltaAvg(21),
        outDiscardDeltaMax(22),
        outDiscardDeltaMin(23),
        rcvDelta(24),
        rcvDeltaAvg(25),
        rcvDeltaMax(26),
        rcvDeltaMin(27),
        underSizeDelta(28),
        underSizeDeltaAvg(29),
        underSizeDeltaMax(30),
        underSizeDeltaMin(31),
        xmitDelta(32),
        xmitDeltaAvg(33),
        xmitDeltaMax(34),
        xmitDeltaMin(35)
    }

CucsEtherErrStatsHistThresholded ::= TEXTUAL-CONVENTION
    STATUS        current
    DESCRIPTION
        ""
    SYNTAX        BITS
    {
        alignDelta(0),
        alignDeltaAvg(1),
        alignDeltaMax(2),
        alignDeltaMin(3),
        deferredTxDelta(4),
        deferredTxDeltaAvg(5),
        deferredTxDeltaMax(6),
        deferredTxDeltaMin(7),
        fcsDelta(8),
        fcsDeltaAvg(9),
        fcsDeltaMax(10),
        fcsDeltaMin(11),
        intMacRxDelta(12),
        intMacRxDeltaAvg(13),
        intMacRxDeltaMax(14),
        intMacRxDeltaMin(15),
        intMacTxDelta(16),
        intMacTxDeltaAvg(17),
        intMacTxDeltaMax(18),
        intMacTxDeltaMin(19),
        outDiscardDelta(20),
        outDiscardDeltaAvg(21),
        outDiscardDeltaMax(22),
        outDiscardDeltaMin(23),
        rcvDelta(24),
        rcvDeltaAvg(25),
        rcvDeltaMax(26),
        rcvDeltaMin(27),
        underSizeDelta(28),
        underSizeDeltaAvg(29),
        underSizeDeltaMax(30),
        underSizeDeltaMin(31),
        xmitDelta(32),
        xmitDeltaAvg(33),
        xmitDeltaMax(34),
        xmitDeltaMin(35)
    }

CucsEtherExternalEpAdminState ::= TEXTUAL-CONVENTION
    STATUS        current
    DESCRIPTION
        ""
    SYNTAX        INTEGER
    {
        enabled(1),
        disabled(2)
    }

CucsEtherExternalEpLocale ::= TEXTUAL-CONVENTION
    STATUS        current
    DESCRIPTION
        ""
    SYNTAX        BITS
    {
        server(0),
        chassis(1),
        internal(2),
        external(3)
    }

CucsEtherExternalPcAdminState ::= TEXTUAL-CONVENTION
    STATUS        current
    DESCRIPTION
        ""
    SYNTAX        INTEGER
    {
        enabled(1),
        disabled(2)
    }

CucsEtherExternalPcLocale ::= TEXTUAL-CONVENTION
    STATUS        current
    DESCRIPTION
        ""
    SYNTAX        BITS
    {
        server(0),
        chassis(1),
        internal(2),
        external(3)
    }

CucsEtherFcoeInterfaceStatsThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CucsEtherFcoeInterfaceStatsHistThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CucsEtherIntFIoEpType ::= TEXTUAL-CONVENTION
    STATUS        current
    DESCRIPTION
        ""
    SYNTAX        BITS
    {
        lan(0),
        san(1),
        ipc(2)
    }

CucsEtherInternalPcLocale ::= TEXTUAL-CONVENTION
    STATUS        current
    DESCRIPTION
        ""
    SYNTAX        BITS
    {
        server(0),
        chassis(1),
        internal(2),
        external(3)
    }

CucsEtherLossStatsThresholded ::= TEXTUAL-CONVENTION
    STATUS        current
    DESCRIPTION
        ""
    SYNTAX        BITS
    {
        sqetestDelta(0),
        sqetestDeltaAvg(1),
        sqetestDeltaMax(2),
        sqetestDeltaMin(3),
        carrierSenseDelta(4),
        carrierSenseDeltaAvg(5),
        carrierSenseDeltaMax(6),
        carrierSenseDeltaMin(7),
        excessCollisionDelta(8),
        excessCollisionDeltaAvg(9),
        excessCollisionDeltaMax(10),
        excessCollisionDeltaMin(11),
        giantsDelta(12),
        giantsDeltaAvg(13),
        giantsDeltaMax(14),
        giantsDeltaMin(15),
        lateCollisionDelta(16),
        lateCollisionDeltaAvg(17),
        lateCollisionDeltaMax(18),
        lateCollisionDeltaMin(19),
        multiCollisionDelta(20),
        multiCollisionDeltaAvg(21),
        multiCollisionDeltaMax(22),
        multiCollisionDeltaMin(23),
        singleCollisionDelta(24),
        singleCollisionDeltaAvg(25),
        singleCollisionDeltaMax(26),
        singleCollisionDeltaMin(27),
        symbolDelta(28),
        symbolDeltaAvg(29),
        symbolDeltaMax(30),
        symbolDeltaMin(31)
    }

CucsEtherLossStatsHistThresholded ::= TEXTUAL-CONVENTION
    STATUS        current
    DESCRIPTION
        ""
    SYNTAX        BITS
    {
        sqetestDelta(0),
        sqetestDeltaAvg(1),
        sqetestDeltaMax(2),
        sqetestDeltaMin(3),
        carrierSenseDelta(4),
        carrierSenseDeltaAvg(5),
        carrierSenseDeltaMax(6),
        carrierSenseDeltaMin(7),
        excessCollisionDelta(8),
        excessCollisionDeltaAvg(9),
        excessCollisionDeltaMax(10),
        excessCollisionDeltaMin(11),
        giantsDelta(12),
        giantsDeltaAvg(13),
        giantsDeltaMax(14),
        giantsDeltaMin(15),
        lateCollisionDelta(16),
        lateCollisionDeltaAvg(17),
        lateCollisionDeltaMax(18),
        lateCollisionDeltaMin(19),
        multiCollisionDelta(20),
        multiCollisionDeltaAvg(21),
        multiCollisionDeltaMax(22),
        multiCollisionDeltaMin(23),
        singleCollisionDelta(24),
        singleCollisionDeltaAvg(25),
        singleCollisionDeltaMax(26),
        singleCollisionDeltaMin(27),
        symbolDelta(28),
        symbolDeltaAvg(29),
        symbolDeltaMax(30),
        symbolDeltaMin(31)
    }

CucsEtherMacSecAuthModeType ::= TEXTUAL-CONVENTION
    STATUS        current
    DESCRIPTION
        ""
    SYNTAX        INTEGER
    {
        unknown(0),
        primaryPsk(1),
        fallbackPsk(2)
    }

CucsEtherMacSecKeyServerType ::= TEXTUAL-CONVENTION
    STATUS        current
    DESCRIPTION
        ""
    SYNTAX        INTEGER
    {
        unknown(0),
        no(1),
        yes(2)
    }

CucsEtherMacSecRxStatsThresholded ::= TEXTUAL-CONVENTION
    STATUS        current
    DESCRIPTION
        ""
    SYNTAX        BITS
    {
        broadcastControlledPacketsDelta(0),
        broadcastControlledPacketsDeltaAvg(1),
        broadcastControlledPacketsDeltaMax(2),
        broadcastControlledPacketsDeltaMin(3),
        broadcastUncontrolledPacketsDelta(4),
        broadcastUncontrolledPacketsDeltaAvg(5),
        broadcastUncontrolledPacketsDeltaMax(6),
        broadcastUncontrolledPacketsDeltaMin(7),
        controlledPacketsDelta(8),
        controlledPacketsDeltaAvg(9),
        controlledPacketsDeltaMax(10),
        controlledPacketsDeltaMin(11),
        controlledRxDropPacketsDelta(12),
        controlledRxDropPacketsDeltaAvg(13),
        controlledRxDropPacketsDeltaMax(14),
        controlledRxDropPacketsDeltaMin(15),
        controlledRxErrorPacketsDelta(16),
        controlledRxErrorPacketsDeltaAvg(17),
        controlledRxErrorPacketsDeltaMax(18),
        controlledRxErrorPacketsDeltaMin(19),
        multicastControlledPacketsDelta(20),
        multicastControlledPacketsDeltaAvg(21),
        multicastControlledPacketsDeltaMax(22),
        multicastControlledPacketsDeltaMin(23),
        multicastUncontrolledPacketsDelta(24),
        multicastUncontrolledPacketsDeltaAvg(25),
        multicastUncontrolledPacketsDeltaMax(26),
        multicastUncontrolledPacketsDeltaMin(27),
        uncontrolledRxDropPacketsDelta(28),
        uncontrolledRxDropPacketsDeltaAvg(29),
        uncontrolledRxDropPacketsDeltaMax(30),
        uncontrolledRxDropPacketsDeltaMin(31),
        uncontrolledRxErrorPacketsDelta(32),
        uncontrolledRxErrorPacketsDeltaAvg(33),
        uncontrolledRxErrorPacketsDeltaMax(34),
        uncontrolledRxErrorPacketsDeltaMin(35),
        unicastControlledPacketsDelta(36),
        unicastControlledPacketsDeltaAvg(37),
        unicastControlledPacketsDeltaMax(38),
        unicastControlledPacketsDeltaMin(39),
        unicastUncontrolledPacketsDelta(40),
        unicastUncontrolledPacketsDeltaAvg(41),
        unicastUncontrolledPacketsDeltaMax(42),
        unicastUncontrolledPacketsDeltaMin(43)
    }

CucsEtherMacSecRxStatsHistThresholded ::= TEXTUAL-CONVENTION
    STATUS        current
    DESCRIPTION
        ""
    SYNTAX        BITS
    {
        broadcastControlledPacketsDelta(0),
        broadcastControlledPacketsDeltaAvg(1),
        broadcastControlledPacketsDeltaMax(2),
        broadcastControlledPacketsDeltaMin(3),
        broadcastUncontrolledPacketsDelta(4),
        broadcastUncontrolledPacketsDeltaAvg(5),
        broadcastUncontrolledPacketsDeltaMax(6),
        broadcastUncontrolledPacketsDeltaMin(7),
        controlledPacketsDelta(8),
        controlledPacketsDeltaAvg(9),
        controlledPacketsDeltaMax(10),
        controlledPacketsDeltaMin(11),
        controlledRxDropPacketsDelta(12),
        controlledRxDropPacketsDeltaAvg(13),
        controlledRxDropPacketsDeltaMax(14),
        controlledRxDropPacketsDeltaMin(15),
        controlledRxErrorPacketsDelta(16),
        controlledRxErrorPacketsDeltaAvg(17),
        controlledRxErrorPacketsDeltaMax(18),
        controlledRxErrorPacketsDeltaMin(19),
        multicastControlledPacketsDelta(20),
        multicastControlledPacketsDeltaAvg(21),
        multicastControlledPacketsDeltaMax(22),
        multicastControlledPacketsDeltaMin(23),
        multicastUncontrolledPacketsDelta(24),
        multicastUncontrolledPacketsDeltaAvg(25),
        multicastUncontrolledPacketsDeltaMax(26),
        multicastUncontrolledPacketsDeltaMin(27),
        uncontrolledRxDropPacketsDelta(28),
        uncontrolledRxDropPacketsDeltaAvg(29),
        uncontrolledRxDropPacketsDeltaMax(30),
        uncontrolledRxDropPacketsDeltaMin(31),
        uncontrolledRxErrorPacketsDelta(32),
        uncontrolledRxErrorPacketsDeltaAvg(33),
        uncontrolledRxErrorPacketsDeltaMax(34),
        uncontrolledRxErrorPacketsDeltaMin(35),
        unicastControlledPacketsDelta(36),
        unicastControlledPacketsDeltaAvg(37),
        unicastControlledPacketsDeltaMax(38),
        unicastControlledPacketsDeltaMin(39),
        unicastUncontrolledPacketsDelta(40),
        unicastUncontrolledPacketsDeltaAvg(41),
        unicastUncontrolledPacketsDeltaMax(42),
        unicastUncontrolledPacketsDeltaMin(43)
    }

CucsEtherMacSecStateType ::= TEXTUAL-CONVENTION
    STATUS        current
    DESCRIPTION
        ""
    SYNTAX        INTEGER
    {
        unknown(0),
        init(1),
        pending(2),
        secured(3),
        rekeyed(4)
    }

CucsEtherMacSecTxStatsThresholded ::= TEXTUAL-CONVENTION
    STATUS        current
    DESCRIPTION
        ""
    SYNTAX        BITS
    {
        broadcastControlledPacketsDelta(0),
        broadcastControlledPacketsDeltaAvg(1),
        broadcastControlledPacketsDeltaMax(2),
        broadcastControlledPacketsDeltaMin(3),
        broadcastUncontrolledPacketsDelta(4),
        broadcastUncontrolledPacketsDeltaAvg(5),
        broadcastUncontrolledPacketsDeltaMax(6),
        broadcastUncontrolledPacketsDeltaMin(7),
        controlledPacketsDelta(8),
        controlledPacketsDeltaAvg(9),
        controlledPacketsDeltaMax(10),
        controlledPacketsDeltaMin(11),
        controlledRxDropPacketsDelta(12),
        controlledRxDropPacketsDeltaAvg(13),
        controlledRxDropPacketsDeltaMax(14),
        controlledRxDropPacketsDeltaMin(15),
        controlledRxErrorPacketsDelta(16),
        controlledRxErrorPacketsDeltaAvg(17),
        controlledRxErrorPacketsDeltaMax(18),
        controlledRxErrorPacketsDeltaMin(19),
        multicastControlledPacketsDelta(20),
        multicastControlledPacketsDeltaAvg(21),
        multicastControlledPacketsDeltaMax(22),
        multicastControlledPacketsDeltaMin(23),
        multicastUncontrolledPacketsDelta(24),
        multicastUncontrolledPacketsDeltaAvg(25),
        multicastUncontrolledPacketsDeltaMax(26),
        multicastUncontrolledPacketsDeltaMin(27),
        uncontrolledRxDropPacketsDelta(28),
        uncontrolledRxDropPacketsDeltaAvg(29),
        uncontrolledRxDropPacketsDeltaMax(30),
        uncontrolledRxDropPacketsDeltaMin(31),
        uncontrolledRxErrorPacketsDelta(32),
        uncontrolledRxErrorPacketsDeltaAvg(33),
        uncontrolledRxErrorPacketsDeltaMax(34),
        uncontrolledRxErrorPacketsDeltaMin(35),
        unicastControlledPacketsDelta(36),
        unicastControlledPacketsDeltaAvg(37),
        unicastControlledPacketsDeltaMax(38),
        unicastControlledPacketsDeltaMin(39),
        unicastUncontrolledPacketsDelta(40),
        unicastUncontrolledPacketsDeltaAvg(41),
        unicastUncontrolledPacketsDeltaMax(42),
        unicastUncontrolledPacketsDeltaMin(43)
    }

CucsEtherMacSecTxStatsHistThresholded ::= TEXTUAL-CONVENTION
    STATUS        current
    DESCRIPTION
        ""
    SYNTAX        BITS
    {
        broadcastControlledPacketsDelta(0),
        broadcastControlledPacketsDeltaAvg(1),
        broadcastControlledPacketsDeltaMax(2),
        broadcastControlledPacketsDeltaMin(3),
        broadcastUncontrolledPacketsDelta(4),
        broadcastUncontrolledPacketsDeltaAvg(5),
        broadcastUncontrolledPacketsDeltaMax(6),
        broadcastUncontrolledPacketsDeltaMin(7),
        controlledPacketsDelta(8),
        controlledPacketsDeltaAvg(9),
        controlledPacketsDeltaMax(10),
        controlledPacketsDeltaMin(11),
        controlledRxDropPacketsDelta(12),
        controlledRxDropPacketsDeltaAvg(13),
        controlledRxDropPacketsDeltaMax(14),
        controlledRxDropPacketsDeltaMin(15),
        controlledRxErrorPacketsDelta(16),
        controlledRxErrorPacketsDeltaAvg(17),
        controlledRxErrorPacketsDeltaMax(18),
        controlledRxErrorPacketsDeltaMin(19),
        multicastControlledPacketsDelta(20),
        multicastControlledPacketsDeltaAvg(21),
        multicastControlledPacketsDeltaMax(22),
        multicastControlledPacketsDeltaMin(23),
        multicastUncontrolledPacketsDelta(24),
        multicastUncontrolledPacketsDeltaAvg(25),
        multicastUncontrolledPacketsDeltaMax(26),
        multicastUncontrolledPacketsDeltaMin(27),
        uncontrolledRxDropPacketsDelta(28),
        uncontrolledRxDropPacketsDeltaAvg(29),
        uncontrolledRxDropPacketsDeltaMax(30),
        uncontrolledRxDropPacketsDeltaMin(31),
        uncontrolledRxErrorPacketsDelta(32),
        uncontrolledRxErrorPacketsDeltaAvg(33),
        uncontrolledRxErrorPacketsDeltaMax(34),
        uncontrolledRxErrorPacketsDeltaMin(35),
        unicastControlledPacketsDelta(36),
        unicastControlledPacketsDeltaAvg(37),
        unicastControlledPacketsDeltaMax(38),
        unicastControlledPacketsDeltaMin(39),
        unicastUncontrolledPacketsDelta(40),
        unicastUncontrolledPacketsDeltaAvg(41),
        unicastUncontrolledPacketsDeltaMax(42),
        unicastUncontrolledPacketsDeltaMin(43)
    }

CucsEtherNiErrStatsThresholded ::= TEXTUAL-CONVENTION
    STATUS        current
    DESCRIPTION
        ""
    SYNTAX        BITS
    {
        crcDelta(0),
        crcDeltaAvg(1),
        crcDeltaMax(2),
        crcDeltaMin(3),
        frameTxDelta(4),
        frameTxDeltaAvg(5),
        frameTxDeltaMax(6),
        frameTxDeltaMin(7),
        inRangeDelta(8),
        inRangeDeltaAvg(9),
        inRangeDeltaMax(10),
        inRangeDeltaMin(11),
        tooLongDelta(12),
        tooLongDeltaAvg(13),
        tooLongDeltaMax(14),
        tooLongDeltaMin(15),
        tooShortDelta(16),
        tooShortDeltaAvg(17),
        tooShortDeltaMax(18),
        tooShortDeltaMin(19)
    }

CucsEtherNiErrStatsHistThresholded ::= TEXTUAL-CONVENTION
    STATUS        current
    DESCRIPTION
        ""
    SYNTAX        BITS
    {
        crcDelta(0),
        crcDeltaAvg(1),
        crcDeltaMax(2),
        crcDeltaMin(3),
        frameTxDelta(4),
        frameTxDeltaAvg(5),
        frameTxDeltaMax(6),
        frameTxDeltaMin(7),
        inRangeDelta(8),
        inRangeDeltaAvg(9),
        inRangeDeltaMax(10),
        inRangeDeltaMin(11),
        tooLongDelta(12),
        tooLongDeltaAvg(13),
        tooLongDeltaMax(14),
        tooLongDeltaMin(15),
        tooShortDelta(16),
        tooShortDeltaAvg(17),
        tooShortDeltaMax(18),
        tooShortDeltaMin(19)
    }

CucsEtherPIoEpIfType ::= TEXTUAL-CONVENTION
    STATUS        current
    DESCRIPTION
        ""
    SYNTAX        INTEGER
    {
        unknown(0),
        physical(1),
        aggregation(2),
        virtual(3)
    }

CucsEtherPIoFsmCurrentFsm ::= TEXTUAL-CONVENTION
    STATUS        current
    DESCRIPTION
        ""
    SYNTAX        INTEGER
    {
        nop(0),
        inCompatSfpPresence(1014),
        inCompatSfpReplaced(1334)
    }

CucsEtherPIoFsmStageName ::= TEXTUAL-CONVENTION
    STATUS        current
    DESCRIPTION
        ""
    SYNTAX        INTEGER
    {
        nop(0),
        inCompatSfpPresenceBegin(1014),
        inCompatSfpPresenceShutdown(1015),
        inCompatSfpPresenceFail(1034),
        inCompatSfpPresenceSuccess(1035),
        inCompatSfpReplacedBegin(1334),
        inCompatSfpReplacedEnablePort(1335),
        inCompatSfpReplacedFail(1461),
        inCompatSfpReplacedSuccess(1462)
    }

CucsEtherPauseStatsThresholded ::= TEXTUAL-CONVENTION
    STATUS        current
    DESCRIPTION
        ""
    SYNTAX        BITS
    {
        recvPauseDelta(0),
        recvPauseDeltaAvg(1),
        recvPauseDeltaMax(2),
        recvPauseDeltaMin(3),
        resetsDelta(4),
        resetsDeltaAvg(5),
        resetsDeltaMax(6),
        resetsDeltaMin(7),
        xmitPauseDelta(8),
        xmitPauseDeltaAvg(9),
        xmitPauseDeltaMax(10),
        xmitPauseDeltaMin(11)
    }

CucsEtherPauseStatsHistThresholded ::= TEXTUAL-CONVENTION
    STATUS        current
    DESCRIPTION
        ""
    SYNTAX        BITS
    {
        recvPauseDelta(0),
        recvPauseDeltaAvg(1),
        recvPauseDeltaMax(2),
        recvPauseDeltaMin(3),
        resetsDelta(4),
        resetsDeltaAvg(5),
        resetsDeltaMax(6),
        resetsDeltaMin(7),
        xmitPauseDelta(8),
        xmitPauseDeltaAvg(9),
        xmitPauseDeltaMax(10),
        xmitPauseDeltaMin(11)
    }

CucsEtherRxStatsThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CucsEtherRxStatsHistThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CucsEtherSatelliteConnectionDisc ::= TEXTUAL-CONVENTION
    STATUS        current
    DESCRIPTION
        ""
    SYNTAX        INTEGER
    {
        absent(0),
        present(1),
        misConnect(2),
        missing(3),
        new(4),
        unInitialized(5),
        unSupported(6),
        init(7)
    }

CucsEtherServerIntFIoAdminState ::= TEXTUAL-CONVENTION
    STATUS        current
    DESCRIPTION
        ""
    SYNTAX        INTEGER
    {
        enabled(1),
        disabled(2)
    }

CucsEtherServerIntFIoIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsEtherServerIntFIoLocale ::= TEXTUAL-CONVENTION
    STATUS        current
    DESCRIPTION
        ""
    SYNTAX        BITS
    {
        server(0),
        chassis(1),
        internal(2),
        external(3)
    }

CucsEtherServerIntFIoTransport ::= TEXTUAL-CONVENTION
    STATUS        current
    DESCRIPTION
        ""
    SYNTAX        BITS
    {
        ether(0),
        dce(1),
        fc(2)
    }

CucsEtherServerIntFIoType ::= TEXTUAL-CONVENTION
    STATUS        current
    DESCRIPTION
        ""
    SYNTAX        BITS
    {
        lan(0),
        san(1),
        ipc(2)
    }

CucsEtherServerIntFIoFsmCurrentFsm ::= TEXTUAL-CONVENTION
    STATUS        current
    DESCRIPTION
        ""
    SYNTAX        INTEGER
    {
        nop(0),
        configSpeed(1150),
        config(2101)
    }

CucsEtherServerIntFIoFsmStageName ::= TEXTUAL-CONVENTION
    STATUS        current
    DESCRIPTION
        ""
    SYNTAX        INTEGER
    {
        nop(0),
        configSpeedBegin(1150),
        configSpeedConfigure(1151),
        configSpeedFail(1182),
        configSpeedSuccess(1183),
        configBegin(2101),
        configConfigure(2102),
        configFail(2173),
        configSuccess(2174)
    }

CucsEtherServerIntFIoFsmTaskItem ::= TEXTUAL-CONVENTION
    STATUS        current
    DESCRIPTION
        ""
    SYNTAX        INTEGER
    {
        nop(0),
        configSpeed(1150),
        config(2101)
    }

CucsEtherServerIntFIoPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsEtherServerIntFIoPcPortId ::= TEXTUAL-CONVENTION
    STATUS        current
    DESCRIPTION
        ""
    SYNTAX        Gauge32 (1024..4096)

CucsEtherServerIntFIoPcTransport ::= TEXTUAL-CONVENTION
    STATUS        current
    DESCRIPTION
        ""
    SYNTAX        BITS
    {
        ether(0),
        dce(1),
        fc(2)
    }

CucsEtherServerIntFIoPcType ::= TEXTUAL-CONVENTION
    STATUS        current
    DESCRIPTION
        ""
    SYNTAX        BITS
    {
        lan(0),
        san(1),
        ipc(2)
    }

CucsEtherServerIntFIoPcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsEtherServerIntFIoPcEpPortId ::= TEXTUAL-CONVENTION
    STATUS        current
    DESCRIPTION
        ""
    SYNTAX        Gauge32 (1..33)

CucsEtherSwitchIntFIoAck ::= TEXTUAL-CONVENTION
    STATUS        current
    DESCRIPTION
        ""
    SYNTAX        INTEGER
    {
        unInitialized(0),
        unAcknowledged(1),
        unsupportedConnectivity(2),
        ok(3),
        removing(4),
        ackInProgress(6),
        evaluation(7),
        acknowledged(8),
        autoAck(9)
    }

CucsEtherSwitchIntFIoIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsEtherSwitchIntFIoLocale ::= TEXTUAL-CONVENTION
    STATUS        current
    DESCRIPTION
        ""
    SYNTAX        BITS
    {
        server(0),
        chassis(1),
        internal(2),
        external(3)
    }

CucsEtherSwitchIntFIoTransport ::= TEXTUAL-CONVENTION
    STATUS        current
    DESCRIPTION
        ""
    SYNTAX        BITS
    {
        ether(0),
        dce(1),
        fc(2)
    }

CucsEtherSwitchIntFIoType ::= TEXTUAL-CONVENTION
    STATUS        current
    DESCRIPTION
        ""
    SYNTAX        BITS
    {
        lan(0),
        san(1),
        ipc(2)
    }

CucsEtherSwitchIntFIoPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsEtherSwitchIntFIoPcMulticastHwHash ::= TEXTUAL-CONVENTION
    STATUS        current
    DESCRIPTION
        ""
    SYNTAX        INTEGER
    {
        disabled(0),
        enabled(1)
    }

CucsEtherSwitchIntFIoPcPortId ::= TEXTUAL-CONVENTION
    STATUS        current
    DESCRIPTION
        ""
    SYNTAX        Gauge32 (1024..4096)

CucsEtherSwitchIntFIoPcTransport ::= TEXTUAL-CONVENTION
    STATUS        current
    DESCRIPTION
        ""
    SYNTAX        BITS
    {
        ether(0),
        dce(1),
        fc(2)
    }

CucsEtherSwitchIntFIoPcType ::= TEXTUAL-CONVENTION
    STATUS        current
    DESCRIPTION
        ""
    SYNTAX        BITS
    {
        lan(0),
        san(1),
        ipc(2)
    }

CucsEtherSwitchIntFIoPcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsEtherSwitchIntFIoPcEpPortId ::= TEXTUAL-CONVENTION
    STATUS        current
    DESCRIPTION
        ""
    SYNTAX        Gauge32 (1..8)

CucsEtherTxStatsThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CucsEtherTxStatsHistThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CucsEtherUserRecoveryOperation ::= TEXTUAL-CONVENTION
    STATUS        current
    DESCRIPTION
        ""
    SYNTAX        INTEGER
    {
        none(0),
        reset(1)
    }

CucsEventEpCtrlLevel ::= TEXTUAL-CONVENTION
    STATUS        current
    DESCRIPTION
        ""
    SYNTAX        INTEGER
    {
        cleared(0),
        info(1),
        condition(2),
        warning(3),
        minor(4),
        major(5),
        critical(6)
    }

CucsEventStatus ::= TEXTUAL-CONVENTION
    STATUS        current
    DESCRIPTION
        ""
    SYNTAX        BITS
    {
        subscribed(0),
        failed(1)
    }

CucsExtmgmtArpTargetsMaxDeadlineTimeout ::= TEXTUAL-CONVENTION
    STATUS        current
    DESCRIPTION
        ""
    SYNTAX        Gauge32 (5..15)

CucsExtmgmtArpTargetsNumberOfArpRequests ::= TEXTUAL-CONVENTION
    STATUS        current
    DESCRIPTION
        ""
    SYNTAX        Gauge32 (1..5)

CucsExtmgmtGatewayPingMaxDeadlineTimeout ::= TEXTUAL-CONVENTION
    STATUS        current
    DESCRIPTION
        ""
    SYNTAX        Gauge32 (5..15)

CucsExtmgmtGatewayPingNumberOfPingRequests ::= TEXTUAL-CONVENTION
    STATUS        current
    DESCRIPTION
        ""
    SYNTAX        Gauge32 (1..5)

CucsExtmgmtIfMonPolicyAdminState ::= TEXTUAL-CONVENTION
    STATUS        current
    DESCRIPTION
        ""
    SYNTAX        INTEGER
    {
        enabled(1),
        disabled(2)
    }

CucsExtmgmtIfMonPolicyMonitorMechanism ::= TEXTUAL-CONVENTION
    STATUS        current
    DESCRIPTION
        ""
    SYNTAX        INTEGER
    {
        miiStatus(0),
        arpTargetPing(1),
        gatewayPing(2)
    }

CucsExtmgmtMiiStatusMaxRetryCount ::= TEXTUAL-CONVENTION
    STATUS        current
    DESCRIPTION
        ""
    SYNTAX        Gauge32 (1..3)

CucsExtmgmtMiiStatusRetryInterval ::= TEXTUAL-CONVENTION
    STATUS        current
    DESCRIPTION
        ""
    SYNTAX        Gauge32 (3..10)

CucsExtmgmtNdiscTargetsMaxDeadlineTimeout ::= TEXTUAL-CONVENTION
    STATUS        current
    DESCRIPTION
        ""
    SYNTAX        Gauge32 (5..15)

CucsExtmgmtNdiscTargetsNumberOfNdiscRequests ::= TEXTUAL-CONVENTION
    STATUS        current
    DESCRIPTION
        ""
    SYNTAX        Gauge32 (1..5)

CucsExtpolAppCapability ::= TEXTUAL-CONVENTION
    STATUS        current
    DESCRIPTION
        ""
    SYNTAX        BITS
    {
        serviceReg(0),
        identifierMgr(1),
        operationMgr(2),
        resourceMgr(3),
        virtualSwitchingMgr(4),
        policyMgr(5),
        bootMgr(6),
        vmMgr(7),
        vmAdmin(8),
        infraCryptoOffloa(9),
        vmm(10),
        vmVasw(11),
        vmFw(12),
        vmSlb(13),
        infraFw(14),
        infraSlb(15),
        ipam(16),
        pcm(17),
        infraAggr(18),
        infraWas(19),
        infraWaf(20),
        infraPasw(21),
        infraPdsw(22),
        storageBroker(23),
        orgMgr(24),
        statsMgr(25),
        centralMgr(26),
        serverMgr(27)
    }

CucsExtpolClientFsmCurrentFsm ::= TEXTUAL-CONVENTION
    STATUS        current
    DESCRIPTION
        ""
    SYNTAX        INTEGER
    {
        nop(0),
        updateContextFsm(214)
    }

CucsExtpolClientFsmStageName ::= TEXTUAL-CONVENTION
    STATUS        current
    DESCRIPTION
        ""
    SYNTAX        INTEGER
    {
        nop(0),
        updateContextFsmBegin(214),
        updateContextFsmExecute(215),
        updateContextFsmFail(218),
        updateContextFsmSuccess(219)
    }

CucsExtpolClientFsmTaskItem ::= TEXTUAL-CONVENTION
    STATUS        current
    DESCRIPTION
        ""
    SYNTAX        INTEGER
    {
        nop(0),
        updateContextFsm(214)
    }

CucsExtpolConnProtocol ::= TEXTUAL-CONVENTION
    STATUS        current
    DESCRIPTION
        ""
    SYNTAX        INTEGER
    {
        ipv4(0),
        ipv6(1),
        unknown(2)
    }

CucsExtpolConnType ::= TEXTUAL-CONVENTION
    STATUS        current
    DESCRIPTION
        ""
    SYNTAX        INTEGER
    {
        ape(5),
        serverMgr(19),
        serviceReg(27),
        identifierMgr(28),
        operationMgr(29),
        resourceMgr(30),
        virtualSwitchingMgr(31),
        policyMgr(32),
        bootMgr(33),
        vmMgr(34),
        managedEndpoint(35),
        mgmtController(36),
        storageBroker(37),
        resourceAggr(38),
        statsMgr(39),
        centralMgr(40)
    }

CucsExtpolConnectorNwState ::= TEXTUAL-CONVENTION
    STATUS        current
    DESCRIPTION
        ""
    SYNTAX        INTEGER
    {
        connected(0),
        lostConnectivity(1)
    }

CucsExtpolConnectorOperState ::= TEXTUAL-CONVENTION
    STATUS        current
    DESCRIPTION
        ""
    SYNTAX        INTEGER
    {
        unregistered(0),
        lostVisibility(1),
        registering(2),
        synchronizing(3),
        registered(4),
        versionMismatch(5),
        registryNotReachable(6)
    }

CucsExtpolEpFsmCurrentFsm ::= TEXTUAL-CONVENTION
    STATUS        current
    DESCRIPTION
        ""
    SYNTAX        INTEGER
    {
        nop(0),
        repairCert(1193),
        registerFsm(1349)
    }

CucsExtpolEpFsmStageName ::= TEXTUAL-CONVENTION
    STATUS        current
    DESCRIPTION
        ""
    SYNTAX        INTEGER
    {
        nop(0),
        repairCertBegin(1193),
        repairCertVerifyGuid(1194),
        repairCertUnregister(1195),
        repairCertCleanOldData(1196),
        repairCertRequest(1197),
        repairCertVerify(1198),
        registerFsmBegin(1349),
        registerFsmExecute(1350),
        registerFsmFail(1393),
        registerFsmSuccess(1394),
        repairCertFail(1395),
        repairCertSuccess(1396)
    }

CucsExtpolEpFsmTaskItem ::= TEXTUAL-CONVENTION
    STATUS        current
    DESCRIPTION
        ""
    SYNTAX        INTEGER
    {
        nop(0),
        repairCert(1193),
        registerFsm(1349)
    }

CucsExtpolLossVisibilitySource ::= TEXTUAL-CONVENTION
    STATUS        current
    DESCRIPTION
        ""
    SYNTAX        INTEGER
    {
        unknown(0),
        polling(1)
    }

CucsExtpolProviderFsmCurrentFsm ::= TEXTUAL-CONVENTION
    STATUS        current
    DESCRIPTION
        ""
    SYNTAX        INTEGER
    {
        nop(0),
        reportConfigImport(1374)
    }

CucsExtpolProviderFsmStageName ::= TEXTUAL-CONVENTION
    STATUS        current
    DESCRIPTION
        ""
    SYNTAX        INTEGER
    {
        nop(0),
        reportConfigImportBegin(1374),
        reportConfigImportReport(1375),
        reportConfigImportFail(1398),
        reportConfigImportSuccess(1399)
    }

CucsExtpolProviderFsmTaskItem ::= TEXTUAL-CONVENTION
    STATUS        current
    DESCRIPTION
        ""
    SYNTAX        INTEGER
    {
        nop(0),
        reportConfigImport(1374)
    }

CucsExtpolRegistryFsmCurrentFsm ::= TEXTUAL-CONVENTION
    STATUS        current
    DESCRIPTION
        ""
    SYNTAX        INTEGER
    {
        nop(0),
        crossDomainConfig(1351),
        crossDomainDelete(1354)
    }

CucsExtpolRegistryFsmStageName ::= TEXTUAL-CONVENTION
    STATUS        current
    DESCRIPTION
        ""
    SYNTAX        INTEGER
    {
        nop(0),
        crossDomainConfigBegin(1351),
        crossDomainConfigSetLocal(1352),
        crossDomainConfigSetPeer(1353),
        crossDomainDeleteBegin(1354),
        crossDomainDeleteSetLocal(1355),
        crossDomainDeleteSetPeer(1356),
        crossDomainConfigFail(1397),
        crossDomainConfigSuccess(1398),
        crossDomainDeleteFail(1399),
        crossDomainDeleteSuccess(1400)
    }

CucsExtpolRegistryFsmTaskItem ::= TEXTUAL-CONVENTION
    STATUS        current
    DESCRIPTION
        ""
    SYNTAX        INTEGER
    {
        nop(0),
        crossDomainConfig(1351),
        crossDomainDelete(1354)
    }

CucsExtpolScanCompletionStatus ::= TEXTUAL-CONVENTION
    STATUS        current
    DESCRIPTION
        ""
    SYNTAX        INTEGER
    {
        inProgress(0),
        completed(1)
    }

CucsExtpolScanEnablementState ::= TEXTUAL-CONVENTION
    STATUS        current
    DESCRIPTION
        ""
    SYNTAX        INTEGER
    {
        enabled(0),
        disabled(1)
    }

CucsExtpolState ::= TEXTUAL-CONVENTION
    STATUS        current
    DESCRIPTION
        ""
    SYNTAX        INTEGER
    {
        unknown(0),
        licenseOk(1),
        licenseInsufficient(2),
        licenseGraceperiod(3),
        licenseExpired(4),
        notApplicable(5)
    }

CucsExtpolSuspendState ::= TEXTUAL-CONVENTION
    STATUS        current
    DESCRIPTION
        ""
    SYNTAX        INTEGER
    {
        off(0),
        on(1)
    }

CucsExtpolVersionHolderOperation ::= TEXTUAL-CONVENTION
    STATUS        current
    DESCRIPTION
        ""
    SYNTAX        INTEGER
    {
        noOperation(0),
        add(1),
        delete(2)
    }

CucsExtpolConnectionProtocol ::= TEXTUAL-CONVENTION
    STATUS        current
    DESCRIPTION
        ""
    SYNTAX        INTEGER
    {
        ipv4(0),
        ipv6(1),
        unknown(2)
    }

CucsExtvmmEpFsmCurrentFsm ::= TEXTUAL-CONVENTION
    STATUS        current
    DESCRIPTION
        ""
    SYNTAX        INTEGER
    {
        nop(0),
        clusterRole(1129)
    }

CucsExtvmmEpFsmStageName ::= TEXTUAL-CONVENTION
    STATUS        current
    DESCRIPTION
        ""
    SYNTAX        INTEGER
    {
        nop(0),
        clusterRoleBegin(1129),
        clusterRoleSetPeer(1130),
        clusterRoleSetLocal(1131),
        clusterRoleFail(1142),
        clusterRoleSuccess(1143)
    }

CucsExtvmmEpFsmTaskItem ::= TEXTUAL-CONVENTION
    STATUS        current
    DESCRIPTION
        ""
    SYNTAX        INTEGER
    {
        nop(0),
        clusterRole(1086)
    }

CucsExtvmmFabricNetworkType ::= TEXTUAL-CONVENTION
    STATUS        current
    DESCRIPTION
        ""
    SYNTAX        INTEGER
    {
        notConnected(0),
        notConnectedPvlans(1),
        connected(2)
    }

CucsExtvmmKeyStoreFsmCurrentFsm ::= TEXTUAL-CONVENTION
    STATUS        current
    DESCRIPTION
        ""
    SYNTAX        INTEGER
    {
        nop(0),
        certInstall(539)
    }

CucsExtvmmKeyStoreFsmStageName ::= TEXTUAL-CONVENTION
    STATUS        current
    DESCRIPTION
        ""
    SYNTAX        INTEGER
    {
        nop(0),
        certInstallBegin(539),
        certInstallSetLocal(540),
        certInstallSetPeer(541),
        certInstallFail(561),
        certInstallSuccess(562)
    }

CucsExtvmmKeyStoreFsmTaskItem ::= TEXTUAL-CONVENTION
    STATUS        current
    DESCRIPTION
        ""
    SYNTAX        INTEGER
    {
        nop(0),
        certInstall(539)
    }

CucsExtvmmMasterExtKeyFsmCurrentFsm ::= TEXTUAL-CONVENTION
    STATUS        current
    DESCRIPTION
        ""
    SYNTAX        INTEGER
    {
        nop(0),
        config(575)
    }

CucsExtvmmMasterExtKeyFsmStageName ::= TEXTUAL-CONVENTION
    STATUS        current
    DESCRIPTION
        ""
    SYNTAX        INTEGER
    {
        nop(0),
        configBegin(575),
        configSetLocal(576),
        configSetPeer(577),
        configFail(578),
        configSuccess(579)
    }

CucsExtvmmMasterExtKeyFsmTaskItem ::= TEXTUAL-CONVENTION
    STATUS        current
    DESCRIPTION
        ""
    SYNTAX        INTEGER
    {
        nop(0),
        config(575)
    }

CucsExtvmmNetworkSetConfigQualifier ::= TEXTUAL-CONVENTION
    STATUS        current
    DESCRIPTION
        ""
    SYNTAX        INTEGER
    {
        normal(0),
        duplicateVmndReference(1)
    }

CucsExtvmmNetworkSetsFsmCurrentFsm ::= TEXTUAL-CONVENTION
    STATUS        current
    DESCRIPTION
        ""
    SYNTAX        INTEGER
    {
        nop(0),
        deploy(1539)
    }

CucsExtvmmNetworkSetsFsmStageName ::= TEXTUAL-CONVENTION
    STATUS        current
    DESCRIPTION
        ""
    SYNTAX        INTEGER
    {
        nop(0),
        deployBegin(1539),
        deployLocal(1540),
        deployPeer(1541),
        deployFail(1554),
        deploySuccess(1555)
    }

CucsExtvmmNetworkSetsFsmTaskItem ::= TEXTUAL-CONVENTION
    STATUS        current
    DESCRIPTION
        ""
    SYNTAX        INTEGER
    {
        nop(0),
        deploy(1539)
    }

CucsExtvmmOwnership ::= TEXTUAL-CONVENTION
    STATUS        current
    DESCRIPTION
        ""
    SYNTAX        INTEGER
    {
        discovered(1),
        managed(2)
    }

CucsExtvmmProviderFsmCurrentFsm ::= TEXTUAL-CONVENTION
    STATUS        current
    DESCRIPTION
        ""
    SYNTAX        INTEGER
    {
        nop(0),
        config(536)
    }

CucsExtvmmProviderFsmStageName ::= TEXTUAL-CONVENTION
    STATUS        current
    DESCRIPTION
        ""
    SYNTAX        INTEGER
    {
        nop(0),
        configBegin(536),
        configSetPeer(537),
        configSetLocal(538),
        configFail(563),
        configSuccess(564),
        configGetVersion(581)
    }

CucsExtvmmProviderFsmTaskItem ::= TEXTUAL-CONVENTION
    STATUS        current
    DESCRIPTION
        ""
    SYNTAX        INTEGER
    {
        nop(0),
        config(536),
        collectGarbage(1130)
    }

CucsExtvmmRefOperState ::= TEXTUAL-CONVENTION
    STATUS        current
    DESCRIPTION
        ""
    SYNTAX        INTEGER
    {
        up(0),
        invalidReference(1)
    }

CucsExtvmmSwitchDelTaskFsmCurrentFsm ::= TEXTUAL-CONVENTION
    STATUS        current
    DESCRIPTION
        ""
    SYNTAX        INTEGER
    {
        nop(0),
        removeProvider(542)
    }

CucsExtvmmSwitchDelTaskFsmStageName ::= TEXTUAL-CONVENTION
    STATUS        current
    DESCRIPTION
        ""
    SYNTAX        INTEGER
    {
        nop(0),
        removeProviderBegin(542),
        removeProviderRemoveLocal(543),
        removeProviderFail(565),
        removeProviderSuccess(566)
    }

CucsExtvmmSwitchDelTaskFsmTaskItem ::= TEXTUAL-CONVENTION
    STATUS        current
    DESCRIPTION
        ""
    SYNTAX        INTEGER
    {
        nop(0),
        removeProvider(542)
    }

CucsExtvmmVcVersion ::= TEXTUAL-CONVENTION
    STATUS        current
    DESCRIPTION
        ""
    SYNTAX        INTEGER
    {
        unknown(0),
        kl(1),
        klU1(2)
    }

CucsExtvmmVnicType ::= TEXTUAL-CONVENTION
    STATUS        current
    DESCRIPTION
        ""
    SYNTAX        INTEGER
    {
        unknown(0),
        ether(1),
        fc(4),
        scsi(8),
        ipc(16)
    }

CucsExtvmmProviderVendorType ::= TEXTUAL-CONVENTION
    STATUS        current
    DESCRIPTION
        ""
    SYNTAX        INTEGER
    {
        unknown(0),
        vmware(1),
        microsoft(2)
    }

CucsFabricADceSwSrvEpTransport ::= TEXTUAL-CONVENTION
    STATUS        current
    DESCRIPTION
        ""
    SYNTAX        BITS
    {
        ether(0),
        dce(1),
        fc(2)
    }

CucsFabricAEthEstcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricAEthEstcEpTransport ::= TEXTUAL-CONVENTION
    STATUS        current
    DESCRIPTION
        ""
    SYNTAX        BITS
    {
        ether(0),
        dce(1),
        fc(2)
    }

CucsFabricAEthEstcEpType ::= TEXTUAL-CONVENTION
    STATUS        current
    DESCRIPTION
        ""
    SYNTAX        BITS
    {
        lan(0),
        san(1),
        ipc(2)
    }

CucsFabricAEthLanEpTransport ::= TEXTUAL-CONVENTION
    STATUS        current
    DESCRIPTION
        ""
    SYNTAX        BITS
    {
        ether(0),
        dce(1),
        fc(2)
    }

CucsFabricAFcEstcEpTransport ::= TEXTUAL-CONVENTION
    STATUS        current
    DESCRIPTION
        ""
    SYNTAX        BITS
    {
        ether(0),
        dce(1),
        fc(2)
    }

CucsFabricAFcEstcEpType ::= TEXTUAL-CONVENTION
    STATUS        current
    DESCRIPTION
        ""
    SYNTAX        BITS
    {
        lan(0),
        san(1),
        ipc(2)
    }

CucsFabricAFcSanEpTransport ::= TEXTUAL-CONVENTION
    STATUS        current
    DESCRIPTION
        ""
    SYNTAX        BITS
    {
        ether(0),
        dce(1),
        fc(2)
    }

CucsFabricAFcoeEstcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricAFcoeEstcEpTransport ::= TEXTUAL-CONVENTION
    STATUS        current
    DESCRIPTION
        ""
    SYNTAX        BITS
    {
        ether(0),
        dce(1),
        fc(2)
    }

CucsFabricAFcoeEstcEpType ::= TEXTUAL-CONVENTION
    STATUS        current
    DESCRIPTION
        ""
    SYNTAX        BITS
    {
        lan(0),
        san(1),
        ipc(2)
    }

CucsFabricAFcoeSanEpTransport ::= TEXTUAL-CONVENTION
    STATUS        current
    DESCRIPTION
        ""
    SYNTAX        BITS
    {
        ether(0),
        dce(1),
        fc(2)
    }

CucsFabricAVlanAssocPrimaryVlanSwitchId ::= TEXTUAL-CONVENTION
    STATUS        current
    DESCRIPTION
        ""
    SYNTAX        INTEGER
    {
        none(0),
        a(1),
        b(2),
        mgmt(3)
    }

CucsFabricAVlanSharing ::= TEXTUAL-CONVENTION
    STATUS        current
    DESCRIPTION
        ""
    SYNTAX        INTEGER
    {
        none(0),
        primary(1),
        isolated(2),
        community(3)
    }

CucsFabricAVlanTransport ::= TEXTUAL-CONVENTION
    STATUS        current
    DESCRIPTION
        ""
    SYNTAX        BITS
    {
        ether(0),
        dce(1),
        fc(2)
    }

CucsFabricAVlanType ::= TEXTUAL-CONVENTION
    STATUS        current
    DESCRIPTION
        ""
    SYNTAX        BITS
    {
        lan(0),
        san(1),
        ipc(2)
    }

CucsFabricAVsanTransport ::= TEXTUAL-CONVENTION
    STATUS        current
    DESCRIPTION
        ""
    SYNTAX        BITS
    {
        ether(0),
        dce(1),
        fc(2)
    }

CucsFabricAVsanType ::= TEXTUAL-CONVENTION
    STATUS        current
    DESCRIPTION
        ""
    SYNTAX        BITS
    {
        lan(0),
        san(1),
        ipc(2)
    }

CucsFabricAccessType ::= TEXTUAL-CONVENTION
    STATUS        current
    DESCRIPTION
        ""
    SYNTAX        INTEGER
    {
        lan(0),
        san(1)
    }

CucsFabricAdminState ::= TEXTUAL-CONVENTION
    STATUS        current
    DESCRIPTION
        ""
    SYNTAX        INTEGER
    {
        enabled(1),
        disabled(2)
    }

CucsFabricBHVlanSwitchId ::= TEXTUAL-CONVENTION
    STATUS        current
    DESCRIPTION
        ""
    SYNTAX        INTEGER
    {
        none(0),
        a(1),
        b(2),
        dual(3)
    }

CucsFabricBladeLifeCycle ::= TEXTUAL-CONVENTION
    STATUS        current
    DESCRIPTION
        ""
    SYNTAX        INTEGER
    {
        inService(1),
        outOfService(2),
        outOfServiceSlave(3)
    }

CucsFabricBreakoutPortId ::= TEXTUAL-CONVENTION
    STATUS        current
    DESCRIPTION
        ""
    SYNTAX        Gauge32 (1..48)

CucsFabricBreakoutSlotId ::= TEXTUAL-CONVENTION
    STATUS        current
    DESCRIPTION
        ""
    SYNTAX        Gauge32 (1..2)

CucsFabricBreakoutOperationPortId ::= TEXTUAL-CONVENTION
    STATUS        current
    DESCRIPTION
        ""
    SYNTAX        Gauge32 (1..48)

CucsFabricBreakoutOperationSlotId ::= TEXTUAL-CONVENTION
    STATUS        current
    DESCRIPTION
        ""
    SYNTAX        Gauge32 (1..2)

CucsFabricBreakoutType ::= TEXTUAL-CONVENTION
    STATUS        current
    DESCRIPTION
        ""
    SYNTAX        INTEGER
    {
        unknown(0),
        n10g4x(1),
        n25g4x(2)
    }

CucsFabricCIoEpAdminState ::= TEXTUAL-CONVENTION
    STATUS        current
    DESCRIPTION
        ""
    SYNTAX        INTEGER
    {
        enabled(1),
        disabled(2)
    }

CucsFabricCIoEpIfType ::= TEXTUAL-CONVENTION
    STATUS        current
    DESCRIPTION
        ""
    SYNTAX        INTEGER
    {
        unknown(0),
        physical(1),
        aggregation(2),
        virtual(3)
    }

CucsFabricCartridgeSlotEpSlotId ::= TEXTUAL-CONVENTION
    STATUS        current
    DESCRIPTION
        ""
    SYNTAX        Gauge32 (1..8)

CucsFabricCartridgeSlotEpFsmCurrentFsm ::= TEXTUAL-CONVENTION
    STATUS        current
    DESCRIPTION
        ""
    SYNTAX        INTEGER
    {
        nop(0),
        identify(1874)
    }

CucsFabricCartridgeSlotEpFsmStageName ::= TEXTUAL-CONVENTION
    STATUS        current
    DESCRIPTION
        ""
    SYNTAX        INTEGER
    {
        nop(0),
        identifyBegin(1874),
        identifyExecuteLocal(1875),
        identifyExecutePeer(1876),
        identifyFail(1917),
        identifySuccess(1918)
    }

CucsFabricCartridgeSlotEpFsmTaskItem ::= TEXTUAL-CONVENTION
    STATUS        current
    DESCRIPTION
        ""
    SYNTAX        INTEGER
    {
        nop(0),
        identify(1874)
    }

CucsFabricCdpLinkPolicyAdminState ::= TEXTUAL-CONVENTION
    STATUS        current
    DESCRIPTION
        ""
    SYNTAX        INTEGER
    {
        enabled(1),
        disabled(2)
    }

CucsFabricCloudType ::= TEXTUAL-CONVENTION
    STATUS        current
    DESCRIPTION
        ""
    SYNTAX        BITS
    {
        ethlan(0),
        ethestclan(1),
        ethlanmon(2),
        fcsan(3),
        fcsanmon(4),
        fcestc(5)
    }

CucsFabricComputeEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricComputeEpType ::= TEXTUAL-CONVENTION
    STATUS        current
    DESCRIPTION
        ""
    SYNTAX        BITS
    {
        lan(0),
        san(1),
        ipc(2)
    }

CucsFabricComputeMSlotEpServerInstanceId ::= TEXTUAL-CONVENTION
    STATUS        current
    DESCRIPTION
        ""
    SYNTAX        Gauge32 (1..16)

CucsFabricComputeMSlotEpSlotId ::= TEXTUAL-CONVENTION
    STATUS        current
    DESCRIPTION
        ""
    SYNTAX        Gauge32 (1..8)

CucsFabricComputeMSlotEpFsmCurrentFsm ::= TEXTUAL-CONVENTION
    STATUS        current
    DESCRIPTION
        ""
    SYNTAX        INTEGER
    {
        nop(0),
        identify(1877)
    }

CucsFabricComputeMSlotEpFsmStageName ::= TEXTUAL-CONVENTION
    STATUS        current
    DESCRIPTION
        ""
    SYNTAX        INTEGER
    {
        nop(0),
        identifyBegin(1877),
        identifyExecuteLocal(1878),
        identifyExecutePeer(1879),
        identifyFail(1919),
        identifySuccess(1920)
    }

CucsFabricComputeMSlotEpFsmTaskItem ::= TEXTUAL-CONVENTION
    STATUS        current
    DESCRIPTION
        ""
    SYNTAX        INTEGER
    {
        nop(0),
        identify(1877)
    }

CucsFabricComputePhEpAdminState ::= TEXTUAL-CONVENTION
    STATUS        current
    DESCRIPTION
        ""
    SYNTAX        INTEGER
    {
        enabled(1),
        disabled(2),
        remove(3)
    }

CucsFabricComputePhEpSlotId ::= TEXTUAL-CONVENTION
    STATUS        current
    DESCRIPTION
        ""
    SYNTAX        Gauge32 (1..4)

CucsFabricComputePhEpOperationAdminState ::= TEXTUAL-CONVENTION
    STATUS        current
    DESCRIPTION
        ""
    SYNTAX        INTEGER
    {
        remoteTrigger(0),
        enabled(1),
        disabled(2),
        remove(3)
    }

CucsFabricComputeSlotEpSlotId ::= TEXTUAL-CONVENTION
    STATUS        current
    DESCRIPTION
        ""
    SYNTAX        Gauge32 (1..8)

CucsFabricComputeSlotEpFsmCurrentFsm ::= TEXTUAL-CONVENTION
    STATUS        current
    DESCRIPTION
        ""
    SYNTAX        INTEGER
    {
        nop(0),
        identify(20)
    }

CucsFabricComputeSlotEpFsmStageName ::= TEXTUAL-CONVENTION
    STATUS        current
    DESCRIPTION
        ""
    SYNTAX        INTEGER
    {
        nop(0),
        identifyBegin(20),
        identifyExecuteLocal(21),
        identifyExecutePeer(22),
        identifyFail(390),
        identifySuccess(391),
        identifyEvaluateIdentity(1691)
    }

CucsFabricComputeSlotEpFsmTaskItem ::= TEXTUAL-CONVENTION
    STATUS        current
    DESCRIPTION
        ""
    SYNTAX        INTEGER
    {
        nop(0),
        identify(20)
    }

CucsFabricConfMode ::= TEXTUAL-CONVENTION
    STATUS        current
    DESCRIPTION
        ""
    SYNTAX        INTEGER
    {
        none(0),
        logicalConfigInvalid(1),
        validatingConf(2),
        applyPhysTrans(3),
        confSwitch(4),
        confHifBreakout(5)
    }

CucsFabricConfState ::= TEXTUAL-CONVENTION
    STATUS        current
    DESCRIPTION
        ""
    SYNTAX        INTEGER
    {
        ok(0),
        logicalConfigInvalid(1)
    }

CucsFabricConfigIssues ::= TEXTUAL-CONVENTION
    STATUS        current
    DESCRIPTION
        ""
    SYNTAX        BITS
    {
        zoneLimit(0)
    }

CucsFabricConfigState ::= TEXTUAL-CONVENTION
    STATUS        current
    DESCRIPTION
        ""
    SYNTAX        INTEGER
    {
        applied(1),
        inconsistent(2)
    }

CucsFabricCryptographicAlgo ::= TEXTUAL-CONVENTION
    STATUS        current
    DESCRIPTION
        ""
    SYNTAX        INTEGER
    {
        aes128Cmac(0),
        aes256Cmac(1)
    }

CucsFabricDceSwSrvEpFec ::= TEXTUAL-CONVENTION
    STATUS        current
    DESCRIPTION
        ""
    SYNTAX        INTEGER
    {
        auto(0),
        cl74(1),
        cl91(2),
        rsCons16(3),
        rsIeee(4),
        off(5)
    }

CucsFabricDceSwSrvEpPortId ::= TEXTUAL-CONVENTION
    STATUS        current
    DESCRIPTION
        ""
    SYNTAX        Gauge32 (1..40)

CucsFabricDceSwSrvEpSlotId ::= TEXTUAL-CONVENTION
    STATUS        current
    DESCRIPTION
        ""
    SYNTAX        Gauge32 (1..1)

CucsFabricDceSwSrvEpOperationAdminState ::= TEXTUAL-CONVENTION
    STATUS        current
    DESCRIPTION
        ""
    SYNTAX        INTEGER
    {
        remoteTrigger(0),
        enabled(1),
        disabled(2),
        remove(3)
    }

CucsFabricDceSwSrvEpOperationPortId ::= TEXTUAL-CONVENTION
    STATUS        current
    DESCRIPTION
        ""
    SYNTAX        Gauge32 (1..48)

CucsFabricDceSwSrvEpOperationSlotId ::= TEXTUAL-CONVENTION
    STATUS        current
    DESCRIPTION
        ""
    SYNTAX        Gauge32 (1..4)

CucsFabricDceSwSrvPcAdminState ::= TEXTUAL-CONVENTION
    STATUS        current
    DESCRIPTION
        ""
    SYNTAX        INTEGER
    {
        enabled(1),
        disabled(2)
    }

CucsFabricDceSwSrvPcPortId ::= TEXTUAL-CONVENTION
    STATUS        current
    DESCRIPTION
        ""
    SYNTAX        Gauge32 (1024..4096)

CucsFabricDceSwSrvPcTransport ::= TEXTUAL-CONVENTION
    STATUS        current
    DESCRIPTION
        ""
    SYNTAX        BITS
    {
        ether(0),
        dce(1),
        fc(2)
    }

CucsFabricDceSwSrvPcEpFec ::= TEXTUAL-CONVENTION
    STATUS        current
    DESCRIPTION
        ""
    SYNTAX        INTEGER
    {
        auto(0),
        cl74(1),
        cl91(2),
        rsCons16(3),
        rsIeee(4),
        off(5)
    }

CucsFabricDceSwSrvPcEpPortId ::= TEXTUAL-CONVENTION
    STATUS        current
    DESCRIPTION
        ""
    SYNTAX        Gauge32 (1..48)

CucsFabricDceSwSrvPcEpSlotId ::= TEXTUAL-CONVENTION
    STATUS        current
    DESCRIPTION
        ""
    SYNTAX        Gauge32 (1..3)

CucsFabricDceSwSrvPcEpOperationAdminState ::= TEXTUAL-CONVENTION
    STATUS        current
    DESCRIPTION
        ""
    SYNTAX        INTEGER
    {
        enabled(1),
        disabled(2)
    }

CucsFabricDceSwSrvPcEpOperationPortId ::= TEXTUAL-CONVENTION
    STATUS        current
    DESCRIPTION
        ""
    SYNTAX        Gauge32 (1..48)

CucsFabricDceSwSrvPcEpOperationSlotId ::= TEXTUAL-CONVENTION
    STATUS        current
    DESCRIPTION
        ""
    SYNTAX        Gauge32 (1..4)

CucsFabricDceSwSrvPcOperationAdminState ::= TEXTUAL-CONVENTION
    STATUS        current
    DESCRIPTION
        ""
    SYNTAX        INTEGER
    {
        enabled(1),
        disabled(2)
    }

CucsFabricDceSwSrvPcOperationIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricDceSwSrvPcOperationPortId ::= TEXTUAL-CONVENTION
    STATUS        current
    DESCRIPTION
        ""
    SYNTAX        Gauge32 (1024..4096)

CucsFabricDceSwSrvPcOperationTransport ::= TEXTUAL-CONVENTION
    STATUS        current
    DESCRIPTION
        ""
    SYNTAX        BITS
    {
        ether(0),
        dce(1),
        fc(2)
    }

CucsFabricDceSwSrvPcOperationType ::= TEXTUAL-CONVENTION
    STATUS        current
    DESCRIPTION
        ""
    SYNTAX        BITS
    {
        lan(0),
        san(1),
        ipc(2)
    }

CucsFabricDceSwSrvPcOperationFsmCurrentFsm ::= TEXTUAL-CONVENTION
    STATUS        current
    DESCRIPTION
        ""
    SYNTAX        INTEGER
    {
        nop(0),
        fiport(524)
    }

CucsFabricDceSwSrvPcOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricDefaultZoningState ::= TEXTUAL-CONVENTION
    STATUS        current
    DESCRIPTION
        ""
    SYNTAX        INTEGER
    {
        disabled(0),
        enabled(1)
    }

CucsFabricDirection ::= TEXTUAL-CONVENTION
    STATUS        current
    DESCRIPTION
        ""
    SYNTAX        INTEGER
    {
        receive(1),
        transmit(2)
    }

CucsFabricEnclosureSlotEpSlotId ::= TEXTUAL-CONVENTION
    STATUS        current
    DESCRIPTION
        ""
    SYNTAX        Gauge32 (1..8)

CucsFabricEpMgrFsmCurrentFsm ::= TEXTUAL-CONVENTION
    STATUS        current
    DESCRIPTION
        ""
    SYNTAX        INTEGER
    {
        nop(0),
        configure(1113)
    }

CucsFabricEpMgrFsmStageName ::= TEXTUAL-CONVENTION
    STATUS        current
    DESCRIPTION
        ""
    SYNTAX        INTEGER
    {
        nop(0),
        configureBegin(1113),
        configureValidateConfiguration(1114),
        configureApplyPhysical(1115),
        configureWaitOnPhys(1116),
        configureApplyConfig(1117),
        configureFail(1144),
        configureSuccess(1145)
    }

CucsFabricEpMgrFsmTaskFlags ::= TEXTUAL-CONVENTION
    STATUS        current
    DESCRIPTION
        ""
    SYNTAX        BITS
    {
        samDmeFabricEpMgrConfigurePhysChange(51),
        samDmeFabricEpMgrConfigureModification(52),
        samDmeFabricEpMgrConfigureEthServerConfig(53),
        samDmeFabricEpMgrConfigureEthUplinkConfig(54),
        samDmeFabricEpMgrConfigureFcUplinkConfig(55),
        samDmeFabricEpMgrConfigureEthStorageConfig(56),
        samDmeFabricEpMgrConfigureFcStorageConfig(57),
        samDmeFabricEpMgrConfigureEthMacsecConfig(58)
    }

CucsFabricEpMgrFsmTaskItem ::= TEXTUAL-CONVENTION
    STATUS        current
    DESCRIPTION
        ""
    SYNTAX        INTEGER
    {
        nop(0),
        configure(1078)
    }

CucsFabricEpVlanVlanType ::= TEXTUAL-CONVENTION
    STATUS        current
    DESCRIPTION
        ""
    SYNTAX        INTEGER
    {
        regular(0),
        default(1),
        native(2),
        fcoeuplinknative(3)
    }

CucsFabricEquipmentEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricEquipmentEpType ::= TEXTUAL-CONVENTION
    STATUS        current
    DESCRIPTION
        ""
    SYNTAX        BITS
    {
        lan(0),
        san(1),
        ipc(2)
    }

CucsFabricEstcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricEstcPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricEstcPcType ::= TEXTUAL-CONVENTION
    STATUS        current
    DESCRIPTION
        ""
    SYNTAX        BITS
    {
        lan(0),
        san(1),
        ipc(2)
    }

CucsFabricEthCdpPolicyProtocol ::= TEXTUAL-CONVENTION
    STATUS        current
    DESCRIPTION
        ""
    SYNTAX        INTEGER
    {
        unknown(0),
        udld(1),
        cdp(2)
    }

CucsFabricEthEstcTransport ::= TEXTUAL-CONVENTION
    STATUS        current
    DESCRIPTION
        ""
    SYNTAX        BITS
    {
        ether(0),
        dce(1),
        fc(2)
    }

CucsFabricEthEstcType ::= TEXTUAL-CONVENTION
    STATUS        current
    DESCRIPTION
        ""
    SYNTAX        BITS
    {
        lan(0),
        san(1),
        ipc(2)
    }

CucsFabricEthEstcEpPortId ::= TEXTUAL-CONVENTION
    STATUS        current
    DESCRIPTION
        ""
    SYNTAX        Gauge32 (1..40)

CucsFabricEthEstcEpPrio ::= TEXTUAL-CONVENTION
    STATUS        current
    DESCRIPTION
        ""
    SYNTAX        INTEGER
    {
        fc(1),
        platinum(2),
        gold(3),
        silver(4),
        bronze(5),
        bestEffort(6)
    }

CucsFabricEthEstcEpSlotId ::= TEXTUAL-CONVENTION
    STATUS        current
    DESCRIPTION
        ""
    SYNTAX        Gauge32 (1..3)

CucsFabricEthEstcEpTransport ::= TEXTUAL-CONVENTION
    STATUS        current
    DESCRIPTION
        ""
    SYNTAX        BITS
    {
        ether(0),
        dce(1),
        fc(2)
    }

CucsFabricEthEstcEpType ::= TEXTUAL-CONVENTION
    STATUS        current
    DESCRIPTION
        ""
    SYNTAX        BITS
    {
        lan(0),
        san(1),
        ipc(2)
    }

CucsFabricEthEstcEpOperationAdminState ::= TEXTUAL-CONVENTION
    STATUS        current
    DESCRIPTION
        ""
    SYNTAX        INTEGER
    {
        remoteTrigger(0),
        enabled(1),
        disabled(2),
        remove(3)
    }

CucsFabricEthEstcEpOperationPortId ::= TEXTUAL-CONVENTION
    STATUS        current
    DESCRIPTION
        ""
    SYNTAX        Gauge32 (1..48)

CucsFabricEthEstcEpOperationSlotId ::= TEXTUAL-CONVENTION
    STATUS        current
    DESCRIPTION
        ""
    SYNTAX        Gauge32 (1..4)

CucsFabricEthEstcEpOperationFsmCurrentFsm ::= TEXTUAL-CONVENTION
    STATUS        current
    DESCRIPTION
        ""
    SYNTAX        INTEGER
    {
        nop(0),
        fiport(524)
    }

CucsFabricEthEstcEpOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricEthEstcOperPortMode ::= TEXTUAL-CONVENTION
    STATUS        current
    DESCRIPTION
        ""
    SYNTAX        INTEGER
    {
        regularTrunk(1),
        regularAccess(2),
        promiscuousTrunk(3),
        promiscuousAccess(4)
    }

CucsFabricEthEstcPcAdminSpeed ::= TEXTUAL-CONVENTION
    STATUS        current
    DESCRIPTION
        ""
    SYNTAX        INTEGER
    {
        indeterminate(0),
        n1gbps(1),
        n10gbps(2),
        n20gbps(3),
        n40gbps(4),
        n25gbps(5),
        n100gbps(6),
        auto(7)
    }

CucsFabricEthEstcPcTransport ::= TEXTUAL-CONVENTION
    STATUS        current
    DESCRIPTION
        ""
    SYNTAX        BITS
    {
        ether(0),
        dce(1),
        fc(2)
    }

CucsFabricEthEstcPcEpPortId ::= TEXTUAL-CONVENTION
    STATUS        current
    DESCRIPTION
        ""
    SYNTAX        Gauge32 (1..40)

CucsFabricEthEstcPcEpSlotId ::= TEXTUAL-CONVENTION
    STATUS        current
    DESCRIPTION
        ""
    SYNTAX        Gauge32 (1..3)

CucsFabricEthEstcPcEpOperationAdminState ::= TEXTUAL-CONVENTION
    STATUS        current
    DESCRIPTION
        ""
    SYNTAX        INTEGER
    {
        enabled(1),
        disabled(2)
    }

CucsFabricEthEstcPcEpOperationPortId ::= TEXTUAL-CONVENTION
    STATUS        current
    DESCRIPTION
        ""
    SYNTAX        Gauge32 (1..48)

CucsFabricEthEstcPcEpOperationSlotId ::= TEXTUAL-CONVENTION
    STATUS        current
    DESCRIPTION
        ""
    SYNTAX        Gauge32 (1..5)

CucsFabricEthEstcPcOperationAdminState ::= TEXTUAL-CONVENTION
    STATUS        current
    DESCRIPTION
        ""
    SYNTAX        INTEGER
    {
        enabled(1),
        disabled(2)
    }

CucsFabricEthEstcPcOperationPortId ::= TEXTUAL-CONVENTION
    STATUS        current
    DESCRIPTION
        ""
    SYNTAX        Gauge32 (1..256)

CucsFabricEthEstcPcOperationFsmCurrentFsm ::= TEXTUAL-CONVENTION
    STATUS        current
    DESCRIPTION
        ""
    SYNTAX        INTEGER
    {
        nop(0),
        fiport(524)
    }

CucsFabricEthEstcPcOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricEthEstcPortMode ::= TEXTUAL-CONVENTION
    STATUS        current
    DESCRIPTION
        ""
    SYNTAX        INTEGER
    {
        trunk(1),
        access(2)
    }

CucsFabricEthFlowMonLanTransport ::= TEXTUAL-CONVENTION
    STATUS        current
    DESCRIPTION
        ""
    SYNTAX        BITS
    {
        ether(0),
        dce(1),
        fc(2)
    }

CucsFabricEthFlowMonLanType ::= TEXTUAL-CONVENTION
    STATUS        current
    DESCRIPTION
        ""
    SYNTAX        BITS
    {
        lan(0),
        san(1),
        ipc(2)
    }

CucsFabricEthFlowMonSourceType ::= TEXTUAL-CONVENTION
    STATUS        current
    DESCRIPTION
        ""
    SYNTAX        INTEGER
    {
        vnic(1),
        portProfile(2)
    }

CucsFabricEthFlowMonSrcRefType ::= TEXTUAL-CONVENTION
    STATUS        current
    DESCRIPTION
        ""
    SYNTAX        BITS
    {
        lan(0),
        san(1),
        ipc(2)
    }

CucsFabricEthLanTransport ::= TEXTUAL-CONVENTION
    STATUS        current
    DESCRIPTION
        ""
    SYNTAX        BITS
    {
        ether(0),
        dce(1),
        fc(2)
    }

CucsFabricEthLanEpVlanStatus ::= TEXTUAL-CONVENTION
    STATUS        current
    DESCRIPTION
        ""
    SYNTAX        INTEGER
    {
        ok(0),
        missingPrimary(1)
    }

CucsFabricEthLanEpOperationAdminState ::= TEXTUAL-CONVENTION
    STATUS        current
    DESCRIPTION
        ""
    SYNTAX        INTEGER
    {
        remoteTrigger(0),
        enabled(1),
        disabled(2),
        remove(3)
    }

CucsFabricEthLanEpOperationAutoNegotiate ::= TEXTUAL-CONVENTION
    STATUS        current
    DESCRIPTION
        ""
    SYNTAX        INTEGER
    {
        disabled(0),
        enabled(1),
        remoteAutoNeg(2)
    }

CucsFabricEthLanEpOperationPortId ::= TEXTUAL-CONVENTION
    STATUS        current
    DESCRIPTION
        ""
    SYNTAX        Gauge32 (1..48)

CucsFabricEthLanEpOperationSlotId ::= TEXTUAL-CONVENTION
    STATUS        current
    DESCRIPTION
        ""
    SYNTAX        Gauge32 (1..4)

CucsFabricEthLanEpOperationFsmCurrentFsm ::= TEXTUAL-CONVENTION
    STATUS        current
    DESCRIPTION
        ""
    SYNTAX        INTEGER
    {
        nop(0),
        fiport(524)
    }

CucsFabricEthLanEpOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricEthLanFlowMonTransport ::= TEXTUAL-CONVENTION
    STATUS        current
    DESCRIPTION
        ""
    SYNTAX        BITS
    {
        ether(0),
        dce(1),
        fc(2)
    }

CucsFabricEthLanFlowMonCollectorTransport ::= TEXTUAL-CONVENTION
    STATUS        current
    DESCRIPTION
        ""
    SYNTAX        BITS
    {
        ether(0),
        dce(1),
        fc(2)
    }

CucsFabricEthLanFlowMonExporterTransport ::= TEXTUAL-CONVENTION
    STATUS        current
    DESCRIPTION
        ""
    SYNTAX        BITS
    {
        ether(0),
        dce(1),
        fc(2)
    }

CucsFabricEthLanFlowMonSrcEpTransport ::= TEXTUAL-CONVENTION
    STATUS        current
    DESCRIPTION
        ""
    SYNTAX        BITS
    {
        ether(0),
        dce(1),
        fc(2)
    }

CucsFabricEthLanFlowMonitorTransport ::= TEXTUAL-CONVENTION
    STATUS        current
    DESCRIPTION
        ""
    SYNTAX        BITS
    {
        ether(0),
        dce(1),
        fc(2)
    }

CucsFabricEthLanFlowMonitoringType ::= TEXTUAL-CONVENTION
    STATUS        current
    DESCRIPTION
        ""
    SYNTAX        INTEGER
    {
        unknown(0),
        ethFlowMonitoring(1),
        span(2)
    }

CucsFabricEthLanPcTransport ::= TEXTUAL-CONVENTION
    STATUS        current
    DESCRIPTION
        ""
    SYNTAX        BITS
    {
        ether(0),
        dce(1),
        fc(2)
    }

CucsFabricEthLanPcVlanStatus ::= TEXTUAL-CONVENTION
    STATUS        current
    DESCRIPTION
        ""
    SYNTAX        INTEGER
    {
        ok(0),
        missingPrimary(1)
    }

CucsFabricEthLanPcEpOperationAdminState ::= TEXTUAL-CONVENTION
    STATUS        current
    DESCRIPTION
        ""
    SYNTAX        INTEGER
    {
        enabled(1),
        disabled(2)
    }

CucsFabricEthLanPcEpOperationPortId ::= TEXTUAL-CONVENTION
    STATUS        current
    DESCRIPTION
        ""
    SYNTAX        Gauge32 (1..48)

CucsFabricEthLanPcEpOperationSlotId ::= TEXTUAL-CONVENTION
    STATUS        current
    DESCRIPTION
        ""
    SYNTAX        Gauge32 (1..5)

CucsFabricEthLanPcOperationAdminState ::= TEXTUAL-CONVENTION
    STATUS        current
    DESCRIPTION
        ""
    SYNTAX        INTEGER
    {
        enabled(1),
        disabled(2)
    }

CucsFabricEthLanPcOperationPortId ::= TEXTUAL-CONVENTION
    STATUS        current
    DESCRIPTION
        ""
    SYNTAX        Gauge32 (1..256)

CucsFabricEthLanPcOperationFsmCurrentFsm ::= TEXTUAL-CONVENTION
    STATUS        current
    DESCRIPTION
        ""
    SYNTAX        INTEGER
    {
        nop(0),
        fiport(524)
    }

CucsFabricEthLanPcOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricEthLinkPolicyType ::= TEXTUAL-CONVENTION
    STATUS        current
    DESCRIPTION
        ""
    SYNTAX        BITS
    {
        lan(0),
        san(1),
        ipc(2)
    }

CucsFabricEthMonTransport ::= TEXTUAL-CONVENTION
    STATUS        current
    DESCRIPTION
        ""
    SYNTAX        BITS
    {
        ether(0),
        dce(1),
        fc(2)
    }

CucsFabricEthMonType ::= TEXTUAL-CONVENTION
    STATUS        current
    DESCRIPTION
        ""
    SYNTAX        BITS
    {
        lan(0),
        san(1),
        ipc(2)
    }

CucsFabricEthMonDestEpAdminSpeed ::= TEXTUAL-CONVENTION
    STATUS        current
    DESCRIPTION
        ""
    SYNTAX        INTEGER
    {
        indeterminate(0),
        n1gbps(1),
        n10gbps(2),
        n20gbps(3),
        n40gbps(4),
        n25gbps(5),
        n100gbps(6),
        auto(7)
    }

CucsFabricEthMonDestEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricEthMonDestEpPortId ::= TEXTUAL-CONVENTION
    STATUS        current
    DESCRIPTION
        ""
    SYNTAX        Gauge32 (1..40)

CucsFabricEthMonDestEpSlotId ::= TEXTUAL-CONVENTION
    STATUS        current
    DESCRIPTION
        ""
    SYNTAX        Gauge32 (1..3)

CucsFabricEthMonDestEpType ::= TEXTUAL-CONVENTION
    STATUS        current
    DESCRIPTION
        ""
    SYNTAX        BITS
    {
        lan(0),
        san(1),
        ipc(2)
    }

CucsFabricEthMonDestEpOperationAdminSpeed ::= TEXTUAL-CONVENTION
    STATUS        current
    DESCRIPTION
        ""
    SYNTAX        INTEGER
    {
        indeterminate(0),
        n1gbps(1),
        n10gbps(2),
        n20gbps(3),
        n40gbps(4)
    }

CucsFabricEthMonDestEpOperationAdminState ::= TEXTUAL-CONVENTION
    STATUS        current
    DESCRIPTION
        ""
    SYNTAX        INTEGER
    {
        enabled(1),
        disabled(2)
    }

CucsFabricEthMonDestEpOperationIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricEthMonDestEpOperationPortId ::= TEXTUAL-CONVENTION
    STATUS        current
    DESCRIPTION
        ""
    SYNTAX        Gauge32 (1..48)

CucsFabricEthMonDestEpOperationSlotId ::= TEXTUAL-CONVENTION
    STATUS        current
    DESCRIPTION
        ""
    SYNTAX        Gauge32 (1..4)

CucsFabricEthMonDestEpOperationType ::= TEXTUAL-CONVENTION
    STATUS        current
    DESCRIPTION
        ""
    SYNTAX        BITS
    {
        lan(0),
        san(1),
        ipc(2)
    }

CucsFabricEthMonFiltEpType ::= TEXTUAL-CONVENTION
    STATUS        current
    DESCRIPTION
        ""
    SYNTAX        BITS
    {
        lan(0),
        san(1),
        ipc(2)
    }

CucsFabricEthMonFiltRefType ::= TEXTUAL-CONVENTION
    STATUS        current
    DESCRIPTION
        ""
    SYNTAX        BITS
    {
        lan(0),
        san(1),
        ipc(2)
    }

CucsFabricEthMonLanTransport ::= TEXTUAL-CONVENTION
    STATUS        current
    DESCRIPTION
        ""
    SYNTAX        BITS
    {
        ether(0),
        dce(1),
        fc(2)
    }

CucsFabricEthMonLanType ::= TEXTUAL-CONVENTION
    STATUS        current
    DESCRIPTION
        ""
    SYNTAX        BITS
    {
        lan(0),
        san(1),
        ipc(2)
    }

CucsFabricEthMonOperationAdminState ::= TEXTUAL-CONVENTION
    STATUS        current
    DESCRIPTION
        ""
    SYNTAX        INTEGER
    {
        enabled(1),
        disabled(2)
    }

CucsFabricEthMonOperationOperState ::= TEXTUAL-CONVENTION
    STATUS        current
    DESCRIPTION
        ""
    SYNTAX        INTEGER
    {
        unknown(0),
        up(1),
        down(2),
        error(3)
    }

CucsFabricEthMonOperationOperStateReason ::= TEXTUAL-CONVENTION
    STATUS        current
    DESCRIPTION
        ""
    SYNTAX        INTEGER
    {
        active(0),
        noHardwareResource(1),
        noOperationalSrcDst(2),
        genericError(3),
        noSourcesConfigured(4),
        noDestinationConfigured(5),
        noSourceDestinationConfigured(6),
        sessionAdminShut(7),
        wrongDestinationMode(8),
        wrongSourceMode(9),
        tunnelMisconfDown(10),
        noFlowIdSpecified(11),
        unknown(12)
    }

CucsFabricEthMonOperationFsmCurrentFsm ::= TEXTUAL-CONVENTION
    STATUS        current
    DESCRIPTION
        ""
    SYNTAX        INTEGER
    {
        nop(0),
        fiport(524)
    }

CucsFabricEthMonOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricEthMonSrcEpType ::= TEXTUAL-CONVENTION
    STATUS        current
    DESCRIPTION
        ""
    SYNTAX        BITS
    {
        lan(0),
        san(1),
        ipc(2)
    }

CucsFabricEthMonSrcEpOperationAdminState ::= TEXTUAL-CONVENTION
    STATUS        current
    DESCRIPTION
        ""
    SYNTAX        INTEGER
    {
        remoteTrigger(0),
        enabled(1),
        disabled(2),
        remove(3)
    }

CucsFabricEthMonSrcRefType ::= TEXTUAL-CONVENTION
    STATUS        current
    DESCRIPTION
        ""
    SYNTAX        BITS
    {
        lan(0),
        san(1),
        ipc(2)
    }

CucsFabricEthPcProtocol ::= TEXTUAL-CONVENTION
    STATUS        current
    DESCRIPTION
        ""
    SYNTAX        INTEGER
    {
        static(1),
        lacp(2)
    }

CucsFabricEthPortOperationFsmCurrentFsm ::= TEXTUAL-CONVENTION
    STATUS        current
    DESCRIPTION
        ""
    SYNTAX        INTEGER
    {
        nop(0),
        fiport(524)
    }

CucsFabricEthPortOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricEthSourceType ::= TEXTUAL-CONVENTION
    STATUS        current
    DESCRIPTION
        ""
    SYNTAX        INTEGER
    {
        vnic(1),
        uplinkPort(2),
        vlan(3),
        serverPort(4),
        portChannel(5),
        hostPort(6),
        storage(7),
        nasPort(8),
        nasPortChannel(9),
        fcoeuplinkPortchannel(10),
        vmNic(11),
        vhba(20)
    }

CucsFabricEthTargetEpTransport ::= TEXTUAL-CONVENTION
    STATUS        current
    DESCRIPTION
        ""
    SYNTAX        BITS
    {
        ether(0),
        dce(1),
        fc(2)
    }

CucsFabricEthUdldPolicyProtocol ::= TEXTUAL-CONVENTION
    STATUS        current
    DESCRIPTION
        ""
    SYNTAX        INTEGER
    {
        unknown(0),
        udld(1),
        cdp(2)
    }

CucsFabricEthVlanPcTransport ::= TEXTUAL-CONVENTION
    STATUS        current
    DESCRIPTION
        ""
    SYNTAX        BITS
    {
        ether(0),
        dce(1),
        fc(2)
    }

CucsFabricEthVlanPortEpVlanStatus ::= TEXTUAL-CONVENTION
    STATUS        current
    DESCRIPTION
        ""
    SYNTAX        INTEGER
    {
        ok(0),
        missingPrimary(1)
    }

CucsFabricEtherRefLcCtrlState ::= TEXTUAL-CONVENTION
    STATUS        current
    DESCRIPTION
        ""
    SYNTAX        INTEGER
    {
        available(0),
        allocated(1),
        deallocated(2),
        repurposed(3)
    }

CucsFabricExternalLocale ::= TEXTUAL-CONVENTION
    STATUS        current
    DESCRIPTION
        ""
    SYNTAX        BITS
    {
        server(0),
        chassis(1),
        internal(2),
        external(3)
    }

CucsFabricExternalEpAdminState ::= TEXTUAL-CONVENTION
    STATUS        current
    DESCRIPTION
        ""
    SYNTAX        INTEGER
    {
        enabled(1),
        disabled(2)
    }

CucsFabricExternalEpLocale ::= TEXTUAL-CONVENTION
    STATUS        current
    DESCRIPTION
        ""
    SYNTAX        BITS
    {
        server(0),
        chassis(1),
        internal(2),
        external(3)
    }

CucsFabricExternalPcLocale ::= TEXTUAL-CONVENTION
    STATUS        current
    DESCRIPTION
        ""
    SYNTAX        BITS
    {
        server(0),
        chassis(1),
        internal(2),
        external(3)
    }

CucsFabricFIPortOperationFsmCurrentFsm ::= TEXTUAL-CONVENTION
    STATUS        current
    DESCRIPTION
        ""
    SYNTAX        INTEGER
    {
        nop(0),
        fiport(524)
    }

CucsFabricFIPortOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricFIPortOperationFsmTaskItem ::= TEXTUAL-CONVENTION
    STATUS        current
    DESCRIPTION
        ""
    SYNTAX        INTEGER
    {
        nop(0),
        fiport(524)
    }

CucsFabricFcBreakoutType ::= TEXTUAL-CONVENTION
    STATUS        current
    DESCRIPTION
        ""
    SYNTAX        INTEGER
    {
        unknown(0),
        n8g4x(1),
        n16g4x(2),
        n32g4x(3)
    }

CucsFabricFcEstcTransport ::= TEXTUAL-CONVENTION
    STATUS        current
    DESCRIPTION
        ""
    SYNTAX        BITS
    {
        ether(0),
        dce(1),
        fc(2)
    }

CucsFabricFcEstcType ::= TEXTUAL-CONVENTION
    STATUS        current
    DESCRIPTION
        ""
    SYNTAX        BITS
    {
        lan(0),
        san(1),
        ipc(2)
    }

CucsFabricFcEstcEpPortId ::= TEXTUAL-CONVENTION
    STATUS        current
    DESCRIPTION
        ""
    SYNTAX        Gauge32 (1..40)

CucsFabricFcEstcEpSlotId ::= TEXTUAL-CONVENTION
    STATUS        current
    DESCRIPTION
        ""
    SYNTAX        Gauge32 (2..5)

CucsFabricFcEstcEpOperationAdminState ::= TEXTUAL-CONVENTION
    STATUS        current
    DESCRIPTION
        ""
    SYNTAX        INTEGER
    {
        remoteTrigger(0),
        enabled(1),
        disabled(2),
        remove(3)
    }

CucsFabricFcEstcEpOperationPortId ::= TEXTUAL-CONVENTION
    STATUS        current
    DESCRIPTION
        ""
    SYNTAX        Gauge32 (1..48)

CucsFabricFcEstcEpOperationSlotId ::= TEXTUAL-CONVENTION
    STATUS        current
    DESCRIPTION
        ""
    SYNTAX        Gauge32 (1..5)

CucsFabricFcEstcEpOperationFsmCurrentFsm ::= TEXTUAL-CONVENTION
    STATUS        current
    DESCRIPTION
        ""
    SYNTAX        INTEGER
    {
        nop(0),
        fiport(524)
    }

CucsFabricFcEstcEpOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricFcMonTransport ::= TEXTUAL-CONVENTION
    STATUS        current
    DESCRIPTION
        ""
    SYNTAX        BITS
    {
        ether(0),
        dce(1),
        fc(2)
    }

CucsFabricFcMonType ::= TEXTUAL-CONVENTION
    STATUS        current
    DESCRIPTION
        ""
    SYNTAX        BITS
    {
        lan(0),
        san(1),
        ipc(2)
    }

CucsFabricFcMonDestEpAdminSpeed ::= TEXTUAL-CONVENTION
    STATUS        current
    DESCRIPTION
        ""
    SYNTAX        INTEGER
    {
        indeterminate(0),
        n1gbps(1),
        n2gbps(2),
        n4gbps(3),
        n8gbps(4),
        auto(5),
        n16gbps(6),
        n32gbps(7),
        n64gbps(8)
    }

CucsFabricFcMonDestEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricFcMonDestEpPortId ::= TEXTUAL-CONVENTION
    STATUS        current
    DESCRIPTION
        ""
    SYNTAX        Gauge32 (1..40)

CucsFabricFcMonDestEpSlotId ::= TEXTUAL-CONVENTION
    STATUS        current
    DESCRIPTION
        ""
    SYNTAX        Gauge32 (2..5)

CucsFabricFcMonDestEpType ::= TEXTUAL-CONVENTION
    STATUS        current
    DESCRIPTION
        ""
    SYNTAX        BITS
    {
        lan(0),
        san(1),
        ipc(2)
    }

CucsFabricFcMonDestEpOperationAdminSpeed ::= TEXTUAL-CONVENTION
    STATUS        current
    DESCRIPTION
        ""
    SYNTAX        INTEGER
    {
        indeterminate(0),
        n1gbps(1),
        n2gbps(2),
        n4gbps(3),
        n8gbps(4),
        auto(5),
        n16gbps(6)
    }

CucsFabricFcMonDestEpOperationAdminState ::= TEXTUAL-CONVENTION
    STATUS        current
    DESCRIPTION
        ""
    SYNTAX        INTEGER
    {
        enabled(1),
        disabled(2)
    }

CucsFabricFcMonDestEpOperationIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricFcMonDestEpOperationPortId ::= TEXTUAL-CONVENTION
    STATUS        current
    DESCRIPTION
        ""
    SYNTAX        Gauge32 (1..48)

CucsFabricFcMonDestEpOperationSlotId ::= TEXTUAL-CONVENTION
    STATUS        current
    DESCRIPTION
        ""
    SYNTAX        Gauge32 (1..5)

CucsFabricFcMonDestEpOperationType ::= TEXTUAL-CONVENTION
    STATUS        current
    DESCRIPTION
        ""
    SYNTAX        BITS
    {
        lan(0),
        san(1),
        ipc(2)
    }

CucsFabricFcMonFiltEpType ::= TEXTUAL-CONVENTION
    STATUS        current
    DESCRIPTION
        ""
    SYNTAX        BITS
    {
        lan(0),
        san(1),
        ipc(2)
    }

CucsFabricFcMonFiltRefType ::= TEXTUAL-CONVENTION
    STATUS        current
    DESCRIPTION
        ""
    SYNTAX        BITS
    {
        lan(0),
        san(1),
        ipc(2)
    }

CucsFabricFcMonOperationAdminState ::= TEXTUAL-CONVENTION
    STATUS        current
    DESCRIPTION
        ""
    SYNTAX        INTEGER
    {
        enabled(1),
        disabled(2)
    }

CucsFabricFcMonOperationOperState ::= TEXTUAL-CONVENTION
    STATUS        current
    DESCRIPTION
        ""
    SYNTAX        INTEGER
    {
        unknown(0),
        up(1),
        down(2),
        error(3)
    }

CucsFabricFcMonOperationOperStateReason ::= TEXTUAL-CONVENTION
    STATUS        current
    DESCRIPTION
        ""
    SYNTAX        INTEGER
    {
        active(0),
        noHardwareResource(1),
        noOperationalSrcDst(2),
        genericError(3),
        noSourcesConfigured(4),
        noDestinationConfigured(5),
        noSourceDestinationConfigured(6),
        sessionAdminShut(7),
        wrongDestinationMode(8),
        wrongSourceMode(9),
        tunnelMisconfDown(10),
        noFlowIdSpecified(11),
        unknown(12)
    }

CucsFabricFcMonOperationFsmCurrentFsm ::= TEXTUAL-CONVENTION
    STATUS        current
    DESCRIPTION
        ""
    SYNTAX        INTEGER
    {
        nop(0),
        fiport(524)
    }

CucsFabricFcMonOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricFcMonSanTransport ::= TEXTUAL-CONVENTION
    STATUS        current
    DESCRIPTION
        ""
    SYNTAX        BITS
    {
        ether(0),
        dce(1),
        fc(2)
    }

CucsFabricFcMonSanType ::= TEXTUAL-CONVENTION
    STATUS        current
    DESCRIPTION
        ""
    SYNTAX        BITS
    {
        lan(0),
        san(1),
        ipc(2)
    }

CucsFabricFcMonSrcEpType ::= TEXTUAL-CONVENTION
    STATUS        current
    DESCRIPTION
        ""
    SYNTAX        BITS
    {
        lan(0),
        san(1),
        ipc(2)
    }

CucsFabricFcMonSrcEpOperationAdminState ::= TEXTUAL-CONVENTION
    STATUS        current
    DESCRIPTION
        ""
    SYNTAX        INTEGER
    {
        remoteTrigger(0),
        enabled(1),
        disabled(2),
        remove(3)
    }

CucsFabricFcMonSrcRefType ::= TEXTUAL-CONVENTION
    STATUS        current
    DESCRIPTION
        ""
    SYNTAX        BITS
    {
        lan(0),
        san(1),
        ipc(2)
    }

CucsFabricFcPortOperationFsmCurrentFsm ::= TEXTUAL-CONVENTION
    STATUS        current
    DESCRIPTION
        ""
    SYNTAX        INTEGER
    {
        nop(0),
        fiport(524)
    }

CucsFabricFcPortOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricFcSanTransport ::= TEXTUAL-CONVENTION
    STATUS        current
    DESCRIPTION
        ""
    SYNTAX        BITS
    {
        ether(0),
        dce(1),
        fc(2)
    }

CucsFabricFcSanUplinkTrunking ::= TEXTUAL-CONVENTION
    STATUS        current
    DESCRIPTION
        ""
    SYNTAX        INTEGER
    {
        disabled(0),
        enabled(1)
    }

CucsFabricFcSanEpPortId ::= TEXTUAL-CONVENTION
    STATUS        current
    DESCRIPTION
        ""
    SYNTAX        Gauge32 (1..40)

CucsFabricFcSanEpSlotId ::= TEXTUAL-CONVENTION
    STATUS        current
    DESCRIPTION
        ""
    SYNTAX        Gauge32 (2..5)

CucsFabricFcSanEpOperationAdminState ::= TEXTUAL-CONVENTION
    STATUS        current
    DESCRIPTION
        ""
    SYNTAX        INTEGER
    {
        remoteTrigger(0),
        enabled(1),
        disabled(2),
        remove(3)
    }

CucsFabricFcSanEpOperationPortId ::= TEXTUAL-CONVENTION
    STATUS        current
    DESCRIPTION
        ""
    SYNTAX        Gauge32 (1..48)

CucsFabricFcSanEpOperationSlotId ::= TEXTUAL-CONVENTION
    STATUS        current
    DESCRIPTION
        ""
    SYNTAX        Gauge32 (1..5)

CucsFabricFcSanEpOperationFsmCurrentFsm ::= TEXTUAL-CONVENTION
    STATUS        current
    DESCRIPTION
        ""
    SYNTAX        INTEGER
    {
        nop(0),
        fiport(524)
    }

CucsFabricFcSanEpOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricFcSanPcTransport ::= TEXTUAL-CONVENTION
    STATUS        current
    DESCRIPTION
        ""
    SYNTAX        BITS
    {
        ether(0),
        dce(1),
        fc(2)
    }

CucsFabricFcSanPcEpPortId ::= TEXTUAL-CONVENTION
    STATUS        current
    DESCRIPTION
        ""
    SYNTAX        Gauge32 (1..40)

CucsFabricFcSanPcEpSlotId ::= TEXTUAL-CONVENTION
    STATUS        current
    DESCRIPTION
        ""
    SYNTAX        Gauge32 (2..5)

CucsFabricFcSanPcEpOperationAdminState ::= TEXTUAL-CONVENTION
    STATUS        current
    DESCRIPTION
        ""
    SYNTAX        INTEGER
    {
        enabled(1),
        disabled(2)
    }

CucsFabricFcSanPcEpOperationPortId ::= TEXTUAL-CONVENTION
    STATUS        current
    DESCRIPTION
        ""
    SYNTAX        Gauge32 (1..48)

CucsFabricFcSanPcEpOperationSlotId ::= TEXTUAL-CONVENTION
    STATUS        current
    DESCRIPTION
        ""
    SYNTAX        Gauge32 (1..5)

CucsFabricFcSanPcOperationAdminState ::= TEXTUAL-CONVENTION
    STATUS        current
    DESCRIPTION
        ""
    SYNTAX        INTEGER
    {
        enabled(1),
        disabled(2)
    }

CucsFabricFcSanPcOperationPortId ::= TEXTUAL-CONVENTION
    STATUS        current
    DESCRIPTION
        ""
    SYNTAX        Gauge32 (1..256)

CucsFabricFcSanPcOperationFsmCurrentFsm ::= TEXTUAL-CONVENTION
    STATUS        current
    DESCRIPTION
        ""
    SYNTAX        INTEGER
    {
        nop(0),
        fiport(524)
    }

CucsFabricFcSanPcOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricFcSourceType ::= TEXTUAL-CONVENTION
    STATUS        current
    DESCRIPTION
        ""
    SYNTAX        INTEGER
    {
        vhba(1),
        uplinkPort(2),
        vsan(3),
        storage(4),
        portChannel(5)
    }

CucsFabricFcVsanPcTransport ::= TEXTUAL-CONVENTION
    STATUS        current
    DESCRIPTION
        ""
    SYNTAX        BITS
    {
        ether(0),
        dce(1),
        fc(2)
    }

CucsFabricFcVsanPortEpPortId ::= TEXTUAL-CONVENTION
    STATUS        current
    DESCRIPTION
        ""
    SYNTAX        Gauge32 (1..256)

CucsFabricFcVsanPortEpSlotId ::= TEXTUAL-CONVENTION
    STATUS        current
    DESCRIPTION
        ""
    SYNTAX        Gauge32 (0..5)

CucsFabricFcZoneConfigState ::= TEXTUAL-CONVENTION
    STATUS        current
    DESCRIPTION
        ""
    SYNTAX        INTEGER
    {
        notApplied(0),
        applied(1),
        applying(2),
        failedToApply(11)
    }

CucsFabricFcZoneOperState ::= TEXTUAL-CONVENTION
    STATUS        current
    DESCRIPTION
        ""
    SYNTAX        INTEGER
    {
        notActive(4),
        active(5),
        created(6),
        createFailed(7),
        deleted(8),
        zoneMergeFailure(9)
    }

CucsFabricFcZoneProfileFsmCurrentFsm ::= TEXTUAL-CONVENTION
    STATUS        current
    DESCRIPTION
        ""
    SYNTAX        INTEGER
    {
        nop(0),
        configure(642)
    }

CucsFabricFcZoneProfileFsmStageName ::= TEXTUAL-CONVENTION
    STATUS        current
    DESCRIPTION
        ""
    SYNTAX        INTEGER
    {
        nop(0),
        configureBegin(642),
        configureValidation(643),
        configureConsumerVsanDeployment(644),
        configureWaitForRecvVsan(645),
        configureApplyConfig(646),
        configureFail(656),
        configureSuccess(657)
    }

CucsFabricFcZoneProfileFsmTaskItem ::= TEXTUAL-CONVENTION
    STATUS        current
    DESCRIPTION
        ""
    SYNTAX        INTEGER
    {
        nop(0),
        configure(642)
    }

CucsFabricFcZoneSharingMode ::= TEXTUAL-CONVENTION
    STATUS        current
    DESCRIPTION
        ""
    SYNTAX        INTEGER
    {
        coalesce(0),
        clearUnmanagedZoneActive(1),
        clearUnmanagedZoneAll(2)
    }

CucsFabricFcoeEstcEpPortId ::= TEXTUAL-CONVENTION
    STATUS        current
    DESCRIPTION
        ""
    SYNTAX        Gauge32 (1..40)

CucsFabricFcoeEstcEpSlotId ::= TEXTUAL-CONVENTION
    STATUS        current
    DESCRIPTION
        ""
    SYNTAX        Gauge32 (1..3)

CucsFabricFcoeEstcEpOperationAdminState ::= TEXTUAL-CONVENTION
    STATUS        current
    DESCRIPTION
        ""
    SYNTAX        INTEGER
    {
        remoteTrigger(0),
        enabled(1),
        disabled(2),
        remove(3)
    }

CucsFabricFcoeEstcEpOperationPortId ::= TEXTUAL-CONVENTION
    STATUS        current
    DESCRIPTION
        ""
    SYNTAX        Gauge32 (1..48)

CucsFabricFcoeEstcEpOperationSlotId ::= TEXTUAL-CONVENTION
    STATUS        current
    DESCRIPTION
        ""
    SYNTAX        Gauge32 (1..4)

CucsFabricFcoeEstcEpOperationFsmCurrentFsm ::= TEXTUAL-CONVENTION
    STATUS        current
    DESCRIPTION
        ""
    SYNTAX        INTEGER
    {
        nop(0),
        fiport(524)
    }

CucsFabricFcoeEstcEpOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricFcoeSanEpPortId ::= TEXTUAL-CONVENTION
    STATUS        current
    DESCRIPTION
        ""
    SYNTAX        Gauge32 (1..48)

CucsFabricFcoeSanEpSlotId ::= TEXTUAL-CONVENTION
    STATUS        current
    DESCRIPTION
        ""
    SYNTAX        Gauge32 (1..5)

CucsFabricFcoeSanEpOperationAdminState ::= TEXTUAL-CONVENTION
    STATUS        current
    DESCRIPTION
        ""
    SYNTAX        INTEGER
    {
        remoteTrigger(0),
        enabled(1),
        disabled(2),
        remove(3)
    }

CucsFabricFcoeSanEpOperationPortId ::= TEXTUAL-CONVENTION
    STATUS        current
    DESCRIPTION
        ""
    SYNTAX        Gauge32 (1..48)

CucsFabricFcoeSanEpOperationSlotId ::= TEXTUAL-CONVENTION
    STATUS        current
    DESCRIPTION
        ""
    SYNTAX        Gauge32 (1..4)

CucsFabricFcoeSanEpOperationFsmCurrentFsm ::= TEXTUAL-CONVENTION
    STATUS        current
    DESCRIPTION
        ""
    SYNTAX        INTEGER
    {
        nop(0),
        fiport(524)
    }

CucsFabricFcoeSanEpOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricFcoeSanPcTransport ::= TEXTUAL-CONVENTION
    STATUS        current
    DESCRIPTION
        ""
    SYNTAX        BITS
    {
        ether(0),
        dce(1),
        fc(2)
    }

CucsFabricFcoeSanPcEpPortId ::= TEXTUAL-CONVENTION
    STATUS        current
    DESCRIPTION
        ""
    SYNTAX        Gauge32 (1..48)

CucsFabricFcoeSanPcEpSlotId ::= TEXTUAL-CONVENTION
    STATUS        current
    DESCRIPTION
        ""
    SYNTAX        Gauge32 (1..5)

CucsFabricFcoeSanPcEpOperationAdminState ::= TEXTUAL-CONVENTION
    STATUS        current
    DESCRIPTION
        ""
    SYNTAX        INTEGER
    {
        enabled(1),
        disabled(2)
    }

CucsFabricFcoeSanPcEpOperationPortId ::= TEXTUAL-CONVENTION
    STATUS        current
    DESCRIPTION
        ""
    SYNTAX        Gauge32 (1..48)

CucsFabricFcoeSanPcEpOperationSlotId ::= TEXTUAL-CONVENTION
    STATUS        current
    DESCRIPTION
        ""
    SYNTAX        Gauge32 (1..5)

CucsFabricFcoeSanPcOperationAdminState ::= TEXTUAL-CONVENTION
    STATUS        current
    DESCRIPTION
        ""
    SYNTAX        INTEGER
    {
        enabled(1),
        disabled(2)
    }

CucsFabricFcoeSanPcOperationPortId ::= TEXTUAL-CONVENTION
    STATUS        current
    DESCRIPTION
        ""
    SYNTAX        Gauge32 (1..256)

CucsFabricFcoeSanPcOperationFsmCurrentFsm ::= TEXTUAL-CONVENTION
    STATUS        current
    DESCRIPTION
        ""
    SYNTAX        INTEGER
    {
        nop(0),
        fiport(524)
    }

CucsFabricFcoeSanPcOperationFsmStageName ::= TEXTUAL-CONVENTION
    STATUS        current
    DESCRIPTION
        ""
    SYNTAX        INTEGER
    {
        nop(0),
        fiportBegin(524),
        fiportRoleConfig(525),
        fiportPushVxan(526),
        fiportWait(527),
        fiportVxanConfig(528),
        fiportCleanUp(529),
        fiportFail(532),
        fiportSuccess(533),
        fiportPushPolicies(640),
        fiportWaitForPolicies(641)
    }

CucsFabricFcoeVsanPcTransport ::= TEXTUAL-CONVENTION
    STATUS        current
    DESCRIPTION
        ""
    SYNTAX        BITS
    {
        ether(0),
        dce(1),
        fc(2)
    }

CucsFabricFcoeVsanPortEpPortId ::= TEXTUAL-CONVENTION
    STATUS        current
    DESCRIPTION
        ""
    SYNTAX        Gauge32 (1..256)

CucsFabricFcoeVsanPortEpSlotId ::= TEXTUAL-CONVENTION
    STATUS        current
    DESCRIPTION
        ""
    SYNTAX        Gauge32 (1..5)

CucsFabricFillPattern ::= TEXTUAL-CONVENTION
    STATUS        current
    DESCRIPTION
        ""
    SYNTAX        INTEGER
    {
        idle(0),
        arbff(1)
    }

CucsFabricFlowMonAdminState ::= TEXTUAL-CONVENTION
    STATUS        current
    DESCRIPTION
        ""
    SYNTAX        INTEGER
    {
        enabled(1),
        disabled(2)
    }

CucsFabricFlowMonCollectorLocale ::= TEXTUAL-CONVENTION
    STATUS        current
    DESCRIPTION
        ""
    SYNTAX        BITS
    {
        server(0),
        chassis(1),
        internal(2),
        external(3)
    }

CucsFabricFlowMonDefType ::= TEXTUAL-CONVENTION
    STATUS        current
    DESCRIPTION
        ""
    SYNTAX        INTEGER
    {
        systemDefined(1),
        userDefined(2)
    }

CucsFabricFlowMonIpv4Keys ::= TEXTUAL-CONVENTION
    STATUS        current
    DESCRIPTION
        ""
    SYNTAX        BITS
    {
        ipv4SrcAddress(0),
        ipv4DestAddress(1),
        ipProtocol(2),
        ipTos(3),
        srcPort(4),
        destPort(5)
    }

CucsFabricFlowMonIpv6Keys ::= TEXTUAL-CONVENTION
    STATUS        current
    DESCRIPTION
        ""
    SYNTAX        BITS
    {
        ipv6SrcAddress(0),
        ipv6DestAddress(1),
        ipProtocol(2),
        srcPort(4),
        destPort(5)
    }

CucsFabricFlowMonKeyType ::= TEXTUAL-CONVENTION
    STATUS        current
    DESCRIPTION
        ""
    SYNTAX        INTEGER
    {
        l2keys(0),
        ipv4keys(1),
        ipv6keys(2)
    }

CucsFabricFlowMonL2Keys ::= TEXTUAL-CONVENTION
    STATUS        current
    DESCRIPTION
        ""
    SYNTAX        BITS
    {
        ethertype(0),
        destMacAddress(1),
        srcMacAddress(2)
    }

CucsFabricFlowMonNonKeys ::= TEXTUAL-CONVENTION
    STATUS        current
    DESCRIPTION
        ""
    SYNTAX        BITS
    {
        counterPacketsLong(0),
        counterBytesLong(1),
        sysUptimeFirst(2),
        sysUptimeLast(3)
    }

CucsFabricFlowMonitoringCategoryAdminState ::= TEXTUAL-CONVENTION
    STATUS        current
    DESCRIPTION
        ""
    SYNTAX        INTEGER
    {
        enabled(1),
        disabled(2)
    }

CucsFabricGroupReqIssues ::= TEXTUAL-CONVENTION
    STATUS        current
    DESCRIPTION
        ""
    SYNTAX        BITS
    {
        permitUnresolved(0)
    }

CucsFabricHideKeyHexStringInFIType ::= TEXTUAL-CONVENTION
    STATUS        current
    DESCRIPTION
        ""
    SYNTAX        INTEGER
    {
        no(0),
        yes(1)
    }

CucsFabricHostPortId ::= TEXTUAL-CONVENTION
    STATUS        current
    DESCRIPTION
        ""
    SYNTAX        INTEGER
    {
        any(0),
        n1(1),
        n2(2),
        none(10)
    }

CucsFabricInternalLocale ::= TEXTUAL-CONVENTION
    STATUS        current
    DESCRIPTION
        ""
    SYNTAX        BITS
    {
        server(0),
        chassis(1),
        internal(2),
        external(3)
    }

CucsFabricInternalDceSrvTransport ::= TEXTUAL-CONVENTION
    STATUS        current
    DESCRIPTION
        ""
    SYNTAX        BITS
    {
        ether(0),
        dce(1),
        fc(2)
    }

CucsFabricInternalDceSrvType ::= TEXTUAL-CONVENTION
    STATUS        current
    DESCRIPTION
        ""
    SYNTAX        BITS
    {
        lan(0),
        san(1),
        ipc(2)
    }

CucsFabricInternalEpAdminState ::= TEXTUAL-CONVENTION
    STATUS        current
    DESCRIPTION
        ""
    SYNTAX        INTEGER
    {
        enabled(1),
        disabled(2)
    }

CucsFabricInternalEpLocale ::= TEXTUAL-CONVENTION
    STATUS        current
    DESCRIPTION
        ""
    SYNTAX        BITS
    {
        server(0),
        chassis(1),
        internal(2),
        external(3)
    }

CucsFabricInternalPcAutoNegotiate ::= TEXTUAL-CONVENTION
    STATUS        current
    DESCRIPTION
        ""
    SYNTAX        INTEGER
    {
        disabled(0),
        enabled(1)
    }

CucsFabricInternalPcLocale ::= TEXTUAL-CONVENTION
    STATUS        current
    DESCRIPTION
        ""
    SYNTAX        BITS
    {
        server(0),
        chassis(1),
        internal(2),
        external(3)
    }

CucsFabricLacpRate ::= TEXTUAL-CONVENTION
    STATUS        current
    DESCRIPTION
        ""
    SYNTAX        INTEGER
    {
        normal(0),
        fast(1)
    }

CucsFabricLacpSuspend ::= TEXTUAL-CONVENTION
    STATUS        current
    DESCRIPTION
        ""
    SYNTAX        INTEGER
    {
        false(0),
        true(1)
    }

CucsFabricLanType ::= TEXTUAL-CONVENTION
    STATUS        current
    DESCRIPTION
        ""
    SYNTAX        BITS
    {
        lan(0),
        san(1),
        ipc(2)
    }

CucsFabricLanCloudQinQForwarding ::= TEXTUAL-CONVENTION
    STATUS        current
    DESCRIPTION
        ""
    SYNTAX        INTEGER
    {
        enabled(1),
        disabled(2)
    }

CucsFabricLanCloudFabricPcVhbaReset ::= TEXTUAL-CONVENTION
    STATUS        current
    DESCRIPTION
        ""
    SYNTAX        INTEGER
    {
        enabled(1),
        disabled(2)
    }

CucsFabricLanCloudServiceUnsupportedTransceiver ::= TEXTUAL-CONVENTION
    STATUS        current
    DESCRIPTION
        ""
    SYNTAX        INTEGER
    {
        enabled(1),
        disabled(2)
    }

CucsFabricLanCloudVlanCompression ::= TEXTUAL-CONVENTION
    STATUS        current
    DESCRIPTION
        ""
    SYNTAX        INTEGER
    {
        enabled(1),
        disabled(2)
    }

CucsFabricLanCloudFsmCurrentFsm ::= TEXTUAL-CONVENTION
    STATUS        current
    DESCRIPTION
        ""
    SYNTAX        INTEGER
    {
        nop(0),
        switchMode(184)
    }

CucsFabricLanCloudFsmStageName ::= TEXTUAL-CONVENTION
    STATUS        current
    DESCRIPTION
        ""
    SYNTAX        INTEGER
    {
        nop(0),
        switchModeBegin(184),
        switchModeSwConfigPeer(185),
        switchModeSwConfigLocal(186),
        switchModeFail(392),
        switchModeSuccess(393),
        switchModeWaitForUserAck(2247)
    }

CucsFabricLanCloudFsmTaskItem ::= TEXTUAL-CONVENTION
    STATUS        current
    DESCRIPTION
        ""
    SYNTAX        INTEGER
    {
        nop(0),
        switchMode(184)
    }

CucsFabricLanCloudPolicyVlanCompression ::= TEXTUAL-CONVENTION
    STATUS        current
    DESCRIPTION
        ""
    SYNTAX        INTEGER
    {
        enabled(1),
        disabled(2)
    }

CucsFabricLanConfigIssues ::= TEXTUAL-CONVENTION
    STATUS        current
    DESCRIPTION
        ""
    SYNTAX        BITS
    {
        vlanCompGrpCountExceedsLimit(0)
    }

CucsFabricLanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricLanEpType ::= TEXTUAL-CONVENTION
    STATUS        current
    DESCRIPTION
        ""
    SYNTAX        BITS
    {
        lan(0),
        san(1),
        ipc(2)
    }

CucsFabricLanFlowMonType ::= TEXTUAL-CONVENTION
    STATUS        current
    DESCRIPTION
        ""
    SYNTAX        BITS
    {
        lan(0),
        san(1),
        ipc(2)
    }

CucsFabricLanFlowMonCollectorType ::= TEXTUAL-CONVENTION
    STATUS        current
    DESCRIPTION
        ""
    SYNTAX        BITS
    {
        lan(0),
        san(1),
        ipc(2)
    }

CucsFabricLanFlowMonExporterType ::= TEXTUAL-CONVENTION
    STATUS        current
    DESCRIPTION
        ""
    SYNTAX        BITS
    {
        lan(0),
        san(1),
        ipc(2)
    }

CucsFabricLanFlowMonSrcEpType ::= TEXTUAL-CONVENTION
    STATUS        current
    DESCRIPTION
        ""
    SYNTAX        BITS
    {
        lan(0),
        san(1),
        ipc(2)
    }

CucsFabricLanFlowMonitorType ::= TEXTUAL-CONVENTION
    STATUS        current
    DESCRIPTION
        ""
    SYNTAX        BITS
    {
        lan(0),
        san(1),
        ipc(2)
    }

CucsFabricLanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricLanPcType ::= TEXTUAL-CONVENTION
    STATUS        current
    DESCRIPTION
        ""
    SYNTAX        BITS
    {
        lan(0),
        san(1),
        ipc(2)
    }

CucsFabricLifeCycle ::= TEXTUAL-CONVENTION
    STATUS        current
    DESCRIPTION
        ""
    SYNTAX        INTEGER
    {
        inService(1),
        outOfService(2),
        outOfServiceSlave(3)
    }

CucsFabricLifeTimeInfinite ::= TEXTUAL-CONVENTION
    STATUS        current
    DESCRIPTION
        ""
    SYNTAX        INTEGER
    {
        enabled(1),
        disabled(2)
    }

CucsFabricMacSecAdminState ::= TEXTUAL-CONVENTION
    STATUS        current
    DESCRIPTION
        ""
    SYNTAX        INTEGER
    {
        enabled(1),
        disabled(2)
    }

CucsFabricMacSecKeyEncryptType ::= TEXTUAL-CONVENTION
    STATUS        current
    DESCRIPTION
        ""
    SYNTAX        INTEGER
    {
        unencrypted(0),
        type7(1),
        type6(2)
    }

CucsFabricMacSecPolicyCipherSuite ::= TEXTUAL-CONVENTION
    STATUS        current
    DESCRIPTION
        ""
    SYNTAX        INTEGER
    {
        gcmAesXpn256(0),
        gcmAesXpn128(1),
        gcmAes256(2),
        gcmAes128(3)
    }

CucsFabricMacSecPolicyConfOffSet ::= TEXTUAL-CONVENTION
    STATUS        current
    DESCRIPTION
        ""
    SYNTAX        INTEGER
    {
        confOffset0(0),
        confOffset30(1),
        confOffset50(2)
    }

CucsFabricMacSecPolicyIncludeIcvParam ::= TEXTUAL-CONVENTION
    STATUS        current
    DESCRIPTION
        ""
    SYNTAX        INTEGER
    {
        no(0),
        yes(1)
    }

CucsFabricMacSecPolicySecurityPolicy ::= TEXTUAL-CONVENTION
    STATUS        current
    DESCRIPTION
        ""
    SYNTAX        INTEGER
    {
        shouldSecure(0),
        mustSecure(1)
    }

CucsFabricMemberStatus ::= TEXTUAL-CONVENTION
    STATUS        current
    DESCRIPTION
        ""
    SYNTAX        INTEGER
    {
        up(0),
        down(1)
    }

CucsFabricMembershipStatus ::= TEXTUAL-CONVENTION
    STATUS        current
    DESCRIPTION
        ""
    SYNTAX        INTEGER
    {
        down(1),
        up(2),
        hotStandby(3),
        suspended(4),
        individual(5),
        moduleRemoved(6),
        incompatibleSpeed(7),
        unknown(8)
    }

CucsFabricMonAdminState ::= TEXTUAL-CONVENTION
    STATUS        current
    DESCRIPTION
        ""
    SYNTAX        INTEGER
    {
        enabled(1),
        disabled(2)
    }

CucsFabricMonOperState ::= TEXTUAL-CONVENTION
    STATUS        current
    DESCRIPTION
        ""
    SYNTAX        INTEGER
    {
        unknown(0),
        up(1),
        down(2),
        error(3)
    }

CucsFabricMonOperStateReason ::= TEXTUAL-CONVENTION
    STATUS        current
    DESCRIPTION
        ""
    SYNTAX        INTEGER
    {
        active(0),
        noHardwareResource(1),
        noOperationalSrcDst(2),
        genericError(3),
        noSourcesConfigured(4),
        noDestinationConfigured(5),
        noSourceDestinationConfigured(6),
        sessionAdminShut(7),
        wrongDestinationMode(8),
        wrongSourceMode(9),
        tunnelMisconfDown(10),
        noFlowIdSpecified(11),
        unknown(12),
        noValidIPAddress(13),
        noValidOriginIP(14),
        noRouteToDestIP(20),
        arpNotResolved(21),
        egressIfNotResolved(22),
        sviNotRetrived(23)
    }

CucsFabricMonSpanCtrlPkts ::= TEXTUAL-CONVENTION
    STATUS        current
    DESCRIPTION
        ""
    SYNTAX        INTEGER
    {
        enabled(1),
        disabled(2)
    }

CucsFabricMulticastPolicySourceIpProxyState ::= TEXTUAL-CONVENTION
    STATUS        current
    DESCRIPTION
        ""
    SYNTAX        INTEGER
    {
        enabled(0),
        disabled(1)
    }

CucsFabricNFExporterVersion ::= TEXTUAL-CONVENTION
    STATUS        current
    DESCRIPTION
        ""
    SYNTAX        INTEGER
    {
        v9(1),
        ipfix(2)
    }

CucsFabricNFTransport ::= TEXTUAL-CONVENTION
    STATUS        current
    DESCRIPTION
        ""
    SYNTAX        INTEGER
    {
        udp(1),
        sctp(2)
    }

CucsFabricNetGroupSwitchId ::= TEXTUAL-CONVENTION
    STATUS        current
    DESCRIPTION
        ""
    SYNTAX        INTEGER
    {
        none(0),
        a(1),
        b(2),
        mgmt(3)
    }

CucsFabricNetGroupConfigIssues ::= TEXTUAL-CONVENTION
    STATUS        current
    DESCRIPTION
        ""
    SYNTAX        BITS
    {
        nativeVlanNotFound(0)
    }

CucsFabricNetGroupRefType ::= TEXTUAL-CONVENTION
    STATUS        current
    DESCRIPTION
        ""
    SYNTAX        INTEGER
    {
        policyLocal(0),
        policyGlobal(1),
        policyExternal(2)
    }

CucsFabricNetGroupType ::= TEXTUAL-CONVENTION
    STATUS        current
    DESCRIPTION
        ""
    SYNTAX        BITS
    {
        mgmt(0),
        vlanCompression(1),
        vlanUncompressed(2),
        vpCompression(3)
    }

CucsFabricNetflowCollectorFlowProtocol ::= TEXTUAL-CONVENTION
    STATUS        current
    DESCRIPTION
        ""
    SYNTAX        INTEGER
    {
        netflow(1)
    }

CucsFabricNetflowConfigIssues ::= TEXTUAL-CONVENTION
    STATUS        current
    DESCRIPTION
        ""
    SYNTAX        BITS
    {
        monitorUnresolved(0),
        exporterUnresolved(1),
        exporterProfileUnresolved(2),
        collectorUnresolved(3),
        sourceVlanUnresolved(4)
    }

CucsFabricNetflowMonExporterProtocol ::= TEXTUAL-CONVENTION
    STATUS        current
    DESCRIPTION
        ""
    SYNTAX        INTEGER
    {
        netflow(1)
    }

CucsFabricNetflowMonSessionAdminState ::= TEXTUAL-CONVENTION
    STATUS        current
    DESCRIPTION
        ""
    SYNTAX        INTEGER
    {
        enabled(1),
        disabled(2)
    }

CucsFabricNetflowMonSessionProtocol ::= TEXTUAL-CONVENTION
    STATUS        current
    DESCRIPTION
        ""
    SYNTAX        INTEGER
    {
        netflow(1)
    }

CucsFabricNetflowMonSrcEpProtocol ::= TEXTUAL-CONVENTION
    STATUS        current
    DESCRIPTION
        ""
    SYNTAX        INTEGER
    {
        netflow(1)
    }

CucsFabricNetflowMonSrcRefProtocol ::= TEXTUAL-CONVENTION
    STATUS        current
    DESCRIPTION
        ""
    SYNTAX        INTEGER
    {
        netflow(1)
    }

CucsFabricNetflowMonitorFlowMonProtocol ::= TEXTUAL-CONVENTION
    STATUS        current
    DESCRIPTION
        ""
    SYNTAX        INTEGER
    {
        netflow(1)
    }

CucsFabricOperState ::= TEXTUAL-CONVENTION
    STATUS        current
    DESCRIPTION
        ""
    SYNTAX        INTEGER
    {
        unknown(0),
        up(1),
        down(2),
        errorMisconfigured(3),
        failed(4)
    }

CucsFabricOwner ::= TEXTUAL-CONVENTION
    STATUS        current
    DESCRIPTION
        ""
    SYNTAX        INTEGER
    {
        policy(1),
        management(2)
    }

CucsFabricPIoEpAutoNegotiate ::= TEXTUAL-CONVENTION
    STATUS        current
    DESCRIPTION
        ""
    SYNTAX        INTEGER
    {
        disabled(0),
        enabled(1)
    }

CucsFabricPIoEpIfType ::= TEXTUAL-CONVENTION
    STATUS        current
    DESCRIPTION
        ""
    SYNTAX        INTEGER
    {
        unknown(0),
        physical(1),
        aggregation(2),
        virtual(3)
    }

CucsFabricPIoEpOperState ::= TEXTUAL-CONVENTION
    STATUS        current
    DESCRIPTION
        ""
    SYNTAX        INTEGER
    {
        unknown(0),
        up(1),
        down(2),
        errorMisconfigured(3),
        failed(4),
        errorUnsupportedMiniServerPort(5)
    }

CucsFabricPIoEpPortId ::= TEXTUAL-CONVENTION
    STATUS        current
    DESCRIPTION
        ""
    SYNTAX        Gauge32 (1..40)

CucsFabricPIoEpSlotId ::= TEXTUAL-CONVENTION
    STATUS        current
    DESCRIPTION
        ""
    SYNTAX        Gauge32 (1..3)

CucsFabricPathEpIfType ::= TEXTUAL-CONVENTION
    STATUS        current
    DESCRIPTION
        ""
    SYNTAX        INTEGER
    {
        unknown(0),
        physical(1),
        aggregation(2),
        virtual(3)
    }

CucsFabricPathEpLocale ::= TEXTUAL-CONVENTION
    STATUS        current
    DESCRIPTION
        ""
    SYNTAX        BITS
    {
        server(0),
        chassis(1),
        internal(2),
        external(3)
    }

CucsFabricPcConfigStatus ::= TEXTUAL-CONVENTION
    STATUS        current
    DESCRIPTION
        ""
    SYNTAX        INTEGER
    {
        applied(1),
        incompatibleSpeed(2)
    }

CucsFabricPermitStatus ::= TEXTUAL-CONVENTION
    STATUS        current
    DESCRIPTION
        ""
    SYNTAX        INTEGER
    {
        available(0),
        inUse(1),
        assigned(2)
    }

CucsFabricPinTargetAggrPortId ::= TEXTUAL-CONVENTION
    STATUS        current
    DESCRIPTION
        ""
    SYNTAX        Gauge32 (1..48)

CucsFabricPinTargetPortId ::= TEXTUAL-CONVENTION
    STATUS        current
    DESCRIPTION
        ""
    SYNTAX        Gauge32 (1..20)

CucsFabricPinTargetSlotId ::= TEXTUAL-CONVENTION
    STATUS        current
    DESCRIPTION
        ""
    SYNTAX        Gauge32 (1..2)

CucsFabricPolicyConfigIssues ::= TEXTUAL-CONVENTION
    STATUS        current
    DESCRIPTION
        ""
    SYNTAX        BITS
    {
        conflictingOrEmptyQuerierIp(0)
    }

CucsFabricPoolMemberConfigIssues ::= TEXTUAL-CONVENTION
    STATUS        current
    DESCRIPTION
        ""
    SYNTAX        BITS
    {
        namedVlanUnresolved(0)
    }

CucsFabricQuerierType ::= TEXTUAL-CONVENTION
    STATUS        current
    DESCRIPTION
        ""
    SYNTAX        INTEGER
    {
        enabled(0),
        disabled(1)
    }

CucsFabricRMonConfigIssues ::= TEXTUAL-CONVENTION
    STATUS        current
    DESCRIPTION
        ""
    SYNTAX        BITS
    {
        sourceVlanUnresolved(0)
    }

CucsFabricRemoteAdminState ::= TEXTUAL-CONVENTION
    STATUS        current
    DESCRIPTION
        ""
    SYNTAX        INTEGER
    {
        remoteTrigger(0),
        enabled(1),
        disabled(2),
        remove(3)
    }

CucsFabricRemoteSlotAdminState ::= TEXTUAL-CONVENTION
    STATUS        current
    DESCRIPTION
        ""
    SYNTAX        INTEGER
    {
        remoteTrigger(0),
        acknowledged(1),
        reacknowledge(3)
    }

CucsFabricReqIssues ::= TEXTUAL-CONVENTION
    STATUS        current
    DESCRIPTION
        ""
    SYNTAX        BITS
    {
        permitUnresolved(0)
    }

CucsFabricResVlanOperState ::= TEXTUAL-CONVENTION
    STATUS        current
    DESCRIPTION
        ""
    SYNTAX        INTEGER
    {
        notApplied(0),
        applying(1),
        applied(2)
    }

CucsFabricReservedVlanFsmCurrentFsm ::= TEXTUAL-CONVENTION
    STATUS        current
    DESCRIPTION
        ""
    SYNTAX        INTEGER
    {
        nop(0),
        deploy(2272)
    }

CucsFabricReservedVlanFsmStageName ::= TEXTUAL-CONVENTION
    STATUS        current
    DESCRIPTION
        ""
    SYNTAX        INTEGER
    {
        nop(0),
        deployBegin(2272),
        deployConfigSwitchPeer(2273),
        deployWaitForUserAck(2274),
        deployConfigSwitchLocal(2275),
        deployFail(2312),
        deploySuccess(2313)
    }

CucsFabricReservedVlanFsmTaskItem ::= TEXTUAL-CONVENTION
    STATUS        current
    DESCRIPTION
        ""
    SYNTAX        INTEGER
    {
        nop(0),
        deploy(2272)
    }

CucsFabricSanType ::= TEXTUAL-CONVENTION
    STATUS        current
    DESCRIPTION
        ""
    SYNTAX        BITS
    {
        lan(0),
        san(1),
        ipc(2)
    }

CucsFabricSanCloudFsmCurrentFsm ::= TEXTUAL-CONVENTION
    STATUS        current
    DESCRIPTION
        ""
    SYNTAX        INTEGER
    {
        nop(0),
        switchMode(871)
    }

CucsFabricSanCloudFsmStageName ::= TEXTUAL-CONVENTION
    STATUS        current
    DESCRIPTION
        ""
    SYNTAX        INTEGER
    {
        nop(0),
        switchModeBegin(871),
        switchModeSwConfigPeer(872),
        switchModeSwConfigLocal(873),
        switchModeFail(992),
        switchModeSuccess(993),
        switchModeWaitForUserAck(2248)
    }

CucsFabricSanCloudFsmTaskItem ::= TEXTUAL-CONVENTION
    STATUS        current
    DESCRIPTION
        ""
    SYNTAX        INTEGER
    {
        nop(0),
        switchMode(875)
    }

CucsFabricSanConfigIssues ::= TEXTUAL-CONVENTION
    STATUS        current
    DESCRIPTION
        ""
    SYNTAX        BITS
    {
        vsanCountExceedsLimit(0)
    }

CucsFabricSanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricSanEpType ::= TEXTUAL-CONVENTION
    STATUS        current
    DESCRIPTION
        ""
    SYNTAX        BITS
    {
        lan(0),
        san(1),
        ipc(2)
    }

CucsFabricSanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricSanPcType ::= TEXTUAL-CONVENTION
    STATUS        current
    DESCRIPTION
        ""
    SYNTAX        BITS
    {
        lan(0),
        san(1),
        ipc(2)
    }

CucsFabricSessionType ::= TEXTUAL-CONVENTION
    STATUS        current
    DESCRIPTION
        ""
    SYNTAX        INTEGER
    {
        spanLocal(1),
        erspanSource(2)
    }

CucsFabricSlotAdminState ::= TEXTUAL-CONVENTION
    STATUS        current
    DESCRIPTION
        ""
    SYNTAX        INTEGER
    {
        acknowledged(1),
        reacknowledge(3)
    }

CucsFabricSnoopingType ::= TEXTUAL-CONVENTION
    STATUS        current
    DESCRIPTION
        ""
    SYNTAX        INTEGER
    {
        enabled(0),
        disabled(1)
    }

CucsFabricStatus ::= TEXTUAL-CONVENTION
    STATUS        current
    DESCRIPTION
        ""
    SYNTAX        INTEGER
    {
        modified(0),
        created(1),
        deleted(2),
        intentDeletion(3)
    }

CucsFabricSubGroupAggrPortId ::= TEXTUAL-CONVENTION
    STATUS        current
    DESCRIPTION
        ""
    SYNTAX        Gauge32 (1..48)

CucsFabricSubGroupConfigState ::= TEXTUAL-CONVENTION
    STATUS        current
    DESCRIPTION
        ""
    SYNTAX        INTEGER
    {
        enabled(1),
        disabled(2)
    }

CucsFabricSubGroupSlotId ::= TEXTUAL-CONVENTION
    STATUS        current
    DESCRIPTION
        ""
    SYNTAX        Gauge32 (1..4)

CucsFabricSwChEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricSwChEpType ::= TEXTUAL-CONVENTION
    STATUS        current
    DESCRIPTION
        ""
    SYNTAX        BITS
    {
        lan(0),
        san(1),
        ipc(2)
    }

CucsFabricSwChPhEpAdminState ::= TEXTUAL-CONVENTION
    STATUS        current
    DESCRIPTION
        ""
    SYNTAX        INTEGER
    {
        enabled(1),
        disabled(2),
        remove(3)
    }

CucsFabricSwChPhEpOperationAdminState ::= TEXTUAL-CONVENTION
    STATUS        current
    DESCRIPTION
        ""
    SYNTAX        INTEGER
    {
        remoteTrigger(0),
        enabled(1),
        disabled(2),
        remove(3)
    }

CucsFabricSwSrvEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricSwSrvEpType ::= TEXTUAL-CONVENTION
    STATUS        current
    DESCRIPTION
        ""
    SYNTAX        BITS
    {
        lan(0),
        san(1),
        ipc(2)
    }

CucsFabricSwSrvPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricSwSrvPcType ::= TEXTUAL-CONVENTION
    STATUS        current
    DESCRIPTION
        ""
    SYNTAX        BITS
    {
        lan(0),
        san(1),
        ipc(2)
    }

CucsFabricSwSubGroupAggrPortId ::= TEXTUAL-CONVENTION
    STATUS        current
    DESCRIPTION
        ""
    SYNTAX        Gauge32 (1..48)

CucsFabricSwSubGroupConfigState ::= TEXTUAL-CONVENTION
    STATUS        current
    DESCRIPTION
        ""
    SYNTAX        INTEGER
    {
        enabled(1),
        disabled(2)
    }

CucsFabricSwSubGroupSlotId ::= TEXTUAL-CONVENTION
    STATUS        current
    DESCRIPTION
        ""
    SYNTAX        Gauge32 (1..4)

CucsFabricSwitchingMode ::= TEXTUAL-CONVENTION
    STATUS        current
    DESCRIPTION
        ""
    SYNTAX        INTEGER
    {
        endHost(0),
        switch(1)
    }

CucsFabricTargetEpType ::= TEXTUAL-CONVENTION
    STATUS        current
    DESCRIPTION
        ""
    SYNTAX        BITS
    {
        lan(0),
        san(1),
        ipc(2)
    }

CucsFabricTargetStatus ::= TEXTUAL-CONVENTION
    STATUS        current
    DESCRIPTION
        ""
    SYNTAX        INTEGER
    {
        valid(0),
        invalid(1)
    }

CucsFabricTimeZone ::= TEXTUAL-CONVENTION
    STATUS        current
    DESCRIPTION
        ""
    SYNTAX        INTEGER
    {
        utc(0),
        local(1)
    }

CucsFabricTrafficDirection ::= TEXTUAL-CONVENTION
    STATUS        current
    DESCRIPTION
        ""
    SYNTAX        INTEGER
    {
        rx(1),
        tx(2),
        both(3)
    }

CucsFabricTransport ::= TEXTUAL-CONVENTION
    STATUS        current
    DESCRIPTION
        ""
    SYNTAX        INTEGER
    {
        ethernet(0),
        fc(1)
    }

CucsFabricUdldLinkPolicyAdminState ::= TEXTUAL-CONVENTION
    STATUS        current
    DESCRIPTION
        ""
    SYNTAX        INTEGER
    {
        enabled(1),
        disabled(2)
    }

CucsFabricUdldLinkPolicyMode ::= TEXTUAL-CONVENTION
    STATUS        current
    DESCRIPTION
        ""
    SYNTAX        INTEGER
    {
        normal(0),
        aggressive(1)
    }

CucsFabricUdldOperState ::= TEXTUAL-CONVENTION
    STATUS        current
    DESCRIPTION
        ""
    SYNTAX        INTEGER
    {
        unknown(0),
        unidirectional(1),
        bidirectional(2),
        txRxLoop(3),
        mismatch(4),
        echoEmpty(5),
        adminDisabled(6)
    }

CucsFabricVConInstType ::= TEXTUAL-CONVENTION
    STATUS        current
    DESCRIPTION
        ""
    SYNTAX        INTEGER
    {
        auto(1),
        manual(2),
        policy(3)
    }

CucsFabricVConMappingScheme ::= TEXTUAL-CONVENTION
    STATUS        current
    DESCRIPTION
        ""
    SYNTAX        INTEGER
    {
        roundRobin(2),
        linearOrdered(3),
        roundRobinToLinearOrdered(4),
        linearOrderedToRoundRobin(5)
    }

CucsFabricVConPlacementPref ::= TEXTUAL-CONVENTION
    STATUS        current
    DESCRIPTION
        ""
    SYNTAX        INTEGER
    {
        physical(1),
        auto(2)
    }

CucsFabricVConSelectPref ::= TEXTUAL-CONVENTION
    STATUS        current
    DESCRIPTION
        ""
    SYNTAX        INTEGER
    {
        assignedOnly(1),
        unassignedOnly(2),
        excludeDynamic(3),
        dynamicOnly(4),
        excludeUnassigned(5),
        excludeUsnic(7),
        usnicOnly(8)
    }

CucsFabricVConSharePref ::= TEXTUAL-CONVENTION
    STATUS        current
    DESCRIPTION
        ""
    SYNTAX        INTEGER
    {
        exclusiveOnly(1),
        exclusivePreferred(2),
        sameTransport(3),
        differentTransport(4),
        shared(5)
    }

CucsFabricVConTransportPref ::= TEXTUAL-CONVENTION
    STATUS        current
    DESCRIPTION
        ""
    SYNTAX        BITS
    {
        fc(0),
        ethernet(1)
    }

CucsFabricVlanSwitchId ::= TEXTUAL-CONVENTION
    STATUS        current
    DESCRIPTION
        ""
    SYNTAX        INTEGER
    {
        none(0),
        a(1),
        b(2),
        mgmt(3)
    }

CucsFabricVlanAssocPrimaryVlanState ::= TEXTUAL-CONVENTION
    STATUS        current
    DESCRIPTION
        ""
    SYNTAX        INTEGER
    {
        ok(1),
        isEmpty(2),
        doesNotExists(3),
        isNotPrimaryType(4),
        isInErrorState(5)
    }

CucsFabricVlanCompType ::= TEXTUAL-CONVENTION
    STATUS        current
    DESCRIPTION
        ""
    SYNTAX        INTEGER
    {
        included(1),
        excluded(2)
    }

CucsFabricVlanConfigIssues ::= TEXTUAL-CONVENTION
    STATUS        current
    DESCRIPTION
        ""
    SYNTAX        BITS
    {
        conflictingVlanAccess(0),
        unsupportedMulticastPolicy(1)
    }

CucsFabricVlanOperState ::= TEXTUAL-CONVENTION
    STATUS        current
    DESCRIPTION
        ""
    SYNTAX        INTEGER
    {
        ok(1),
        errorMisconfigured(2)
    }

CucsFabricVlanOverlapState ::= TEXTUAL-CONVENTION
    STATUS        current
    DESCRIPTION
        ""
    SYNTAX        INTEGER
    {
        notActive(0),
        ok(1),
        sharingTypeMismatch(2),
        primaryIdMismatch(3),
        active(4)
    }

CucsFabricVlanSharingType ::= TEXTUAL-CONVENTION
    STATUS        current
    DESCRIPTION
        ""
    SYNTAX        INTEGER
    {
        none(0),
        primary(1),
        isolated(2),
        community(3)
    }

CucsFabricVnetConfigState ::= TEXTUAL-CONVENTION
    STATUS        current
    DESCRIPTION
        ""
    SYNTAX        INTEGER
    {
        notDeployedYet(1),
        deploymentError(2)
    }

CucsFabricVnetEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsFabricVnetEpLcCtrlState ::= TEXTUAL-CONVENTION
    STATUS        current
    DESCRIPTION
        ""
    SYNTAX        INTEGER
    {
        available(0),
        allocated(1),
        deallocated(2),
        repurposed(3)
    }

CucsFabricVnetEpLocale ::= TEXTUAL-CONVENTION
    STATUS        current
    DESCRIPTION
        ""
    SYNTAX        BITS
    {
        server(0),
        chassis(1),
        internal(2),
        external(3)
    }

CucsFabricVnetEpPolicyOwner ::= TEXTUAL-CONVENTION
    STATUS        current
    DESCRIPTION
        ""
    SYNTAX        INTEGER
    {
        local(0),
        policy(1),
        pendingPolicy(2),
        unspecified(3)
    }

CucsFabricVnetEpSyncEpFsmCurrentFsm ::= TEXTUAL-CONVENTION
    STATUS        current
    DESCRIPTION
        ""
    SYNTAX        INTEGER
    {
        nop(0),
        syncVnetEpUCS(367),
        pushVnetEpDeletion(1474)
    }

CucsFabricVnetEpSyncEpFsmStageName ::= TEXTUAL-CONVENTION
    STATUS        current
    DESCRIPTION
        ""
    SYNTAX        INTEGER
    {
        nop(0),
        syncVnetEpUCSBegin(367),
        syncVnetEpUCSSync(368),
        syncVnetEpUCSFail(373),
        syncVnetEpUCSSuccess(374),
        pushVnetEpDeletionBegin(1474),
        pushVnetEpDeletionSync(1475),
        pushVnetEpDeletionFail(1482),
        pushVnetEpDeletionSuccess(1483)
    }

CucsFabricVnetEpSyncEpFsmTaskItem ::= TEXTUAL-CONVENTION
    STATUS        current
    DESCRIPTION
        ""
    SYNTAX        INTEGER
    {
        nop(0),
        syncVnetEpUCS(367),
        pushVnetEpDeletion(1474)
    }

CucsFabricVsanSwitchId ::= TEXTUAL-CONVENTION
    STATUS        current
    DESCRIPTION
        ""
    SYNTAX        INTEGER
    {
        none(0),
        a(1),
        b(2),
        mgmt(3)
    }

CucsFabricVsanOperState ::= TEXTUAL-CONVENTION
    STATUS        current
    DESCRIPTION
        ""
    SYNTAX        INTEGER
    {
        ok(1),
        errorMisconfigured(2),
        errorReserved(3)
    }

CucsFabricVxanConfigOverlap ::= TEXTUAL-CONVENTION
    STATUS        current
    DESCRIPTION
        ""
    SYNTAX        INTEGER
    {
        ok(1),
        errorReservedConflict(2)
    }

CucsFabricWarnings ::= TEXTUAL-CONVENTION
    STATUS        current
    DESCRIPTION
        ""
    SYNTAX        BITS
    {
        fcZoningEnabled(0),
        configurationError(1)
    }

CucsFabricZoningState ::= TEXTUAL-CONVENTION
    STATUS        current
    DESCRIPTION
        ""
    SYNTAX        INTEGER
    {
        disabled(0),
        enabled(1)
    }

CucsFabricQosPriority ::= TEXTUAL-CONVENTION
    STATUS        current
    DESCRIPTION
        ""
    SYNTAX        INTEGER
    {
        unknown(0),
        fc(1),
        platinum(2),
        gold(3),
        silver(4),
        bronze(5),
        bestEffort(6)
    }

CucsFabricRecoveryAction ::= TEXTUAL-CONVENTION
    STATUS        current
    DESCRIPTION
        ""
    SYNTAX        INTEGER
    {
        none(0),
        reset(1)
    }

CucsFaultBasePolicyClearAction ::= TEXTUAL-CONVENTION
    STATUS        current
    DESCRIPTION
        ""
    SYNTAX        INTEGER
    {
        retain(0),
        delete(1)
    }

CucsFaultBasePolicySoakingSeverity ::= TEXTUAL-CONVENTION
    STATUS        current
    DESCRIPTION
        ""
    SYNTAX        INTEGER
    {
        info(1),
        condition(2),
        warning(3)
    }

CucsFaultPolicyClearAction ::= TEXTUAL-CONVENTION
    STATUS        current
    DESCRIPTION
        ""
    SYNTAX        INTEGER
    {
        retain(0),
        delete(1)
    }

CucsFcErrStatsThresholded ::= TEXTUAL-CONVENTION
    STATUS        current
    DESCRIPTION
        ""
    SYNTAX        BITS
    {
        crcRxDelta(0),
        crcRxDeltaAvg(1),
        crcRxDeltaMax(2),
        crcRxDeltaMin(3),
        discardRxDelta(4),
        discardRxDeltaAvg(5),
        discardRxDeltaMax(6),
        discardRxDeltaMin(7),
        discardTxDelta(8),
        discardTxDeltaAvg(9),
        discardTxDeltaMax(10),
        discardTxDeltaMin(11),
        linkFailuresDelta(12),
        linkFailuresDeltaAvg(13),
        linkFailuresDeltaMax(14),
        linkFailuresDeltaMin(15),
        rxDelta(16),
        rxDeltaAvg(17),
        rxDeltaMax(18),
        rxDeltaMin(19),
        signalLossesDelta(20),
        signalLossesDeltaAvg(21),
        signalLossesDeltaMax(22),
        signalLossesDeltaMin(23),
        syncLossesDelta(24),
        syncLossesDeltaAvg(25),
        syncLossesDeltaMax(26),
        syncLossesDeltaMin(27),
        tooLongRxDelta(28),
        tooLongRxDeltaAvg(29),
        tooLongRxDeltaMax(30),
        tooLongRxDeltaMin(31),
        tooShortRxDelta(32),
        tooShortRxDeltaAvg(33),
        tooShortRxDeltaMax(34),
        tooShortRxDeltaMin(35),
        txDelta(36),
        txDeltaAvg(37),
        txDeltaMax(38),
        txDeltaMin(39)
    }

CucsFcErrStatsHistThresholded ::= TEXTUAL-CONVENTION
    STATUS        current
    DESCRIPTION
        ""
    SYNTAX        BITS
    {
        crcRxDelta(0),
        crcRxDeltaAvg(1),
        crcRxDeltaMax(2),
        crcRxDeltaMin(3),
        discardRxDelta(4),
        discardRxDeltaAvg(5),
        discardRxDeltaMax(6),
        discardRxDeltaMin(7),
        discardTxDelta(8),
        discardTxDeltaAvg(9),
        discardTxDeltaMax(10),
        discardTxDeltaMin(11),
        linkFailuresDelta(12),
        linkFailuresDeltaAvg(13),
        linkFailuresDeltaMax(14),
        linkFailuresDeltaMin(15),
        rxDelta(16),
        rxDeltaAvg(17),
        rxDeltaMax(18),
        rxDeltaMin(19),
        signalLossesDelta(20),
        signalLossesDeltaAvg(21),
        signalLossesDeltaMax(22),
        signalLossesDeltaMin(23),
        syncLossesDelta(24),
        syncLossesDeltaAvg(25),
        syncLossesDeltaMax(26),
        syncLossesDeltaMin(27),
        tooLongRxDelta(28),
        tooLongRxDeltaAvg(29),
        tooLongRxDeltaMax(30),
        tooLongRxDeltaMin(31),
        tooShortRxDelta(32),
        tooShortRxDeltaAvg(33),
        tooShortRxDeltaMax(34),
        tooShortRxDeltaMin(35),
        txDelta(36),
        txDeltaAvg(37),
        txDeltaMax(38),
        txDeltaMin(39)
    }

CucsFcPIoFsmCurrentFsm ::= TEXTUAL-CONVENTION
    STATUS        current
    DESCRIPTION
        ""
    SYNTAX        INTEGER
    {
        nop(0),
        inCompatSfpPresence(1014),
        inCompatSfpReplaced(1334)
    }

CucsFcPIoFsmStageName ::= TEXTUAL-CONVENTION
    STATUS        current
    DESCRIPTION
        ""
    SYNTAX        INTEGER
    {
        nop(0),
        inCompatSfpPresenceBegin(1014),
        inCompatSfpPresenceShutdown(1015),
        inCompatSfpPresenceFail(1034),
        inCompatSfpPresenceSuccess(1035),
        inCompatSfpReplacedBegin(1334),
        inCompatSfpReplacedEnablePort(1335),
        inCompatSfpReplacedFail(1461),
        inCompatSfpReplacedSuccess(1462)
    }

CucsFcStatsThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        packetsRxDelta(8),
        packetsRxDeltaAvg(9),
        packetsRxDeltaMax(10),
        packetsRxDeltaMin(11),
        packetsTxDelta(12),
        packetsTxDeltaAvg(13),
        packetsTxDeltaMax(14),
        packetsTxDeltaMin(15)
    }

CucsFcStatsHistThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        packetsRxDelta(8),
        packetsRxDeltaAvg(9),
        packetsRxDeltaMax(10),
        packetsRxDeltaMin(11),
        packetsTxDelta(12),
        packetsTxDeltaAvg(13),
        packetsTxDeltaMax(14),
        packetsTxDeltaMin(15)
    }

CucsFcpoolBootTargetType ::= TEXTUAL-CONVENTION
    STATUS        current
    DESCRIPTION
        ""
    SYNTAX        INTEGER
    {
        primary(0),
        secondary(1)
    }

CucsFcpoolInitiatorPurpose ::= TEXTUAL-CONVENTION
    STATUS        current
    DESCRIPTION
        ""
    SYNTAX        INTEGER
    {
        portWwn(0),
        nodeWwn(1),
        derived(2)
    }

CucsFcpoolInitiatorEpPurpose ::= TEXTUAL-CONVENTION
    STATUS        current
    DESCRIPTION
        ""
    SYNTAX        INTEGER
    {
        portWwn(0),
        nodeWwn(1)
    }

CucsFcpoolInitiatorsAssignmentOrder ::= TEXTUAL-CONVENTION
    STATUS        current
    DESCRIPTION
        ""
    SYNTAX        INTEGER
    {
        default(0),
        sequential(1)
    }

CucsFcpoolInitiatorsMaxPortsPerNode ::= TEXTUAL-CONVENTION
    STATUS        current
    DESCRIPTION
        ""
    SYNTAX        INTEGER
    {
        upto3(3),
        upto7(7),
        upto15(15),
        upto31(31),
        upto63(63)
    }

CucsFcpoolInitiatorsPurpose ::= TEXTUAL-CONVENTION
    STATUS        current
    DESCRIPTION
        ""
    SYNTAX        INTEGER
    {
        nodeAndPortWwnAssignment(0),
        portWwnAssignment(1),
        nodeWwnAssignment(2)
    }

CucsFcpoolOuiSwitchId ::= TEXTUAL-CONVENTION
    STATUS        current
    DESCRIPTION
        ""
    SYNTAX        INTEGER
    {
        none(0),
        a(1),
        b(2)
    }

CucsFcpoolOuisFsmCurrentFsm ::= TEXTUAL-CONVENTION
    STATUS        current
    DESCRIPTION
        ""
    SYNTAX        INTEGER
    {
        nop(0),
        deploy(2381)
    }

CucsFcpoolOuisFsmStageName ::= TEXTUAL-CONVENTION
    STATUS        current
    DESCRIPTION
        ""
    SYNTAX        INTEGER
    {
        nop(0),
        deployBegin(2381),
        deployLocal(2382),
        deployRemote(2383),
        deployFail(2393),
        deploySuccess(2394)
    }

CucsFcpoolOuisFsmTaskItem ::= TEXTUAL-CONVENTION
    STATUS        current
    DESCRIPTION
        ""
    SYNTAX        INTEGER
    {
        nop(0),
        deploy(2381)
    }

CucsFdBladeFsmCurrentFsm ::= TEXTUAL-CONVENTION
    STATUS        current
    DESCRIPTION
        ""
    SYNTAX        INTEGER
    {
        nop(0),
        configure(616)
    }

CucsFdBladeFsmStageName ::= TEXTUAL-CONVENTION
    STATUS        current
    DESCRIPTION
        ""
    SYNTAX        INTEGER
    {
        nop(0),
        configureBegin(616),
        configureResolvePolicies(617),
        configureCollectIdContexts(618),
        configureApplyThrottle(619),
        configureThrottleWait(620),
        configureResolveIdentifiers(621),
        configureValidateNetworkDesign(622),
        configureConsumerVxanDeployment(623),
        configureWaitForConsumerReceivingVxan(624),
        configurePushPolicies(625),
        configureApplyConfig(626),
        configureFail(658),
        configureSuccess(659)
    }

CucsFdPhysicalFsmCurrentFsm ::= TEXTUAL-CONVENTION
    STATUS        current
    DESCRIPTION
        ""
    SYNTAX        INTEGER
    {
        nop(0),
        configure(616)
    }

CucsFdPhysicalFsmStageName ::= TEXTUAL-CONVENTION
    STATUS        current
    DESCRIPTION
        ""
    SYNTAX        INTEGER
    {
        nop(0),
        configureBegin(616),
        configureResolvePolicies(617),
        configureCollectIdContexts(618),
        configureApplyThrottle(619),
        configureThrottleWait(620),
        configureResolveIdentifiers(621),
        configureValidateNetworkDesign(622),
        configureConsumerVxanDeployment(623),
        configureWaitForConsumerReceivingVxan(624),
        configurePushPolicies(625),
        configureApplyConfig(626),
        configureFail(658),
        configureSuccess(659)
    }

CucsFdPhysicalFsmTaskFlags ::= TEXTUAL-CONVENTION
    STATUS        current
    DESCRIPTION
        ""
    SYNTAX        BITS
    {
        samDmeFdPhysicalConfigureModification(19)
    }

CucsFdPhysicalFsmTaskItem ::= TEXTUAL-CONVENTION
    STATUS        current
    DESCRIPTION
        ""
    SYNTAX        INTEGER
    {
        nop(0),
        configure(616)
    }

CucsFdRackUnitFsmCurrentFsm ::= TEXTUAL-CONVENTION
    STATUS        current
    DESCRIPTION
        ""
    SYNTAX        INTEGER
    {
        nop(0),
        configure(616)
    }

CucsFdRackUnitFsmStageName ::= TEXTUAL-CONVENTION
    STATUS        current
    DESCRIPTION
        ""
    SYNTAX        INTEGER
    {
        nop(0),
        configureBegin(616),
        configureResolvePolicies(617),
        configureCollectIdContexts(618),
        configureApplyThrottle(619),
        configureThrottleWait(620),
        configureResolveIdentifiers(621),
        configureValidateNetworkDesign(622),
        configureConsumerVxanDeployment(623),
        configureWaitForConsumerReceivingVxan(624),
        configurePushPolicies(625),
        configureApplyConfig(626),
        configureFail(658),
        configureSuccess(659)
    }

CucsFeatureSupportabilityType ::= TEXTUAL-CONVENTION
    STATUS        current
    DESCRIPTION
        ""
    SYNTAX        INTEGER
    {
        supported(0),
        notSupported(1),
        deprecated(2)
    }

CucsFirmwareActivityServersPowerState ::= TEXTUAL-CONVENTION
    STATUS        current
    DESCRIPTION
        ""
    SYNTAX        INTEGER
    {
        none(0),
        on(1),
        off(2),
        offNowait(3)
    }

CucsFirmwareActivityUpgradePriorityInfo ::= TEXTUAL-CONVENTION
    STATUS        current
    DESCRIPTION
        ""
    SYNTAX        BITS
    {
        cmcUpdate(0),
        cmcActivate(1),
        boardController(2),
        storageController(3),
        chassisAdaptorUpdate(4),
        chassisAdaptorActivate(5),
        cmcRightUpdate(6),
        cmcRightActivate(7),
        chassisAdaptorRightUpdate(8),
        chassisAdaptorRightActivate(9),
        sasExpanderUpdate(10),
        sasExpanderActivate(11),
        sasExpanderRightUpdate(12),
        sasExpanderRightActivate(13),
        boardControllerRight(14)
    }

CucsFirmwareAdminDnldStatus ::= TEXTUAL-CONVENTION
    STATUS        current
    DESCRIPTION
        ""
    SYNTAX        INTEGER
    {
        idle(0),
        restart(1)
    }

CucsFirmwareAdminState ::= TEXTUAL-CONVENTION
    STATUS        current
    DESCRIPTION
        ""
    SYNTAX        INTEGER
    {
        active(0),
        deleted(1)
    }

CucsFirmwareAutoSyncConfigIssue ::= TEXTUAL-CONVENTION
    STATUS        current
    DESCRIPTION
        ""
    SYNTAX        INTEGER
    {
        noIssues(0),
        defaultPackageMissing(1),
        versionsEmptyInDefaultPackage(2)
    }

CucsFirmwareAutoSyncState ::= TEXTUAL-CONVENTION
    STATUS        current
    DESCRIPTION
        ""
    SYNTAX        INTEGER
    {
        autoAcknowledge(0),
        userAcknowledge(1),
        noActions(2)
    }

CucsFirmwareBladeType ::= TEXTUAL-CONVENTION
    STATUS        current
    DESCRIPTION
        ""
    SYNTAX        INTEGER
    {
        unspecified(0),
        bladeController(4),
        bladeBios(6),
        adaptor(7),
        storageController(8),
        hostNic(9),
        hostHba(10),
        hostHbaOptionrom(11),
        hostNicOptionrom(12),
        boardController(13),
        localDisk(14),
        flexflashController(20),
        storageControllerOnboardDevice(21),
        storageDevBridge(22),
        storageControllerOnboardDeviceCpld(23),
        graphicsCard(25),
        psu(26),
        sasExpander(28),
        sasExpRegFw(31),
        nvmeMswitch(32),
        plxSwitch(33),
        persistentMemoryDimm(34),
        retimer(35),
        ubm(36),
        cpld(37),
        intelAmc(38),
        storageControllerOnboardDevicePsoc(42)
    }

CucsFirmwareBootUnitImage ::= TEXTUAL-CONVENTION
    STATUS        current
    DESCRIPTION
        ""
    SYNTAX        INTEGER
    {
        running(0),
        backup(1)
    }

CucsFirmwareBootUnitMode ::= TEXTUAL-CONVENTION
    STATUS        current
    DESCRIPTION
        ""
    SYNTAX        INTEGER
    {
        install(0),
        upgrade(1)
    }

CucsFirmwareCatalogPackConfigState ::= TEXTUAL-CONVENTION
    STATUS        current
    DESCRIPTION
        ""
    SYNTAX        INTEGER
    {
        ok(0),
        notApplied(1),
        failed(2)
    }

CucsFirmwareChassisType ::= TEXTUAL-CONVENTION
    STATUS        current
    DESCRIPTION
        ""
    SYNTAX        INTEGER
    {
        unspecified(0),
        storageController(8),
        localDisk(14),
        iocard(27),
        sasExpander(28),
        chassisBoardController(29),
        cmc(30)
    }

CucsFirmwareCompleteness ::= TEXTUAL-CONVENTION
    STATUS        current
    DESCRIPTION
        ""
    SYNTAX        INTEGER
    {
        partial(0),
        complete(1)
    }

CucsFirmwareComponentType ::= TEXTUAL-CONVENTION
    STATUS        current
    DESCRIPTION
        ""
    SYNTAX        BITS
    {
        kernel(0),
        system(1),
        combined(2),
        bootLoader(3),
        servicePack(4)
    }

CucsFirmwareDependencyRelationship ::= TEXTUAL-CONVENTION
    STATUS        current
    DESCRIPTION
        ""
    SYNTAX        INTEGER
    {
        special(0),
        ancestor(1),
        descendent(2)
    }

CucsFirmwareDependencyScope ::= TEXTUAL-CONVENTION
    STATUS        current
    DESCRIPTION
        ""
    SYNTAX        INTEGER
    {
        unknown(0),
        blade(1),
        chassis(2),
        system(4),
        switch(8),
        global(16)
    }

CucsFirmwareDependencySensitivity ::= TEXTUAL-CONVENTION
    STATUS        current
    DESCRIPTION
        ""
    SYNTAX        INTEGER
    {
        global(0),
        fabric(1),
        path(2)
    }

CucsFirmwareDeployment ::= TEXTUAL-CONVENTION
    STATUS        current
    DESCRIPTION
        ""
    SYNTAX        INTEGER
    {
        unspecified(0),
        kernel(1),
        bootLoader(2),
        system(3),
        backup(4),
        provider(5),
        servicePack(6)
    }

CucsFirmwareDistributableFsmCurrentFsm ::= TEXTUAL-CONVENTION
    STATUS        current
    DESCRIPTION
        ""
    SYNTAX        INTEGER
    {
        nop(0),
        delete(594)
    }

CucsFirmwareDistributableFsmStageName ::= TEXTUAL-CONVENTION
    STATUS        current
    DESCRIPTION
        ""
    SYNTAX        INTEGER
    {
        nop(0),
        deleteBegin(594),
        deleteLocal(595),
        deleteRemote(596),
        deleteFail(597),
        deleteSuccess(598)
    }

CucsFirmwareDistributableFsmTaskItem ::= TEXTUAL-CONVENTION
    STATUS        current
    DESCRIPTION
        ""
    SYNTAX        INTEGER
    {
        nop(0),
        delete(594)
    }

CucsFirmwareDistributableType ::= TEXTUAL-CONVENTION
    STATUS        current
    DESCRIPTION
        ""
    SYNTAX        INTEGER
    {
        unknown(0),
        image(1),
        fullBundle(2),
        infrastructureBundle(3),
        bSeriesBundle(4),
        cSeriesBundle(5),
        catalog(6),
        sSeriesBundle(7),
        providerBundle(8),
        servicePackBundle(10)
    }

CucsFirmwareDownloadActivity ::= TEXTUAL-CONVENTION
    STATUS        current
    DESCRIPTION
        ""
    SYNTAX        INTEGER
    {
        restart(0),
        idle(1)
    }

CucsFirmwareDownloadInterval ::= TEXTUAL-CONVENTION
    STATUS        current
    DESCRIPTION
        ""
    SYNTAX        INTEGER
    {
        onDemand(0),
        n1day(86400),
        n1week(604800),
        n2week(1209600)
    }

CucsFirmwareDownloadPolicyType ::= TEXTUAL-CONVENTION
    STATUS        current
    DESCRIPTION
        ""
    SYNTAX        INTEGER
    {
        cisco(0),
        local(1)
    }

CucsFirmwareDownloadStatus ::= TEXTUAL-CONVENTION
    STATUS        current
    DESCRIPTION
        ""
    SYNTAX        INTEGER
    {
        idle(0),
        inprogress(1),
        failed(3)
    }

CucsFirmwareDownloaderFsmCurrentFsm ::= TEXTUAL-CONVENTION
    STATUS        current
    DESCRIPTION
        ""
    SYNTAX        INTEGER
    {
        nop(0),
        download(233)
    }

CucsFirmwareDownloaderFsmStageName ::= TEXTUAL-CONVENTION
    STATUS        current
    DESCRIPTION
        ""
    SYNTAX        INTEGER
    {
        nop(0),
        downloadBegin(233),
        downloadLocal(234),
        downloadUnpackLocal(235),
        downloadCopyRemote(236),
        downloadDeleteLocal(239),
        downloadFail(394),
        downloadSuccess(395)
    }

CucsFirmwareDownloaderFsmTaskItem ::= TEXTUAL-CONVENTION
    STATUS        current
    DESCRIPTION
        ""
    SYNTAX        INTEGER
    {
        nop(0),
        download(233)
    }

CucsFirmwareEquipmentType ::= TEXTUAL-CONVENTION
    STATUS        current
    DESCRIPTION
        ""
    SYNTAX        INTEGER
    {
        unknown(0),
        system(1),
        switch(2),
        iocard(3),
        server(4),
        cimc(5),
        adaptor(6),
        storageController(7),
        boardController(8),
        bios(9),
        serviceProfile(10),
        graphicsCard(11),
        storageArrayProfile(12),
        storageBlade(13),
        sasExpander(14),
        cmc(15),
        retimer(16),
        ubm(17),
        cpld(18)
    }

CucsFirmwareFileType ::= TEXTUAL-CONVENTION
    STATUS        current
    DESCRIPTION
        ""
    SYNTAX        BITS
    {
        initConfig(0)
    }

CucsFirmwareFirmwareState ::= TEXTUAL-CONVENTION
    STATUS        current
    DESCRIPTION
        ""
    SYNTAX        BITS
    {
        cimcFirmwareMismatch(0),
        pldFirmwareMismatch(1)
    }

CucsFirmwareFwState ::= TEXTUAL-CONVENTION
    STATUS        current
    DESCRIPTION
        ""
    SYNTAX        INTEGER
    {
        unknown(0),
        sameRelease(1),
        compatible(2),
        incompatible(3),
        multipleReleases(4)
    }

CucsFirmwareHostPackConfigQualifier ::= TEXTUAL-CONVENTION
    STATUS        current
    DESCRIPTION
        ""
    SYNTAX        BITS
    {
        biosImageNotSelected(0)
    }

CucsFirmwareImageDeleted ::= TEXTUAL-CONVENTION
    STATUS        current
    DESCRIPTION
        ""
    SYNTAX        BITS
    {
        a(0),
        b(1)
    }

CucsFirmwareImageError ::= TEXTUAL-CONVENTION
    STATUS        current
    DESCRIPTION
        ""
    SYNTAX        INTEGER
    {
        none(0),
        checksumFailure(1),
        filesystemError(2),
        mgmtConnectError(3),
        bootConfMissing(4),
        crcFailure(5),
        unknownError(6),
        rebuilding(7)
    }

CucsFirmwareImageFsmCurrentFsm ::= TEXTUAL-CONVENTION
    STATUS        current
    DESCRIPTION
        ""
    SYNTAX        INTEGER
    {
        nop(0),
        delete(240)
    }

CucsFirmwareImageFsmStageName ::= TEXTUAL-CONVENTION
    STATUS        current
    DESCRIPTION
        ""
    SYNTAX        INTEGER
    {
        nop(0),
        deleteBegin(240),
        deleteLocal(241),
        deleteRemote(242),
        deleteFail(396),
        deleteSuccess(397)
    }

CucsFirmwareImageFsmTaskItem ::= TEXTUAL-CONVENTION
    STATUS        current
    DESCRIPTION
        ""
    SYNTAX        INTEGER
    {
        nop(0),
        delete(240)
    }

CucsFirmwareImagePresence ::= TEXTUAL-CONVENTION
    STATUS        current
    DESCRIPTION
        ""
    SYNTAX        BITS
    {
        a(0),
        b(1)
    }

CucsFirmwareImageState ::= TEXTUAL-CONVENTION
    STATUS        current
    DESCRIPTION
        ""
    SYNTAX        INTEGER
    {
        ready(0),
        scheduled(1),
        updating(2),
        activating(3),
        failed(4),
        setStartup(5),
        rebooting(6),
        pendingNextBoot(7),
        throttled(8),
        upgrading(9),
        autoUpdating(10),
        badImage(11),
        pendingPowerCycle(12),
        rebuilding(14),
        faultyState(15),
        waiting(16),
        downgradeNotSupported(17),
        operationNotSupported(18),
        vesselNotFound(19),
        downloadError(20),
        vesselValidateError(21)
    }

CucsFirmwareImpactType ::= TEXTUAL-CONVENTION
    STATUS        current
    DESCRIPTION
        ""
    SYNTAX        INTEGER
    {
        activate(0),
        noimpact(1),
        reset(2),
        update(3)
    }

CucsFirmwareInfraProfileStatus ::= TEXTUAL-CONVENTION
    STATUS        current
    DESCRIPTION
        ""
    SYNTAX        INTEGER
    {
        pending(0),
        triggeredActive(1),
        triggered(2),
        failedToTrigger(3)
    }

CucsFirmwareInstallSpState ::= TEXTUAL-CONVENTION
    STATUS        current
    DESCRIPTION
        ""
    SYNTAX        INTEGER
    {
        notInstalled(0),
        ready(1),
        transient(2),
        unknownInstallerBusy(3),
        active(4),
        activeCommitted(5),
        activeOnReload(6),
        activeCommittedOnReload(7),
        failed(8),
        inactive(9),
        inactiveCommitted(10),
        inactiveOnReload(11),
        inactiveCommittedOnReload(12),
        unknown(100)
    }

CucsFirmwareInstallState ::= TEXTUAL-CONVENTION
    STATUS        current
    DESCRIPTION
        ""
    SYNTAX        INTEGER
    {
        ready(0),
        scheduled(1),
        inProgress(2),
        failed(3),
        pendingUserAck(4),
        startPendingExtPermission(5)
    }

CucsFirmwareItemType ::= TEXTUAL-CONVENTION
    STATUS        current
    DESCRIPTION
        ""
    SYNTAX        INTEGER
    {
        unspecified(0),
        switchKernel(1),
        switchSoftware(2),
        system(3),
        bladeController(4),
        iocard(5),
        bladeBios(6),
        adaptor(7),
        storageController(8),
        hostNic(9),
        hostHba(10),
        hostHbaOptionrom(11),
        hostNicOptionrom(12),
        boardController(13),
        localDisk(14),
        flexflashController(20),
        storageNodeController(21),
        storageDevBridge(22),
        storageControllerOnboardDeviceCpld(23),
        graphicsCard(25),
        psu(26),
        sasExpander(28),
        chassisBoardController(29),
        cmc(30),
        sasExpRegFw(31),
        nvmeMswitch(32),
        plxSwitch(33),
        persistentMemoryDimm(34),
        retimer(35),
        ubm(36),
        cpld(37),
        intelAmc(38),
        fiServicePack(40),
        mgmtServicePack(41),
        storageControllerOnboardDevicePsoc(42)
    }

CucsFirmwareOperDnldStatus ::= TEXTUAL-CONVENTION
    STATUS        current
    DESCRIPTION
        ""
    SYNTAX        INTEGER
    {
        notDownloaded(0),
        triggered(1),
        downloading(2),
        downloaded(3),
        failed(4),
        deleting(5),
        eulaAcceptanceRequired(6)
    }

CucsFirmwareOwner ::= TEXTUAL-CONVENTION
    STATUS        current
    DESCRIPTION
        ""
    SYNTAX        INTEGER
    {
        management(0),
        policy(1)
    }

CucsFirmwarePackMode ::= TEXTUAL-CONVENTION
    STATUS        current
    DESCRIPTION
        ""
    SYNTAX        INTEGER
    {
        staged(0),
        oneShot(1)
    }

CucsFirmwarePackItemPresence ::= TEXTUAL-CONVENTION
    STATUS        current
    DESCRIPTION
        ""
    SYNTAX        INTEGER
    {
        unknown(0),
        missing(1),
        present(2)
    }

CucsFirmwarePlatformType ::= TEXTUAL-CONVENTION
    STATUS        current
    DESCRIPTION
        ""
    SYNTAX        INTEGER
    {
        ucs(0),
        ucsMini(1),
        ucs6300(2),
        ucs6400(3),
        ucs6500(4),
        ucsx9100(5),
        ucs6600(6)
    }

CucsFirmwarePolicyAdminState ::= TEXTUAL-CONVENTION
    STATUS        current
    DESCRIPTION
        ""
    SYNTAX        INTEGER
    {
        disable(0),
        enable(1)
    }

CucsFirmwareRepositoryType ::= TEXTUAL-CONVENTION
    STATUS        current
    DESCRIPTION
        ""
    SYNTAX        INTEGER
    {
        cisco(0),
        local(1)
    }

CucsFirmwareRunningDeployment ::= TEXTUAL-CONVENTION
    STATUS        current
    DESCRIPTION
        ""
    SYNTAX        INTEGER
    {
        unspecified(0),
        kernel(1),
        bootLoader(2),
        system(3),
        servicePack(4)
    }

CucsFirmwareSecureFPGAStatus ::= TEXTUAL-CONVENTION
    STATUS        current
    DESCRIPTION
        ""
    SYNTAX        INTEGER
    {
        ready(0),
        activationInProgress(1),
        activationFailed(2)
    }

CucsFirmwareServerBackUpBundleType ::= TEXTUAL-CONVENTION
    STATUS        current
    DESCRIPTION
        ""
    SYNTAX        INTEGER
    {
        none(0),
        blade(1),
        rack(2),
        infra(3),
        chassis(4)
    }

CucsFirmwareSourceType ::= TEXTUAL-CONVENTION
    STATUS        current
    DESCRIPTION
        ""
    SYNTAX        INTEGER
    {
        cisco(0),
        local(1)
    }

CucsFirmwareSystemFsmCurrentFsm ::= TEXTUAL-CONVENTION
    STATUS        current
    DESCRIPTION
        ""
    SYNTAX        INTEGER
    {
        nop(0),
        deploy(1362),
        applyCatalogPack(1378)
    }

CucsFirmwareSystemFsmStageName ::= TEXTUAL-CONVENTION
    STATUS        current
    DESCRIPTION
        ""
    SYNTAX        INTEGER
    {
        nop(0),
        deployBegin(1362),
        deployWaitForDeploy(1363),
        deployResolveDistributableNames(1364),
        deployResolveDistributable(1365),
        deployResolveImages(1366),
        deployActivateUCSM(1367),
        deployPollActivateOfUCSM(1368),
        deployUpdateIOM(1369),
        deployPollUpdateOfIOM(1370),
        deployActivateIOM(1371),
        deployPollActivateOfIOM(1372),
        deployActivateRemoteFI(1373),
        deployPollActivateOfRemoteFI(1374),
        deployWaitForUserAck(1375),
        deployActivateLocalFI(1376),
        deployPollActivateOfLocalFI(1377),
        applyCatalogPackBegin(1378),
        applyCatalogPackResolveDistributableNames(1379),
        applyCatalogPackResolveDistributable(1380),
        applyCatalogPackResolveImages(1381),
        applyCatalogPackActivateCatalog(1382),
        applyCatalogPackFail(1401),
        applyCatalogPackSuccess(1402),
        deployFail(1403),
        deploySuccess(1404),
        deployInternalBackup(1937),
        deployPollInternalBackup(1938),
        deployPollWaitForUserAck(1963),
        deployDownloadImages(1995),
        deployCopyAllImagesToPeer(1996),
        deployFabEvacOnRemoteFI(2201),
        deployPollFabEvacOnRemoteFI(2202),
        deployFabEvacOffRemoteFI(2203),
        deployPollFabEvacOffRemoteFI(2204),
        deployFailOverToRemoteFI(2205),
        deployPollFailOverToRemoteFI(2206),
        deployActivateUCSMServicePack(2207),
        deployPollActivateOfUCSMServicePack(2208)
    }

CucsFirmwareSystemFsmTaskFlags ::= TEXTUAL-CONVENTION
    STATUS        current
    DESCRIPTION
        ""
    SYNTAX        BITS
    {
        samDmeFirmwareSystemDeployApplyInfra(8),
        samDmeFirmwareSystemDeployPrepareForUpdate(21)
    }

CucsFirmwareSystemFsmTaskItem ::= TEXTUAL-CONVENTION
    STATUS        current
    DESCRIPTION
        ""
    SYNTAX        INTEGER
    {
        nop(0),
        deploy(1362),
        applyCatalogPack(1378)
    }

CucsFirmwareTransferState ::= TEXTUAL-CONVENTION
    STATUS        current
    DESCRIPTION
        ""
    SYNTAX        INTEGER
    {
        init(0),
        downloading(1),
        downloaded(2),
        failed(3),
        eulaAcceptanceRequired(4)
    }

CucsFirmwareTransport ::= TEXTUAL-CONVENTION
    STATUS        current
    DESCRIPTION
        ""
    SYNTAX        INTEGER
    {
        ftp(0),
        tftp(1),
        scp(2),
        sftp(3),
        local(4),
        usbA(5),
        usbB(6)
    }

CucsFirmwareTriggerAdminState ::= TEXTUAL-CONVENTION
    STATUS        current
    DESCRIPTION
        ""
    SYNTAX        INTEGER
    {
        none(0),
        triggerDownload(1),
        triggerDelete(2)
    }

CucsFirmwareTriggerState ::= TEXTUAL-CONVENTION
    STATUS        current
    DESCRIPTION
        ""
    SYNTAX        INTEGER
    {
        triggered(0),
        trigger(1),
        forceTrigger(2)
    }

CucsFirmwareType ::= TEXTUAL-CONVENTION
    STATUS        current
    DESCRIPTION
        ""
    SYNTAX        INTEGER
    {
        unspecified(0),
        switchKernel(1),
        switchSoftware(2),
        system(3),
        bladeController(4),
        iocard(5),
        fex(6),
        adaptor(7),
        storageController(8),
        hostNic(9),
        hostHba(10),
        hostHbaOptionrom(11),
        hostNicOptionrom(12),
        boardController(13),
        localDisk(14),
        diag(15),
        catalog(16),
        mgmtExt(17),
        debugPlugIn(18),
        switch(19),
        flexflashController(20),
        storageNodeController(21),
        storageDevBridge(22),
        storageControllerOnboardDeviceCpld(23),
        resourceAggr(24),
        policyMgr(25),
        storageBroker(26),
        statsMgr(27),
        sasExpander(28),
        chassisBoardController(29),
        sasExpRegFw(31),
        nvmeMswitch(32),
        plxSwitch(33),
        persistentMemoryDimm(34),
        retimer(35),
        ubm(36),
        cpld(37),
        intelAmc(38),
        fiServicePack(40),
        mgmtServicePack(41),
        storageControllerOnboardDevicePsoc(42)
    }

CucsFirmwareTypeInstallPath ::= TEXTUAL-CONVENTION
    STATUS        current
    DESCRIPTION
        ""
    SYNTAX        INTEGER
    {
        default(0),
        oob(1),
        ib(2)
    }

CucsFirmwareUpdatableDeployment ::= TEXTUAL-CONVENTION
    STATUS        current
    DESCRIPTION
        ""
    SYNTAX        INTEGER
    {
        unspecified(0),
        kernel(1),
        bootLoader(2),
        system(3),
        backup(4),
        provider(5),
        servicePack(6)
    }

CucsFirmwareUpgradeCategory ::= TEXTUAL-CONVENTION
    STATUS        current
    DESCRIPTION
        ""
    SYNTAX        INTEGER
    {
        other(0),
        dataLoad(1),
        catalog(2),
        config(3),
        serverReboot(4),
        faults(5)
    }

CucsFirmwareUpgradeSeverity ::= TEXTUAL-CONVENTION
    STATUS        current
    DESCRIPTION
        ""
    SYNTAX        INTEGER
    {
        unknown(0),
        fatal(1),
        error(2),
        warn(3),
        info(4)
    }

CucsFirmwareUpgradeStatus ::= TEXTUAL-CONVENTION
    STATUS        current
    DESCRIPTION
        ""
    SYNTAX        INTEGER
    {
        unknown(0),
        inProgress(1),
        failed(2),
        success(3),
        warnings(4),
        skipped(5)
    }

CucsFlowctrlConfig ::= TEXTUAL-CONVENTION
    STATUS        current
    DESCRIPTION
        ""
    SYNTAX        INTEGER
    {
        ok(0),
        notSupported(1)
    }

CucsFlowctrlFlowControl ::= TEXTUAL-CONVENTION
    STATUS        current
    DESCRIPTION
        ""
    SYNTAX        INTEGER
    {
        off(0),
        on(1)
    }

CucsFlowctrlPriorityPause ::= TEXTUAL-CONVENTION
    STATUS        current
    DESCRIPTION
        ""
    SYNTAX        INTEGER
    {
        auto(0),
        on(1)
    }

CucsFsmCompletion ::= TEXTUAL-CONVENTION
    STATUS        current
    DESCRIPTION
        ""
    SYNTAX        INTEGER
    {
        scheduled(0),
        processing(1),
        completed(2),
        cancelled(3)
    }

CucsFsmFlags ::= TEXTUAL-CONVENTION
    STATUS        current
    DESCRIPTION
        ""
    SYNTAX        BITS
    {
        unused(1)
    }

CucsFsmFsmStageStatus ::= TEXTUAL-CONVENTION
    STATUS        current
    DESCRIPTION
        ""
    SYNTAX        INTEGER
    {
        fail(0),
        success(1),
        skip(2),
        pending(3),
        inProgress(4),
        throttled(5),
        nop(255)
    }

CucsFsmLifecycle ::= TEXTUAL-CONVENTION
    STATUS        current
    DESCRIPTION
        ""
    SYNTAX        INTEGER
    {
        available(0),
        allocated(1),
        deallocated(2),
        repurposed(3)
    }

CucsGlAbsIdentCtxOpPurpose ::= TEXTUAL-CONVENTION
    STATUS        current
    DESCRIPTION
        ""
    SYNTAX        INTEGER
    {
        nodeAndPortWwnAssignment(0),
        portWwnAssignment(1),
        nodeWwnAssignment(2),
        default(3)
    }

CucsGlAdminState ::= TEXTUAL-CONVENTION
    STATUS        current
    DESCRIPTION
        ""
    SYNTAX        INTEGER
    {
        evaluate(0),
        globalize(1),
        reevaluate(3),
        terminate(4)
    }

CucsGlAppendType ::= TEXTUAL-CONVENTION
    STATUS        current
    DESCRIPTION
        ""
    SYNTAX        INTEGER
    {
        number(0)
    }

CucsGlBlockIssueType ::= TEXTUAL-CONVENTION
    STATUS        current
    DESCRIPTION
        ""
    SYNTAX        INTEGER
    {
        default(0),
        vxan(1)
    }

CucsGlConflict ::= TEXTUAL-CONVENTION
    STATUS        current
    DESCRIPTION
        ""
    SYNTAX        INTEGER
    {
        noConflict(0),
        hasConflict(1)
    }

CucsGlConflictAdminState ::= TEXTUAL-CONVENTION
    STATUS        current
    DESCRIPTION
        ""
    SYNTAX        INTEGER
    {
        default(0),
        evaluate(1)
    }

CucsGlDomainOperState ::= TEXTUAL-CONVENTION
    STATUS        current
    DESCRIPTION
        ""
    SYNTAX        INTEGER
    {
        notEvaluated(0),
        fetchingVnets(1),
        fetchingVnetsDone(2),
        fetchingDependencies(3),
        fetchingDependenciesDone(4),
        completed(5)
    }

CucsGlEvaluationState ::= TEXTUAL-CONVENTION
    STATUS        current
    DESCRIPTION
        ""
    SYNTAX        INTEGER
    {
        notEvaluated(0),
        evaluating(1),
        evaluated(2)
    }

CucsGlGlobalizeOperation ::= TEXTUAL-CONVENTION
    STATUS        current
    DESCRIPTION
        ""
    SYNTAX        INTEGER
    {
        default(0),
        unbindTemplate(1),
        resolveConflict(2),
        createGlobalPolicy(3),
        createGlobalIdPool(4),
        createGlobalServiceProfile(5),
        globalizeLsp(6),
        applyRule(7)
    }

CucsGlIdentCtxResOpFsmCurrentFsm ::= TEXTUAL-CONVENTION
    STATUS        current
    DESCRIPTION
        ""
    SYNTAX        INTEGER
    {
        nop(0),
        validateId(581)
    }

CucsGlIdentCtxResOpFsmStageName ::= TEXTUAL-CONVENTION
    STATUS        current
    DESCRIPTION
        ""
    SYNTAX        INTEGER
    {
        nop(0),
        validateIdBegin(581),
        validateIdValidate(582),
        validateIdFail(660),
        validateIdSuccess(661)
    }

CucsGlIdentCtxResOpFsmTaskItem ::= TEXTUAL-CONVENTION
    STATUS        current
    DESCRIPTION
        ""
    SYNTAX        INTEGER
    {
        nop(0),
        validateId(581)
    }

CucsGlOperState ::= TEXTUAL-CONVENTION
    STATUS        current
    DESCRIPTION
        ""
    SYNTAX        INTEGER
    {
        notEvaluated(0),
        evaluating(1),
        evaluatedWithError(2),
        evaluatedWithSuccess(3),
        globalizing(4),
        globalizedWithError(5),
        globalizedWithSuccess(6),
        applyingRuleAndEvaluating(7),
        fetchingDataFromDomain(8),
        evaluatedWithBlockingIssue(10),
        evaluatedWithConflict(11)
    }

CucsGlPolicyGlAction ::= TEXTUAL-CONVENTION
    STATUS        current
    DESCRIPTION
        ""
    SYNTAX        INTEGER
    {
        noAction(0),
        changeDefaultToGlobalDefault(1),
        policyConflict(2)
    }

CucsGlPolicyGlOperAction ::= TEXTUAL-CONVENTION
    STATUS        current
    DESCRIPTION
        ""
    SYNTAX        INTEGER
    {
        noConflict(0),
        policyConflict(1)
    }

CucsGlPolicyUserAction ::= TEXTUAL-CONVENTION
    STATUS        current
    DESCRIPTION
        ""
    SYNTAX        INTEGER
    {
        noAction(0),
        referenceGlobal(1),
        rename(2)
    }

CucsGlReqOperState ::= TEXTUAL-CONVENTION
    STATUS        current
    DESCRIPTION
        ""
    SYNTAX        INTEGER
    {
        notEvaluated(0),
        fetchingDataFromDomain(1),
        fetchingDependencies(2),
        evaluating(3),
        evaluatedWithError(4),
        evaluatedWithSuccess(5),
        createDependencies(6),
        globalizing(7),
        globalizedWithError(8),
        globalizedWithSuccess(9)
    }

CucsGlRequestFsmCurrentFsm ::= TEXTUAL-CONVENTION
    STATUS        current
    DESCRIPTION
        ""
    SYNTAX        INTEGER
    {
        nop(0),
        evaluate(583),
        createGlobalIdPool(587),
        createGlobalPolicy(589),
        globalize(591)
    }

CucsGlRequestFsmStageName ::= TEXTUAL-CONVENTION
    STATUS        current
    DESCRIPTION
        ""
    SYNTAX        INTEGER
    {
        nop(0),
        evaluateBegin(583),
        evaluateValidate(584),
        evaluateFetchDomainData(585),
        evaluateEvaluate(586),
        createGlobalIdPoolBegin(587),
        createGlobalIdPoolCreatePolicies(588),
        createGlobalPolicyBegin(589),
        createGlobalPolicyCreatePolicies(590),
        globalizeBegin(591),
        globalizeCreateOrg(592),
        globalizeCreatePolicies(593),
        globalizeUpdateDomainMos(594),
        globalizeCreateVlanOrgPermission(595),
        globalizeCreateGSP(596),
        globalizeResolveGlobalPoolDn(597),
        globalizeAddIdToGlobalPool(598),
        globalizeAssignIds(599),
        globalizeUnassignIds(600),
        createGlobalIdPoolFail(662),
        createGlobalIdPoolSuccess(663),
        createGlobalPolicyFail(664),
        createGlobalPolicySuccess(665),
        evaluateFail(666),
        evaluateSuccess(667),
        globalizeFail(668),
        globalizeSuccess(669),
        globalizeCreateUpdatePolicyScope(680),
        globalizeReapplyGSP(681)
    }

CucsGlRequestFsmTaskItem ::= TEXTUAL-CONVENTION
    STATUS        current
    DESCRIPTION
        ""
    SYNTAX        INTEGER
    {
        nop(0),
        evaluate(583),
        createGlobalIdPool(587),
        createGlobalPolicy(589),
        globalize(591)
    }

CucsGlRequestSessionState ::= TEXTUAL-CONVENTION
    STATUS        current
    DESCRIPTION
        ""
    SYNTAX        INTEGER
    {
        active(0),
        terminated(1)
    }

CucsGlRequestVnetEpDomainEpFsmCurrentFsm ::= TEXTUAL-CONVENTION
    STATUS        current
    DESCRIPTION
        ""
    SYNTAX        INTEGER
    {
        nop(0),
        evalData(609)
    }

CucsGlRequestVnetEpDomainEpFsmStageName ::= TEXTUAL-CONVENTION
    STATUS        current
    DESCRIPTION
        ""
    SYNTAX        INTEGER
    {
        nop(0),
        evalDataBegin(609),
        evalDataFetchDomainData(610),
        evalDataFetchVnetDependencies(611),
        evalDataFail(670),
        evalDataSuccess(671)
    }

CucsGlRequestVnetEpDomainEpFsmTaskItem ::= TEXTUAL-CONVENTION
    STATUS        current
    DESCRIPTION
        ""
    SYNTAX        INTEGER
    {
        nop(0),
        evalData(609)
    }

CucsGlRequestVnetEpFsmCurrentFsm ::= TEXTUAL-CONVENTION
    STATUS        current
    DESCRIPTION
        ""
    SYNTAX        INTEGER
    {
        nop(0),
        evalReq(601)
    }

CucsGlRequestVnetEpFsmStageName ::= TEXTUAL-CONVENTION
    STATUS        current
    DESCRIPTION
        ""
    SYNTAX        INTEGER
    {
        nop(0),
        evalReqBegin(601),
        evalReqValidate(602),
        evalReqFetchDomainData(603),
        evalReqEvaluate(605),
        evalReqCreatePolicies(606),
        evalReqGlobalize(607),
        evalReqWaitGlobalize(608),
        evalReqFail(672),
        evalReqSuccess(673)
    }

CucsGlRequestVnetEpFsmTaskItem ::= TEXTUAL-CONVENTION
    STATUS        current
    DESCRIPTION
        ""
    SYNTAX        INTEGER
    {
        nop(0),
        evalReq(601)
    }

CucsGlRuleType ::= TEXTUAL-CONVENTION
    STATUS        current
    DESCRIPTION
        ""
    SYNTAX        INTEGER
    {
        noAuto(0),
        renameBeforeEvaluate(1),
        renameAfterEvaluate(2)
    }

CucsGlVlanSharing ::= TEXTUAL-CONVENTION
    STATUS        current
    DESCRIPTION
        ""
    SYNTAX        INTEGER
    {
        none(0),
        primary(1),
        isolated(2),
        community(3)
    }

CucsGlVnetOperState ::= TEXTUAL-CONVENTION
    STATUS        current
    DESCRIPTION
        ""
    SYNTAX        INTEGER
    {
        notEvaluated(0),
        notConflict(1),
        conflict(2),
        conflictResolved(3),
        globalizing(4),
        globalized(5),
        failedToGlobalize(6)
    }

CucsGmetaCategory ::= TEXTUAL-CONVENTION
    STATUS        current
    DESCRIPTION
        ""
    SYNTAX        INTEGER
    {
        unknown(0),
        inventory(1)
    }

CucsGmetaHolderFsmCurrentFsm ::= TEXTUAL-CONVENTION
    STATUS        current
    DESCRIPTION
        ""
    SYNTAX        INTEGER
    {
        nop(0),
        inventory(1476)
    }

CucsGmetaHolderFsmStageName ::= TEXTUAL-CONVENTION
    STATUS        current
    DESCRIPTION
        ""
    SYNTAX        INTEGER
    {
        nop(0),
        inventoryBegin(1476),
        inventoryReportFullInventory(1477),
        inventoryFail(1484),
        inventorySuccess(1485),
        inventoryCheckInventoryStatus(1486),
        inventoryFullInventory(1680),
        inventoryBeginInventory(1681),
        inventoryReportPhysicalInventory(1682),
        inventoryReportOrgInventory(1683),
        inventoryReportStorageInventory(1684),
        inventoryEndInventory(1685),
        inventoryReportFaultInventory(1956)
    }

CucsGmetaHolderFsmTaskFlags ::= TEXTUAL-CONVENTION
    STATUS        current
    DESCRIPTION
        ""
    SYNTAX        BITS
    {
        samDmeGmetaHolderInventoryRegister(12)
    }

CucsGmetaHolderFsmTaskItem ::= TEXTUAL-CONVENTION
    STATUS        current
    DESCRIPTION
        ""
    SYNTAX        INTEGER
    {
        nop(0),
        inventory(1476)
    }

CucsGmetaInventoryStatus ::= TEXTUAL-CONVENTION
    STATUS        current
    DESCRIPTION
        ""
    SYNTAX        INTEGER
    {
        invDisable(0),
        invEnable(1),
        invStop(2),
        invThrottled(3)
    }

CucsGmetaPollInterval ::= TEXTUAL-CONVENTION
    STATUS        current
    DESCRIPTION
        ""
    SYNTAX        INTEGER
    {
        never(0),
        n1min(1),
        n2min(2),
        n5min(5),
        n10min(10),
        n15min(15),
        n30min(30)
    }

CucsGmetaVersion ::= TEXTUAL-CONVENTION
    STATUS        current
    DESCRIPTION
        ""
    SYNTAX        INTEGER
    {
        unknown(0),
        nextgen(2)
    }

CucsGraphicsGpuCecPresent ::= TEXTUAL-CONVENTION
    STATUS        current
    DESCRIPTION
        ""
    SYNTAX        INTEGER
    {
        no(0),
        yes(1),
        na(2)
    }

CucsGraphicsGpuMode ::= TEXTUAL-CONVENTION
    STATUS        current
    DESCRIPTION
        ""
    SYNTAX        INTEGER
    {
        compute(0),
        graphics(1),
        na(2)
    }

CucsHcAdminState ::= TEXTUAL-CONVENTION
    STATUS        current
    DESCRIPTION
        ""
    SYNTAX        INTEGER
    {
        enable(0),
        disable(1)
    }

CucsHcCatalogSourceType ::= TEXTUAL-CONVENTION
    STATUS        current
    DESCRIPTION
        ""
    SYNTAX        INTEGER
    {
        cisco(0),
        local(1)
    }

CucsHcCondition ::= TEXTUAL-CONVENTION
    STATUS        current
    DESCRIPTION
        ""
    SYNTAX        INTEGER
    {
        all(0),
        cannotDetermine(1),
        notSupported(2),
        ok(3)
    }

CucsHcDownloadPolicyType ::= TEXTUAL-CONVENTION
    STATUS        current
    DESCRIPTION
        ""
    SYNTAX        INTEGER
    {
        cisco(0),
        local(1)
    }

CucsHcErrorCode ::= TEXTUAL-CONVENTION
    STATUS        current
    DESCRIPTION
        ""
    SYNTAX        INTEGER
    {
        none(0),
        noMatchingServersFound(1),
        dnNotSpecified(3),
        invalidInput(4),
        osNotTagged(5),
        retry(6),
        dnNotSupported(7),
        ucsFwVersionNotFound(8),
        targetFwVersionInvalid(9),
        missingDataInCatalog(10),
        adapterNotTagged(11),
        targetFwVersionNotSpecified(12),
        adapterFwVersionNotFound(13)
    }

CucsHcGenerationStatus ::= TEXTUAL-CONVENTION
    STATUS        current
    DESCRIPTION
        ""
    SYNTAX        INTEGER
    {
        notStarted(0),
        inProgress(1),
        success(2),
        failed(3)
    }

CucsHcReportMoType ::= TEXTUAL-CONVENTION
    STATUS        current
    DESCRIPTION
        ""
    SYNTAX        INTEGER
    {
        unknown(0),
        profile(1),
        equipment(2),
        hostFirmwarePolicy(3),
        domain(4),
        domainGroup(5)
    }

CucsHcReportStatus ::= TEXTUAL-CONVENTION
    STATUS        current
    DESCRIPTION
        ""
    SYNTAX        INTEGER
    {
        cannotDetermine(0),
        notSupported(1),
        ok(2),
        notApplicable(3)
    }

CucsHcTransferState ::= TEXTUAL-CONVENTION
    STATUS        current
    DESCRIPTION
        ""
    SYNTAX        INTEGER
    {
        init(0),
        downloading(1),
        downloaded(2),
        downloadFailed(3),
        importing(4),
        imported(5),
        importFailed(6),
        uptodate(7)
    }

CucsHostagAction ::= TEXTUAL-CONVENTION
    STATUS        current
    DESCRIPTION
        ""
    SYNTAX        INTEGER
    {
        none(0)
    }

CucsHostagAgentType ::= TEXTUAL-CONVENTION
    STATUS        current
    DESCRIPTION
        ""
    SYNTAX        INTEGER
    {
        indeterminate(0),
        pnuosAgent(1),
        hostAgent(2)
    }

CucsHostagEvent ::= TEXTUAL-CONVENTION
    STATUS        current
    DESCRIPTION
        ""
    SYNTAX        INTEGER
    {
        none(0)
    }

CucsHostimgComposition ::= TEXTUAL-CONVENTION
    STATUS        current
    DESCRIPTION
        ""
    SYNTAX        INTEGER
    {
        complete(0),
        componentized(1)
    }

CucsHostimgDistribution ::= TEXTUAL-CONVENTION
    STATUS        current
    DESCRIPTION
        ""
    SYNTAX        INTEGER
    {
        unknown(0),
        fedora(1)
    }

CucsHostimgImgType ::= TEXTUAL-CONVENTION
    STATUS        current
    DESCRIPTION
        ""
    SYNTAX        INTEGER
    {
        unknown(0),
        esxi(1),
        kvm(2),
        xen(3),
        linux(4),
        windows(5),
        gpxeScript(6)
    }

CucsHostimgType ::= TEXTUAL-CONVENTION
    STATUS        current
    DESCRIPTION
        ""
    SYNTAX        INTEGER
    {
        complete(0),
        kernel(1),
        fileSystem(2),
        module(3),
        gpxeScript(4)
    }

CucsIdentConsType ::= TEXTUAL-CONVENTION
    STATUS        current
    DESCRIPTION
        ""
    SYNTAX        INTEGER
    {
        vnic(1),
        vhba(2),
        server(3),
        chassis(4),
        vm(5),
        vmnic(6)
    }

CucsIdentIdDefinedInIdm ::= TEXTUAL-CONVENTION
    STATUS        current
    DESCRIPTION
        ""
    SYNTAX        INTEGER
    {
        no(0),
        yes(1)
    }

CucsIdentIdentReqIntent ::= TEXTUAL-CONVENTION
    STATUS        current
    DESCRIPTION
        ""
    SYNTAX        INTEGER
    {
        sync(0),
        requisition(1),
        assign(2),
        unassign(3),
        addPooled(4),
        deletePooled(5),
        checkDuplicateId(6),
        reEvaluate(7),
        validate(8),
        unassignOnBehalfOfUcsm(9)
    }

CucsIdentIdentRequestFsmCurrentFsm ::= TEXTUAL-CONVENTION
    STATUS        current
    DESCRIPTION
        ""
    SYNTAX        INTEGER
    {
        nop(0),
        updateIdent(1336)
    }

CucsIdentIdentRequestFsmStageName ::= TEXTUAL-CONVENTION
    STATUS        current
    DESCRIPTION
        ""
    SYNTAX        INTEGER
    {
        nop(0),
        updateIdentReportIdDomainMap(383),
        updateIdentBegin(1336),
        updateIdentExecute(1337),
        updateIdentFail(1405),
        updateIdentSuccess(1406)
    }

CucsIdentIdentRequestFsmTaskFlags ::= TEXTUAL-CONVENTION
    STATUS        current
    DESCRIPTION
        ""
    SYNTAX        BITS
    {
        samDmeIdentIdentRequestUpdateIdentUpdate(5),
        samDmeIdentIdentRequestUpdateIdentReport(6)
    }

CucsIdentIdentRequestFsmTaskItem ::= TEXTUAL-CONVENTION
    STATUS        current
    DESCRIPTION
        ""
    SYNTAX        INTEGER
    {
        nop(0),
        updateIdent(1336)
    }

CucsIdentIdentType ::= TEXTUAL-CONVENTION
    STATUS        current
    DESCRIPTION
        ""
    SYNTAX        INTEGER
    {
        mac(1),
        wwnn(2),
        wwpn(3),
        uuid(4),
        vlan(5),
        ipV4(6),
        ipV6(7),
        iqn(8)
    }

CucsIdentIdmTxnType ::= TEXTUAL-CONVENTION
    STATUS        current
    DESCRIPTION
        ""
    SYNTAX        INTEGER
    {
        regular(0),
        confRename(1)
    }

CucsIdentIsUsingQualifiedPool ::= TEXTUAL-CONVENTION
    STATUS        current
    DESCRIPTION
        ""
    SYNTAX        INTEGER
    {
        no(0),
        yes(1)
    }

CucsIdentMetaSystemFsmCurrentFsm ::= TEXTUAL-CONVENTION
    STATUS        current
    DESCRIPTION
        ""
    SYNTAX        INTEGER
    {
        nop(0),
        sync(1338),
        ucscUnivSync(1618)
    }

CucsIdentMetaSystemFsmStageName ::= TEXTUAL-CONVENTION
    STATUS        current
    DESCRIPTION
        ""
    SYNTAX        INTEGER
    {
        nop(0),
        syncBegin(1338),
        syncPing(1339),
        syncExecute(1340),
        syncFail(1407),
        syncSuccess(1408),
        ucscUnivSyncBegin(1618),
        ucscUnivSyncExecute(1619),
        ucscUnivSyncFail(1622),
        ucscUnivSyncSuccess(1623)
    }

CucsIdentMetaSystemFsmTaskItem ::= TEXTUAL-CONVENTION
    STATUS        current
    DESCRIPTION
        ""
    SYNTAX        INTEGER
    {
        nop(0),
        sync(1338),
        ucscUnivSync(1618)
    }

CucsIdentOperation ::= TEXTUAL-CONVENTION
    STATUS        current
    DESCRIPTION
        ""
    SYNTAX        INTEGER
    {
        update(0),
        unassign(1),
        report(2)
    }

CucsIdentRetStatus ::= TEXTUAL-CONVENTION
    STATUS        current
    DESCRIPTION
        ""
    SYNTAX        INTEGER
    {
        inTransit(0),
        succeeded(1),
        assignedByOther(2),
        outOfSync(3),
        failed(4),
        synced(5),
        valid(6),
        invalid(7)
    }

CucsIdentpoolConsType ::= TEXTUAL-CONVENTION
    STATUS        current
    DESCRIPTION
        ""
    SYNTAX        INTEGER
    {
        vnic(1),
        vhba(2),
        server(3),
        chassis(4),
        vm(5),
        vmnic(6)
    }

CucsIdentpoolConsumedOwner ::= TEXTUAL-CONVENTION
    STATUS        current
    DESCRIPTION
        ""
    SYNTAX        INTEGER
    {
        endPoint(0),
        pool(1)
    }

CucsImgsecKeyType ::= TEXTUAL-CONVENTION
    STATUS        current
    DESCRIPTION
        ""
    SYNTAX        INTEGER
    {
        public(0),
        private(1),
        shared(2)
    }

CucsInitiatorFcInitiatorEpProt ::= TEXTUAL-CONVENTION
    STATUS        current
    DESCRIPTION
        ""
    SYNTAX        INTEGER
    {
        derived(0),
        fc(1),
        iscsi(2)
    }

CucsInitiatorGroupType ::= TEXTUAL-CONVENTION
    STATUS        current
    DESCRIPTION
        ""
    SYNTAX        INTEGER
    {
        dedicated(1),
        shared(2),
        policy(3)
    }

CucsInitiatorIScsiInitiatorEpProt ::= TEXTUAL-CONVENTION
    STATUS        current
    DESCRIPTION
        ""
    SYNTAX        INTEGER
    {
        derived(0),
        fc(1),
        iscsi(2)
    }

CucsInitiatorInitiatorEpPref ::= TEXTUAL-CONVENTION
    STATUS        current
    DESCRIPTION
        ""
    SYNTAX        INTEGER
    {
        preferred(0),
        alternate(1)
    }

CucsInventoryTrigState ::= TEXTUAL-CONVENTION
    STATUS        current
    DESCRIPTION
        ""
    SYNTAX        INTEGER
    {
        off(0),
        on(1)
    }

CucsIpIPv4DnsPref ::= TEXTUAL-CONVENTION
    STATUS        current
    DESCRIPTION
        ""
    SYNTAX        INTEGER
    {
        preferred(0),
        alternate(1)
    }

CucsIpIpV4StaticAddrPref ::= TEXTUAL-CONVENTION
    STATUS        current
    DESCRIPTION
        ""
    SYNTAX        INTEGER
    {
        preferred(0),
        alternate(1)
    }

CucsIpProtocol ::= TEXTUAL-CONVENTION
    STATUS        current
    DESCRIPTION
        ""
    SYNTAX        INTEGER
    {
        tcp(1),
        udp(2)
    }

CucsIpServiceIfPref ::= TEXTUAL-CONVENTION
    STATUS        current
    DESCRIPTION
        ""
    SYNTAX        INTEGER
    {
        preferred(0),
        alternate(1)
    }

CucsIppoolDHCPMode ::= TEXTUAL-CONVENTION
    STATUS        current
    DESCRIPTION
        ""
    SYNTAX        INTEGER
    {
        disabled(0),
        enabled(1)
    }

CucsIppoolManagementMode ::= TEXTUAL-CONVENTION
    STATUS        current
    DESCRIPTION
        ""
    SYNTAX        INTEGER
    {
        internal(0),
        external(1)
    }

CucsIppoolNetBIOSMode ::= TEXTUAL-CONVENTION
    STATUS        current
    DESCRIPTION
        ""
    SYNTAX        INTEGER
    {
        disabled(0),
        enabled(1)
    }

CucsIppoolPoolAssignmentOrder ::= TEXTUAL-CONVENTION
    STATUS        current
    DESCRIPTION
        ""
    SYNTAX        INTEGER
    {
        default(0),
        sequential(1)
    }

CucsIqnpoolBlockFrom ::= TEXTUAL-CONVENTION
    STATUS        current
    DESCRIPTION
        ""
    SYNTAX        Gauge32 (0..65535)

CucsIqnpoolBlockTo ::= TEXTUAL-CONVENTION
    STATUS        current
    DESCRIPTION
        ""
    SYNTAX        Gauge32 (0..65535)

CucsIqnpoolPoolAssignmentOrder ::= TEXTUAL-CONVENTION
    STATUS        current
    DESCRIPTION
        ""
    SYNTAX        INTEGER
    {
        default(0),
        sequential(1)
    }

CucsIqnpoolTransportBlockFrom ::= TEXTUAL-CONVENTION
    STATUS        current
    DESCRIPTION
        ""
    SYNTAX        Gauge32 (0..65535)

CucsIqnpoolTransportBlockTo ::= TEXTUAL-CONVENTION
    STATUS        current
    DESCRIPTION
        ""
    SYNTAX        Gauge32 (0..65535)

CucsIscsiProtocolProfileConnectionTimeOut ::= TEXTUAL-CONVENTION
    STATUS        current
    DESCRIPTION
        ""
    SYNTAX        Gauge32 (0..255)

CucsIscsiProtocolProfileDhcpTimeOut ::= TEXTUAL-CONVENTION
    STATUS        current
    DESCRIPTION
        ""
    SYNTAX        Gauge32 (60..300)

CucsIscsiProtocolProfileLunBusyRetryCount ::= TEXTUAL-CONVENTION
    STATUS        current
    DESCRIPTION
        ""
    SYNTAX        Gauge32 (0..60)

CucsLicenseAdminState ::= TEXTUAL-CONVENTION
    STATUS        current
    DESCRIPTION
        ""
    SYNTAX        INTEGER
    {
        disabled(0),
        enabled(1)
    }

CucsLicenseDownloadActivity ::= TEXTUAL-CONVENTION
    STATUS        current
    DESCRIPTION
        ""
    SYNTAX        INTEGER
    {
        restart(0),
        idle(1)
    }

CucsLicenseDownloaderFsmCurrentFsm ::= TEXTUAL-CONVENTION
    STATUS        current
    DESCRIPTION
        ""
    SYNTAX        INTEGER
    {
        nop(0),
        download(916)
    }

CucsLicenseDownloaderFsmStageName ::= TEXTUAL-CONVENTION
    STATUS        current
    DESCRIPTION
        ""
    SYNTAX        INTEGER
    {
        nop(0),
        downloadBegin(916),
        downloadLocal(917),
        downloadValidateLocal(918),
        downloadCopyRemote(919),
        downloadDeleteLocal(920),
        downloadValidateRemote(921),
        downloadDeleteRemote(922),
        downloadFail(994),
        downloadSuccess(995)
    }

CucsLicenseDownloaderFsmTaskItem ::= TEXTUAL-CONVENTION
    STATUS        current
    DESCRIPTION
        ""
    SYNTAX        INTEGER
    {
        nop(0),
        download(853)
    }

CucsLicenseFeatureType ::= TEXTUAL-CONVENTION
    STATUS        current
    DESCRIPTION
        ""
    SYNTAX        INTEGER
    {
        counted(0),
        boolean(1)
    }

CucsLicenseFileFsmCurrentFsm ::= TEXTUAL-CONVENTION
    STATUS        current
    DESCRIPTION
        ""
    SYNTAX        INTEGER
    {
        nop(0),
        install(923),
        clear(926)
    }

CucsLicenseFileFsmStageName ::= TEXTUAL-CONVENTION
    STATUS        current
    DESCRIPTION
        ""
    SYNTAX        INTEGER
    {
        nop(0),
        installBegin(923),
        installLocal(924),
        installRemote(925),
        clearBegin(926),
        clearLocal(927),
        clearRemote(928),
        clearFail(996),
        clearSuccess(997),
        installFail(998),
        installSuccess(999)
    }

CucsLicenseFileFsmTaskItem ::= TEXTUAL-CONVENTION
    STATUS        current
    DESCRIPTION
        ""
    SYNTAX        INTEGER
    {
        nop(0),
        install(858),
        clear(861)
    }

CucsLicenseFileState ::= TEXTUAL-CONVENTION
    STATUS        current
    DESCRIPTION
        ""
    SYNTAX        INTEGER
    {
        unknown(0),
        installPending(1),
        installing(2),
        stale(3),
        installed(4),
        installFailed(5),
        deletePending(6),
        deleting(7),
        deleted(8),
        deleteFailed(9),
        validated(10)
    }

CucsLicenseInitializationState ::= TEXTUAL-CONVENTION
    STATUS        current
    DESCRIPTION
        ""
    SYNTAX        INTEGER
    {
        uninitialized(0),
        initialized(1)
    }

CucsLicenseInstanceFsmCurrentFsm ::= TEXTUAL-CONVENTION
    STATUS        current
    DESCRIPTION
        ""
    SYNTAX        INTEGER
    {
        nop(0),
        updateFlexlm(929)
    }

CucsLicenseInstanceFsmStageName ::= TEXTUAL-CONVENTION
    STATUS        current
    DESCRIPTION
        ""
    SYNTAX        INTEGER
    {
        nop(0),
        updateFlexlmBegin(929),
        updateFlexlmLocal(930),
        updateFlexlmRemote(931),
        updateFlexlmFail(1000),
        updateFlexlmSuccess(1001)
    }

CucsLicenseInstanceFsmTaskItem ::= TEXTUAL-CONVENTION
    STATUS        current
    DESCRIPTION
        ""
    SYNTAX        INTEGER
    {
        nop(0),
        updateFlexlm(864)
    }

CucsLicensePeerStatus ::= TEXTUAL-CONVENTION
    STATUS        current
    DESCRIPTION
        ""
    SYNTAX        INTEGER
    {
        noPeer(0),
        unknown(1),
        lacks(2),
        matching(3)
    }

CucsLicenseScope ::= TEXTUAL-CONVENTION
    STATUS        current
    DESCRIPTION
        ""
    SYNTAX        INTEGER
    {
        a(1),
        b(2),
        server(3),
        unknown(4)
    }

CucsLicenseState ::= TEXTUAL-CONVENTION
    STATUS        current
    DESCRIPTION
        ""
    SYNTAX        INTEGER
    {
        unknown(0),
        licenseOk(1),
        licenseInsufficient(2),
        licenseGraceperiod(3),
        licenseExpired(4),
        notApplicable(5)
    }

CucsLicenseTransferState ::= TEXTUAL-CONVENTION
    STATUS        current
    DESCRIPTION
        ""
    SYNTAX        INTEGER
    {
        init(0),
        downloading(1),
        downloaded(2),
        failed(3)
    }

CucsLicenseTransport ::= TEXTUAL-CONVENTION
    STATUS        current
    DESCRIPTION
        ""
    SYNTAX        INTEGER
    {
        ftp(0),
        tftp(1),
        scp(2),
        sftp(3),
        local(4)
    }

CucsLicenseType ::= TEXTUAL-CONVENTION
    STATUS        current
    DESCRIPTION
        ""
    SYNTAX        INTEGER
    {
        increment(0),
        upgrade(1),
        feature(2)
    }

CucsLsAdminActionTrigger ::= TEXTUAL-CONVENTION
    STATUS        current
    DESCRIPTION
        ""
    SYNTAX        INTEGER
    {
        idle(0),
        triggered(1)
    }

CucsLsAdminActionType ::= TEXTUAL-CONVENTION
    STATUS        current
    DESCRIPTION
        ""
    SYNTAX        INTEGER
    {
        unspecified(0),
        reapplyConfig(1)
    }

CucsLsAgentCapability ::= TEXTUAL-CONVENTION
    STATUS        current
    DESCRIPTION
        ""
    SYNTAX        INTEGER
    {
        l2IfConfig(1),
        l3IfConfig(2),
        hostNameConfig(4),
        stats(8),
        states(16)
    }

CucsLsAgentLoadCatalog ::= TEXTUAL-CONVENTION
    STATUS        current
    DESCRIPTION
        ""
    SYNTAX        INTEGER
    {
        unknown(0),
        noLoad(1),
        load(2)
    }

CucsLsAgentMode ::= TEXTUAL-CONVENTION
    STATUS        current
    DESCRIPTION
        ""
    SYNTAX        INTEGER
    {
        noAgent(1),
        readOnly(2),
        full(4)
    }

CucsLsApply ::= TEXTUAL-CONVENTION
    STATUS        current
    DESCRIPTION
        ""
    SYNTAX        INTEGER
    {
        onAssociation(1),
        runTime(2)
    }

CucsLsAssignment ::= TEXTUAL-CONVENTION
    STATUS        current
    DESCRIPTION
        ""
    SYNTAX        INTEGER
    {
        unassigned(0),
        assigned(1),
        failed(2)
    }

CucsLsAssocState ::= TEXTUAL-CONVENTION
    STATUS        current
    DESCRIPTION
        ""
    SYNTAX        INTEGER
    {
        unassociated(0),
        associating(1),
        associated(2),
        disassociating(3),
        failed(4)
    }

CucsLsComputeBindingOperState ::= TEXTUAL-CONVENTION
    STATUS        current
    DESCRIPTION
        ""
    SYNTAX        INTEGER
    {
        unused(0),
        used(1),
        failedToApply(2)
    }

CucsLsConfigIssues ::= TEXTUAL-CONVENTION
    STATUS        current
    DESCRIPTION
        ""
    SYNTAX        BITS
    {
        insufficientResources(0),
        vnicCapacity(1),
        vhbaCapacity(2),
        fcoeCapacity(3),
        switchVirtualIfCapacity(4),
        macAddressAssignment(5),
        wwpnAssignment(6),
        wwnnAssignment(7),
        systemUuidAssignment(8),
        bootOrderSanImagePath(9),
        bootOrderPxe(10),
        computeUndiscovered(11),
        adaptorProtectedEthCapability(12),
        adaptorFcoeCapability(13),
        incompatibleNumberOfLocalDisks(14),
        adaptorRequirement(15),
        memoryRequirement(16),
        processorRequirement(17),
        serverPositionRequirement(18),
        computeUnavailable(19),
        wwnnDerivationFromVhba(20),
        bootConfigurationInvalid(21),
        connectionPlacement(22),
        wwpnDerivationVirtualizedPort(23),
        macDerivationVirtualizedPort(24),
        qosPolicyInvalid(25),
        vlanPortCapacity(26),
        physicalRequirement(27),
        destructiveLocalDiskConfig(28),
        powerGroupRequirement(29),
        migration(30),
        incompatibleBiosImage(31),
        incompatibleDiskTypes(32),
        incompatibleRaidLevel(33),
        invalidWwn(34),
        insufficientPowerBudget(35),
        bootipPolicyInvalid(36),
        hostimgPolicyInvalid(37),
        imgsecPolicyInvalid(38),
        provsrvPolicyInvalid(39),
        pinningInvalid(40),
        iscsiConfig(41),
        vnicNotHaReady(42),
        iscsiOverlayVnic(43),
        missingPrimaryVlan(44),
        missingRaidKey(45),
        iscsiBootInvalid(46),
        vifResourcesOverprovisioned(47),
        bootOrderIscsi(48),
        iscsiVnicInitiatorName(49),
        iscsiVnicInvalidVlan(50),
        storagePathConfigurationError(51),
        zoneCapacity(52),
        iscsiInitiatorIpAddress(53),
        vfcVnicPvlanConflict(54),
        vnicVconProvisioningChange(55),
        namedVlanInaccessible(56),
        iscsiIncompatibleOffloadSetting(57),
        nonInterruptFsmRunning(58),
        pinningVlanMismatch(59),
        vnicVlanAssignmentError(60),
        resourceOwnershipConflict(61),
        sbAdaptorBackupVersionUnsupported(62)
    }

CucsLsConfigState ::= TEXTUAL-CONVENTION
    STATUS        current
    DESCRIPTION
        ""
    SYNTAX        INTEGER
    {
        notApplied(0),
        applying(1),
        failedToApply(2),
        applied(3)
    }

CucsLsConfigWarnings ::= TEXTUAL-CONVENTION
    STATUS        current
    DESCRIPTION
        ""
    SYNTAX        BITS
    {
        kvmMgmtPolicyUnsupported(0),
        incompleteSecurityConfig(1)
    }

CucsLsFcZoneGroupSwitchId ::= TEXTUAL-CONVENTION
    STATUS        current
    DESCRIPTION
        ""
    SYNTAX        INTEGER
    {
        none(0),
        a(1),
        b(2),
        mgmt(3)
    }

CucsLsFcZoneState ::= TEXTUAL-CONVENTION
    STATUS        current
    DESCRIPTION
        ""
    SYNTAX        INTEGER
    {
        notApplied(0),
        applied(1),
        applying(2),
        applyPending(3),
        notActive(4),
        active(5),
        created(6),
        createFailed(7),
        deleted(8),
        zoneMergeFailure(9)
    }

CucsLsGlobalConfigIssues ::= TEXTUAL-CONVENTION
    STATUS        current
    DESCRIPTION
        ""
    SYNTAX        BITS
    {
        ungroupedDomain(0)
    }

CucsLsIdentityInfoWriteMode ::= TEXTUAL-CONVENTION
    STATUS        current
    DESCRIPTION
        ""
    SYNTAX        INTEGER
    {
        unsync(0),
        sync(1)
    }

CucsLsOperState ::= TEXTUAL-CONVENTION
    STATUS        current
    DESCRIPTION
        ""
    SYNTAX        INTEGER
    {
        indeterminate(0),
        unassociated(1),
        ok(10),
        discovery(11),
        config(12),
        unconfig(13),
        powerOff(14),
        restart(15),
        maintenance(20),
        test(21),
        computeMismatch(29),
        computeFailed(30),
        degraded(31),
        discoveryFailed(32),
        configFailure(33),
        unconfigFailed(34),
        testFailed(35),
        maintenanceFailed(36),
        removed(40),
        disabled(41),
        inaccessible(50),
        thermalProblem(60),
        powerProblem(61),
        voltageProblem(62),
        inoperable(63),
        decomissioning(101),
        biosRestore(201),
        cmosReset(202),
        diagnostics(203),
        diagnosticsFailed(204),
        biosPasswordReset(205),
        clearTpm(206),
        pendingReboot(210),
        pendingReassociation(211),
        svnicNotPresent(212),
        dataSanitize(213),
        dataSanitizeFailed(214)
    }

CucsLsOwner ::= TEXTUAL-CONVENTION
    STATUS        current
    DESCRIPTION
        ""
    SYNTAX        INTEGER
    {
        management(1),
        physicalInherit(2),
        physicalDefaultConfig(4),
        policy(7),
        tier(8)
    }

CucsLsPowerState ::= TEXTUAL-CONVENTION
    STATUS        current
    DESCRIPTION
        ""
    SYNTAX        INTEGER
    {
        down(0),
        up(1),
        cycleImmediate(2),
        cycleWait(3),
        hardResetImmediate(4),
        hardResetWait(5),
        softShutDown(6),
        softShutDownOnly(7),
        cmosResetImmediate(12),
        bmcResetImmediate(13),
        bmcResetWait(14),
        diagnosticInterrupt(15),
        kvmReset(16),
        biosPasswordResetImmediate(18),
        adminUp(31),
        adminDown(32),
        ipmiReset(33)
    }

CucsLsResolveFromRemoteServer ::= TEXTUAL-CONVENTION
    STATUS        current
    DESCRIPTION
        ""
    SYNTAX        INTEGER
    {
        no(0),
        yes(1)
    }

CucsLsSPMetaGlobalizationState ::= TEXTUAL-CONVENTION
    STATUS        current
    DESCRIPTION
        ""
    SYNTAX        INTEGER
    {
        noOp(0),
        globalizing(1),
        globalized(2)
    }

CucsLsSPMetaOperationCodeClearance ::= TEXTUAL-CONVENTION
    STATUS        current
    DESCRIPTION
        ""
    SYNTAX        INTEGER
    {
        enabled(1),
        disabled(2)
    }

CucsLsSPMetaSpRefresh ::= TEXTUAL-CONVENTION
    STATUS        current
    DESCRIPTION
        ""
    SYNTAX        INTEGER
    {
        enabled(1),
        disabled(2)
    }

CucsLsSPNeedIdReEvaluate ::= TEXTUAL-CONVENTION
    STATUS        current
    DESCRIPTION
        ""
    SYNTAX        INTEGER
    {
        no(0),
        yes(1)
    }

CucsLsSPOperationType ::= TEXTUAL-CONVENTION
    STATUS        current
    DESCRIPTION
        ""
    SYNTAX        INTEGER
    {
        noOp(0),
        rename(1),
        associate(2),
        disassociate(3),
        deletion(4),
        globalization(5)
    }

CucsLsSPOwnershipLC ::= TEXTUAL-CONVENTION
    STATUS        current
    DESCRIPTION
        ""
    SYNTAX        INTEGER
    {
        globalControlled(0),
        disassocPending(1),
        deletePending(2),
        localized(3)
    }

CucsLsScopeType ::= TEXTUAL-CONVENTION
    STATUS        current
    DESCRIPTION
        ""
    SYNTAX        INTEGER
    {
        all(0),
        global(1),
        local(2)
    }

CucsLsServerFsmCurrentFsm ::= TEXTUAL-CONVENTION
    STATUS        current
    DESCRIPTION
        ""
    SYNTAX        INTEGER
    {
        nop(0),
        configure(857)
    }

CucsLsServerFsmStageName ::= TEXTUAL-CONVENTION
    STATUS        current
    DESCRIPTION
        ""
    SYNTAX        INTEGER
    {
        nop(0),
        configureResolveStaticIdentifiers(350),
        configureApplyThrottle(351),
        configureConsumerVxanDeployment(358),
        configureWaitForConsumerReceivingVxan(359),
        configureDeleteIdConsumerMap(381),
        configureProcessIdConsumerMap(382),
        configureApplyRename(392),
        configureThrottleWait(415),
        configureEvaluateServerAssign(416),
        configureReplaceIdAcquirer(418),
        configureResolveDomainGroupPolicies(627),
        configureWaitForDomainGroupPolicies(628),
        configureBegin(857),
        configureApplyTemplate(858),
        configureApplyIdentifiers(859),
        configureApplyPolicies(860),
        configureResolveBootConfig(861),
        configureEvaluateAssociation(862),
        configureAnalyzeImpact(863),
        configureWaitForMaintPermission(864),
        configureWaitForMaintWindow(865),
        configureApplyConfig(866),
        configureFail(1002),
        configureSuccess(1003),
        configureResolveIdentifiers(1321),
        configureApplyDefaultIdentifiers(1322),
        configureResolveDefaultIdentifiers(1323),
        configureResolvePolicies(1324),
        configureResolveDistributableNames(1325),
        configureResolveDistributable(1326),
        configureResolveImages(1327),
        configureResolveSchedule(1328),
        configureProvisionStorage(1329),
        configureWaitForStorageProvision(1330),
        configureCommitStorage(1331),
        configureWaitForCommitStorage(1332),
        configureWaitForAssocCompletion(1333),
        configureResolveNetworkPolicies(1468),
        configureResolveNetworkTemplates(1469),
        configureValidatePolicyOwnership(1470),
        configureCheckAssignedIdentifiersForDup(1616),
        configureCheckAssignedDefaultIdentifiersForDup(1617),
        configureResolveStorageSchedule(1742),
        configureResolveVolumes(1743),
        configureApplyMaintConfig(1982),
        configureEstimateApplyConfig(2245)
    }

CucsLsServerFsmTaskFlags ::= TEXTUAL-CONVENTION
    STATUS        current
    DESCRIPTION
        ""
    SYNTAX        BITS
    {
        samDmeLsServerConfigureDomainSync(4),
        samDmeLsServerConfigureLsRename(7),
        samDmeLsServerConfigureModification(49),
        samDmeLsServerConfigureFinalDisassoc(50)
    }

CucsLsServerFsmTaskItem ::= TEXTUAL-CONVENTION
    STATUS        current
    DESCRIPTION
        ""
    SYNTAX        INTEGER
    {
        nop(0),
        configure(965)
    }

CucsLsType ::= TEXTUAL-CONVENTION
    STATUS        current
    DESCRIPTION
        ""
    SYNTAX        INTEGER
    {
        instance(0),
        initialTemplate(1),
        updatingTemplate(2)
    }

CucsLsUUIDIdentityState ::= TEXTUAL-CONVENTION
    STATUS        current
    DESCRIPTION
        ""
    SYNTAX        INTEGER
    {
        consistent(0),
        mismatch(1)
    }

CucsLsbootADefBootMode ::= TEXTUAL-CONVENTION
    STATUS        current
    DESCRIPTION
        ""
    SYNTAX        INTEGER
    {
        legacy(1),
        uefi(2)
    }

CucsLsbootAccessType ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CucsLsbootDefaultLocalImageType ::= TEXTUAL-CONVENTION
    STATUS        current
    DESCRIPTION
        ""
    SYNTAX        INTEGER
    {
        localAny(1),
        sdCard(2),
        localLun(3),
        usbIntern(4),
        usbExtern(5),
        localJbod(6),
        embeddedLocalLun(7),
        embeddedLocalJbod(8),
        nvme(9)
    }

CucsLsbootEFIShellAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CucsLsbootEFIShellType ::= TEXTUAL-CONVENTION
    STATUS        current
    DESCRIPTION
        ""
    SYNTAX        INTEGER
    {
        virtualMedia(1),
        storage(2),
        lan(3),
        iscsi(4),
        san(5),
        efiShell(6)
    }

CucsLsbootEmbeddedLocalDiskImageType ::= TEXTUAL-CONVENTION
    STATUS        current
    DESCRIPTION
        ""
    SYNTAX        INTEGER
    {
        localAny(1),
        sdCard(2),
        localLun(3),
        usbIntern(4),
        usbExtern(5),
        localJbod(6),
        embeddedLocalLun(7),
        embeddedLocalJbod(8),
        nvme(9)
    }

CucsLsbootEmbeddedLocalDiskImagePathType ::= TEXTUAL-CONVENTION
    STATUS        current
    DESCRIPTION
        ""
    SYNTAX        INTEGER
    {
        primary(0),
        secondary(1)
    }

CucsLsbootEmbeddedLocalLunImageType ::= TEXTUAL-CONVENTION
    STATUS        current
    DESCRIPTION
        ""
    SYNTAX        INTEGER
    {
        localAny(1),
        sdCard(2),
        localLun(3),
        usbIntern(4),
        usbExtern(5),
        localJbod(6),
        embeddedLocalLun(7),
        embeddedLocalJbod(8),
        nvme(9)
    }

CucsLsbootIScsiAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CucsLsbootIScsiOrder ::= TEXTUAL-CONVENTION
    STATUS        current
    DESCRIPTION
        ""
    SYNTAX        INTEGER
    {
        n1(1),
        n2(2),
        n3(3),
        n4(4),
        n5(5)
    }

CucsLsbootIScsiType ::= TEXTUAL-CONVENTION
    STATUS        current
    DESCRIPTION
        ""
    SYNTAX        INTEGER
    {
        virtualMedia(1),
        storage(2),
        lan(3),
        iscsi(4),
        san(5),
        efiShell(6)
    }

CucsLsbootIScsiImagePathType ::= TEXTUAL-CONVENTION
    STATUS        current
    DESCRIPTION
        ""
    SYNTAX        INTEGER
    {
        primary(0),
        secondary(1)
    }

CucsLsbootImagePathIpAddrType ::= TEXTUAL-CONVENTION
    STATUS        current
    DESCRIPTION
        ""
    SYNTAX        INTEGER
    {
        none(0),
        ipv4(1),
        ipv6(2)
    }

CucsLsbootLanAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CucsLsbootLanOrder ::= TEXTUAL-CONVENTION
    STATUS        current
    DESCRIPTION
        ""
    SYNTAX        INTEGER
    {
        n1(1),
        n2(2),
        n3(3),
        n4(4),
        n5(5)
    }

CucsLsbootLanType ::= TEXTUAL-CONVENTION
    STATUS        current
    DESCRIPTION
        ""
    SYNTAX        INTEGER
    {
        virtualMedia(1),
        storage(2),
        lan(3),
        iscsi(4),
        san(5),
        efiShell(6)
    }

CucsLsbootLanBootProt ::= TEXTUAL-CONVENTION
    STATUS        current
    DESCRIPTION
        ""
    SYNTAX        INTEGER
    {
        pxe(0),
        gpxe(1),
        iSCSI(2)
    }

CucsLsbootLanImagePathType ::= TEXTUAL-CONVENTION
    STATUS        current
    DESCRIPTION
        ""
    SYNTAX        INTEGER
    {
        primary(0),
        secondary(1)
    }

CucsLsbootLocalDiskImageType ::= TEXTUAL-CONVENTION
    STATUS        current
    DESCRIPTION
        ""
    SYNTAX        INTEGER
    {
        localAny(1),
        sdCard(2),
        localLun(3),
        usbIntern(4),
        usbExtern(5),
        localJbod(6),
        embeddedLocalLun(7),
        embeddedLocalJbod(8),
        nvme(9)
    }

CucsLsbootLocalDiskImagePathType ::= TEXTUAL-CONVENTION
    STATUS        current
    DESCRIPTION
        ""
    SYNTAX        INTEGER
    {
        primary(0),
        secondary(1)
    }

CucsLsbootLocalHddImageType ::= TEXTUAL-CONVENTION
    STATUS        current
    DESCRIPTION
        ""
    SYNTAX        INTEGER
    {
        localAny(1),
        sdCard(2),
        localLun(3),
        usbIntern(4),
        usbExtern(5),
        localJbod(6),
        embeddedLocalLun(7),
        embeddedLocalJbod(8),
        nvme(9)
    }

CucsLsbootLocalLunImagePathType ::= TEXTUAL-CONVENTION
    STATUS        current
    DESCRIPTION
        ""
    SYNTAX        INTEGER
    {
        primary(0),
        secondary(1)
    }

CucsLsbootNvmeType ::= TEXTUAL-CONVENTION
    STATUS        current
    DESCRIPTION
        ""
    SYNTAX        INTEGER
    {
        localAny(1),
        sdCard(2),
        localLun(3),
        usbIntern(4),
        usbExtern(5),
        localJbod(6),
        embeddedLocalLun(7),
        embeddedLocalJbod(8),
        nvme(9)
    }

CucsLsbootNvmeDiskSsdType ::= TEXTUAL-CONVENTION
    STATUS        current
    DESCRIPTION
        ""
    SYNTAX        INTEGER
    {
        diskSsd(1),
        pciSsd(2)
    }

CucsLsbootNvmePciSsdType ::= TEXTUAL-CONVENTION
    STATUS        current
    DESCRIPTION
        ""
    SYNTAX        INTEGER
    {
        diskSsd(1),
        pciSsd(2)
    }

CucsLsbootPurpose ::= TEXTUAL-CONVENTION
    STATUS        current
    DESCRIPTION
        ""
    SYNTAX        INTEGER
    {
        utility(1),
        operational(2)
    }

CucsLsbootSanAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CucsLsbootSanType ::= TEXTUAL-CONVENTION
    STATUS        current
    DESCRIPTION
        ""
    SYNTAX        INTEGER
    {
        virtualMedia(1),
        storage(2),
        lan(3),
        iscsi(4),
        san(5),
        efiShell(6)
    }

CucsLsbootSanCatSanImageType ::= TEXTUAL-CONVENTION
    STATUS        current
    DESCRIPTION
        ""
    SYNTAX        INTEGER
    {
        primary(0),
        secondary(1)
    }

CucsLsbootSanCatSanImagePathType ::= TEXTUAL-CONVENTION
    STATUS        current
    DESCRIPTION
        ""
    SYNTAX        INTEGER
    {
        primary(0),
        secondary(1)
    }

CucsLsbootSanImageType ::= TEXTUAL-CONVENTION
    STATUS        current
    DESCRIPTION
        ""
    SYNTAX        INTEGER
    {
        primary(0),
        secondary(1)
    }

CucsLsbootSanImagePathType ::= TEXTUAL-CONVENTION
    STATUS        current
    DESCRIPTION
        ""
    SYNTAX        INTEGER
    {
        primary(0),
        secondary(1)
    }

CucsLsbootStorageAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CucsLsbootStorageOrder ::= TEXTUAL-CONVENTION
    STATUS        current
    DESCRIPTION
        ""
    SYNTAX        INTEGER
    {
        n1(1),
        n2(2),
        n3(3),
        n4(4),
        n5(5)
    }

CucsLsbootStorageType ::= TEXTUAL-CONVENTION
    STATUS        current
    DESCRIPTION
        ""
    SYNTAX        INTEGER
    {
        virtualMedia(1),
        storage(2),
        lan(3),
        iscsi(4),
        san(5),
        efiShell(6)
    }

CucsLsbootUsbExternalImageType ::= TEXTUAL-CONVENTION
    STATUS        current
    DESCRIPTION
        ""
    SYNTAX        INTEGER
    {
        localAny(1),
        sdCard(2),
        localLun(3),
        usbIntern(4),
        usbExtern(5),
        localJbod(6),
        embeddedLocalLun(7),
        embeddedLocalJbod(8),
        nvme(9)
    }

CucsLsbootUsbFlashStorageImageType ::= TEXTUAL-CONVENTION
    STATUS        current
    DESCRIPTION
        ""
    SYNTAX        INTEGER
    {
        localAny(1),
        sdCard(2),
        localLun(3),
        usbIntern(4),
        usbExtern(5),
        localJbod(6),
        embeddedLocalLun(7),
        embeddedLocalJbod(8),
        nvme(9)
    }

CucsLsbootUsbInternalImageType ::= TEXTUAL-CONVENTION
    STATUS        current
    DESCRIPTION
        ""
    SYNTAX        INTEGER
    {
        localAny(1),
        sdCard(2),
        localLun(3),
        usbIntern(4),
        usbExtern(5),
        localJbod(6),
        embeddedLocalLun(7),
        embeddedLocalJbod(8),
        nvme(9)
    }

CucsLsbootVirtualMediaAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6)
    }

CucsLsbootVirtualMediaOrder ::= TEXTUAL-CONVENTION
    STATUS        current
    DESCRIPTION
        ""
    SYNTAX        INTEGER
    {
        n1(1),
        n2(2),
        n3(3),
        n4(4),
        n5(5)
    }

CucsLsbootVirtualMediaType ::= TEXTUAL-CONVENTION
    STATUS        current
    DESCRIPTION
        ""
    SYNTAX        INTEGER
    {
        virtualMedia(1),
        storage(2),
        lan(3),
        iscsi(4),
        san(5),
        efiShell(6)
    }

CucsLsmaintAckChangeDetails ::= TEXTUAL-CONVENTION
    STATUS        current
    DESCRIPTION
        ""
    SYNTAX        BITS
    {
        binding(0),
        hostVirtEthIf(1),
        hostNonvirtEthIf(2),
        hostEthIfQos(3),
        hostEthIfNwCtrl(4),
        hostVirtFcIf(6),
        hostNonvirtFcIf(7),
        hostVirtFcIfPersBind(8),
        hostNonvirtFcIfPersBind(9),
        vif(10),
        vlan(11),
        vsan(12),
        ip(13),
        bootOrder(14),
        bootLocalStorage(16),
        bootVirtVnic(18),
        bootNonvirtVnic(19),
        biosFw(20),
        storageControllerFw(21),
        bootNonvirtPxe(22),
        adaptorNwFw(23),
        mgmtControllerFw(24),
        localDiskPolicy(25),
        pin(26),
        sol(27),
        epAuth(28),
        biosProfile(29),
        checkpoint(30),
        implicitReboot(31),
        implicitHostFcIfProfileRedeploy(32),
        boardControllerFw(33),
        hostEthIfQosHostControl(40),
        localDiskFw(41),
        implicitHostEthIfProfileRedeploy(42),
        storagePath(43),
        hostIfPcie(45),
        flexflashConfig(46),
        flexflashReboot(47),
        bootmodeConfig(48),
        securebootConfig(49),
        vmediaConfig(50),
        storageApplianceSw(51),
        storageTargetId(52),
        remoteStorageConfig(53),
        storageDevBridgeFw(54),
        sasExpanderFw(55),
        fanSpeedConfig(57),
        sasExpRegFw(58),
        assetTagConfig(59),
        pciSwitchFw(60),
        localDiskDataLoss(61),
        localStorageSecurity(62),
        nvmeMswitchFw(63)
    }

CucsLsmaintAckChanges ::= TEXTUAL-CONVENTION
    STATUS        current
    DESCRIPTION
        ""
    SYNTAX        BITS
    {
        serverIdentity(0),
        storage(1),
        networking(2),
        vnicVhbaPlacement(3),
        serverAssignment(4),
        operationalPolicies(5),
        storageIdentity(7)
    }

CucsLsmaintAckDisr ::= TEXTUAL-CONVENTION
    STATUS        current
    DESCRIPTION
        ""
    SYNTAX        BITS
    {
        upTime(0),
        acPowerCycle(1),
        storageAccess(2),
        storageUptime(3)
    }

CucsLsmaintAckExtdChangeDetails ::= TEXTUAL-CONVENTION
    STATUS        current
    DESCRIPTION
        ""
    SYNTAX        BITS
    {
        persistentMemoryPolicy(0),
        persistentMemoryDimmFw(1),
        hostPackHaveBackupSet(2),
        adaptorSwmReset(3),
        ubmFw(4),
        cpldFw(5),
        retimerFw(6),
        hybridLocalSlotConfig(7),
        intelAmcFw(8)
    }

CucsLsmaintChangeMode ::= TEXTUAL-CONVENTION
    STATUS        current
    DESCRIPTION
        ""
    SYNTAX        INTEGER
    {
        noChange(0),
        unconfig(1),
        forceUnconfig(2),
        rediscover(4),
        config(8),
        diagConfig(16),
        diagUnconfig(32),
        removeConfig(64),
        diag(128),
        configEvaluation(256)
    }

CucsLsmaintMaintPolicyUptimeDisr ::= TEXTUAL-CONVENTION
    STATUS        current
    DESCRIPTION
        ""
    SYNTAX        INTEGER
    {
        immediate(0),
        userAck(1),
        timerAutomatic(2)
    }

CucsLstorageAckChangeDetails ::= TEXTUAL-CONVENTION
    STATUS        current
    DESCRIPTION
        ""
    SYNTAX        BITS
    {
        binding(0),
        hostVirtEthIf(1),
        hostNonvirtEthIf(2),
        hostEthIfProfile(3),
        hostEthIfQos(4),
        hostEthIfNwCtrl(5),
        hostVirtFcIf(6),
        hostNonvirtFcIf(7),
        hostVirtFcIfPersBind(8),
        hostNonvirtFcIfPersBind(9),
        hostFcIfProfile(10),
        hostFcIfQos(11),
        hostFcoeIf(12),
        vif(13),
        vlan(14),
        vsan(15),
        ip(16),
        bootOrder(17),
        bootVirtVnic(18),
        bootNonvirtVnic(19),
        bootLocalStorage(20),
        bootVirtPxe(21),
        bootNonvirtPxe(22),
        bladeIdentity(24),
        agentPolicy(25),
        biosFw(26),
        storageControllerFw(27),
        adaptorHostFw(28),
        adaptorNwFw(29),
        mgmtControllerFw(30),
        localDiskPolicy(31),
        pin(32),
        sol(33),
        epAuth(34),
        biosProfile(35),
        checkpoint(36),
        implicitReboot(37),
        implicitHostFcIfProfileRedeploy(38),
        boardControllerFw(39),
        hostEthIfQosHostControl(40),
        localDiskFw(41),
        implicitHostEthIfProfileRedeploy(42),
        storagePath(43),
        bmcUpdateBiosFw(44),
        hostIfPcie(45),
        flexflashConfig(46),
        bootmodeConfig(48),
        securebootConfig(49),
        vmediaConfig(50),
        storageApplianceSw(51),
        storageTargetId(52),
        remoteStorageConfig(53),
        storageDevBridgeFw(54),
        sasExpanderFw(55)
    }

CucsLstorageAckChanges ::= TEXTUAL-CONVENTION
    STATUS        current
    DESCRIPTION
        ""
    SYNTAX        BITS
    {
        serverIdentity(0),
        storage(1),
        networking(2),
        vnicVhbaPlacement(3),
        bootOrder(4),
        serverAssignment(5),
        operationalPolicies(6),
        storageIdentity(7)
    }

CucsLstorageAckDisr ::= TEXTUAL-CONVENTION
    STATUS        current
    DESCRIPTION
        ""
    SYNTAX        BITS
    {
        upTime(0),
        acPowerCycle(1),
        storageAccess(2),
        storageUptime(3)
    }

CucsLstorageAdminState ::= TEXTUAL-CONVENTION
    STATUS        current
    DESCRIPTION
        ""
    SYNTAX        INTEGER
    {
        online(1),
        offline(2),
        undeployed(4)
    }

CucsLstorageAutoDeploy ::= TEXTUAL-CONVENTION
    STATUS        current
    DESCRIPTION
        ""
    SYNTAX        INTEGER
    {
        autoDeploy(0),
        noAutoDeploy(1)
    }

CucsLstorageAvailability ::= TEXTUAL-CONVENTION
    STATUS        current
    DESCRIPTION
        ""
    SYNTAX        INTEGER
    {
        unavailable(0),
        available(1)
    }

CucsLstorageBootDevice ::= TEXTUAL-CONVENTION
    STATUS        current
    DESCRIPTION
        ""
    SYNTAX        INTEGER
    {
        disabled(0),
        enabled(1)
    }

CucsLstorageChangeMode ::= TEXTUAL-CONVENTION
    STATUS        current
    DESCRIPTION
        ""
    SYNTAX        INTEGER
    {
        noChange(0),
        unconfig(1),
        forceUnconfig(2),
        config(3),
        removeConfig(4)
    }

CucsLstorageConfigFlags ::= TEXTUAL-CONVENTION
    STATUS        current
    DESCRIPTION
        ""
    SYNTAX        BITS
    {
        createProcessor(0),
        createArrayBinding(1),
        vlanChange(2),
        ipChange(3),
        fwPolicyChange(4),
        storagePolicyChange(5),
        notTriggerAssoc(6),
        hostFirmwarePolicyChange(7),
        iqnTragetNameChange(8),
        applianceSoftwarePolicyChange(9),
        maintenancePolicyChange(10),
        interfaceCountChange(11),
        svcPolicyChange(12),
        templateChange(13),
        sharedSecretChange(14)
    }

CucsLstorageConfigIssues ::= TEXTUAL-CONVENTION
    STATUS        current
    DESCRIPTION
        ""
    SYNTAX        BITS
    {
        lunIdConflict(0),
        lunCapacityExceeded(1),
        lunLimitExceeded(2),
        storageUnavailable(3),
        unsupportedStorageCapability(4),
        insufficientLunResources(5),
        lunOwnershipConflict(6),
        identityAssignment(7),
        missingFirmwareImage(8)
    }

CucsLstorageConfigState ::= TEXTUAL-CONVENTION
    STATUS        current
    DESCRIPTION
        ""
    SYNTAX        INTEGER
    {
        ok(0),
        applied(1),
        failedToApply(2),
        applying(3)
    }

CucsLstorageControllerQualifierControllerType ::= TEXTUAL-CONVENTION
    STATUS        current
    DESCRIPTION
        ""
    SYNTAX        INTEGER
    {
        unknown(0),
        sas(1),
        sata(2),
        flash(3),
        sd(4),
        pt(5),
        pch(6),
        external(7),
        nvme(8),
        hba(9),
        m2(10),
        fch(11)
    }

CucsLstorageControllerRefControllerId ::= TEXTUAL-CONVENTION
    STATUS        current
    DESCRIPTION
        ""
    SYNTAX        Gauge32 (1..1)

CucsLstorageControllerRefControllerType ::= TEXTUAL-CONVENTION
    STATUS        current
    DESCRIPTION
        ""
    SYNTAX        INTEGER
    {
        unknown(0),
        sas(1),
        sata(2),
        flash(3),
        sd(4),
        pt(5),
        pch(6),
        external(7),
        nvme(8),
        hba(9),
        m2(10),
        fch(11)
    }

CucsLstorageControllerRefServerId ::= TEXTUAL-CONVENTION
    STATUS        current
    DESCRIPTION
        ""
    SYNTAX        Gauge32 (1..2)

CucsLstorageCtrlAdminState ::= TEXTUAL-CONVENTION
    STATUS        current
    DESCRIPTION
        ""
    SYNTAX        INTEGER
    {
        inService(1),
        inMaintenance(3)
    }

CucsLstorageDasScsiLunStorageClass ::= TEXTUAL-CONVENTION
    STATUS        current
    DESCRIPTION
        ""
    SYNTAX        INTEGER
    {
        san(1),
        das(2)
    }

CucsLstorageDay ::= TEXTUAL-CONVENTION
    STATUS        current
    DESCRIPTION
        ""
    SYNTAX        INTEGER
    {
        everyDay(0),
        monday(1),
        tuesday(2),
        wednesday(3),
        thursday(4),
        friday(5),
        saturday(6),
        sunday(7),
        everyMonth(8),
        everyHour(9)
    }

CucsLstorageDiskSlotDrivePath ::= TEXTUAL-CONVENTION
    STATUS        current
    DESCRIPTION
        ""
    SYNTAX        INTEGER
    {
        unknown(0),
        pathBoth(1),
        path0(2),
        path1(3),
        none(4)
    }

CucsLstorageDiskSlotOwnership ::= TEXTUAL-CONVENTION
    STATUS        current
    DESCRIPTION
        ""
    SYNTAX        INTEGER
    {
        unknown(0),
        unassigned(1),
        dedicated(2),
        shared(3),
        chassisGlobalSpare(4),
        chassisDedicatedSpare(5)
    }

CucsLstorageInitiatorInterfaceType ::= TEXTUAL-CONVENTION
    STATUS        current
    DESCRIPTION
        ""
    SYNTAX        INTEGER
    {
        unspecified(0),
        native(1),
        vdas(2)
    }

CucsLstorageLunDiskLayout ::= TEXTUAL-CONVENTION
    STATUS        current
    DESCRIPTION
        ""
    SYNTAX        INTEGER
    {
        raidStriped(4),
        raidMirrored(5),
        anyConfiguration(8),
        raidStripedParity(10),
        raidStripedDualParity(11),
        raidMirroredStriped(12),
        raidStripedParityStriped(16),
        raidStripedDualParityStriped(17)
    }

CucsLstorageLunMapType ::= TEXTUAL-CONVENTION
    STATUS        current
    DESCRIPTION
        ""
    SYNTAX        INTEGER
    {
        nonShared(0),
        shared(1),
        unassigned(2)
    }

CucsLstorageNetworkIssues ::= TEXTUAL-CONVENTION
    STATUS        current
    DESCRIPTION
        ""
    SYNTAX        BITS
    {
        invalidConfig(0),
        invalidIscsiVlan(1),
        unsupportedVlanCapability(2),
        invalidIpAddress(3)
    }

CucsLstorageOperMaintState ::= TEXTUAL-CONVENTION
    STATUS        current
    DESCRIPTION
        ""
    SYNTAX        INTEGER
    {
        unknown(0),
        inService(1),
        inMaintenance(2),
        enteringMaintenance(3),
        exitingMaintenance(4),
        notApplicable(5)
    }

CucsLstorageOwner ::= TEXTUAL-CONVENTION
    STATUS        current
    DESCRIPTION
        ""
    SYNTAX        INTEGER
    {
        policy(1),
        management(2)
    }

CucsLstorageProcessorFsmCurrentFsm ::= TEXTUAL-CONVENTION
    STATUS        current
    DESCRIPTION
        ""
    SYNTAX        INTEGER
    {
        nop(0),
        configure(1747)
    }

CucsLstorageProcessorFsmStageName ::= TEXTUAL-CONVENTION
    STATUS        current
    DESCRIPTION
        ""
    SYNTAX        INTEGER
    {
        nop(0),
        configureBegin(1747),
        configureApplyTemplate(1748),
        configureApplyIdentifiers(1749),
        configureResolvePolicies(1750),
        configureResolveNetworkPolicies(1751),
        configureResolveIdentifiers(1752),
        configureApplyDefaultIdentifiers(1753),
        configureResolveDefaultIdentifiers(1754),
        configureResolveDistributableNames(1755),
        configureResolveDistributable(1756),
        configureResolveImages(1757),
        configureResolveSchedule(1758),
        configureValidatePolicyOwnership(1759),
        configureApplyPolicies(1760),
        configureResolveBootConfig(1761),
        configureEvaluateAssociation(1762),
        configureAnalyzeImpact(1763),
        configureWaitForMaintPermission(1764),
        configureWaitForMaintWindow(1765),
        configureWaitForHAQuorum(1766),
        configureApplyConfig(1767),
        configureWaitForServerAssoc(1768),
        configureWaitForPlatformBoot(1769),
        configureWaitForOSInstall(1770),
        configureWaitForPlatformConfig(1771),
        configureFail(1823),
        configureSuccess(1824)
    }

CucsLstorageProcessorFsmTaskFlags ::= TEXTUAL-CONVENTION
    STATUS        current
    DESCRIPTION
        ""
    SYNTAX        BITS
    {
        samDmeLstorageProcessorConfigureModification(28),
        samDmeLstorageProcessorConfigureFinalDisassoc(29)
    }

CucsLstorageProcessorFsmTaskItem ::= TEXTUAL-CONVENTION
    STATUS        current
    DESCRIPTION
        ""
    SYNTAX        INTEGER
    {
        nop(0),
        configure(1747)
    }

CucsLstorageProcessorId ::= TEXTUAL-CONVENTION
    STATUS        current
    DESCRIPTION
        ""
    SYNTAX        INTEGER
    {
        n1(1),
        n2(2)
    }

CucsLstorageRemoteCtrlServiceAdminState ::= TEXTUAL-CONVENTION
    STATUS        current
    DESCRIPTION
        ""
    SYNTAX        INTEGER
    {
        remoteTrigger(0),
        inService(1),
        inMaintenance(3)
    }

CucsLstorageRemoteCtrlServiceFailOverState ::= TEXTUAL-CONVENTION
    STATUS        current
    DESCRIPTION
        ""
    SYNTAX        INTEGER
    {
        triggered(0),
        trigger(1),
        forceTrigger(2),
        remoteTrigger(3)
    }

CucsLstorageReplicationDeviceType ::= TEXTUAL-CONVENTION
    STATUS        current
    DESCRIPTION
        ""
    SYNTAX        INTEGER
    {
        lun(1),
        nfs(2)
    }

CucsLstorageReplicationSourceAccessType ::= TEXTUAL-CONVENTION
    STATUS        current
    DESCRIPTION
        ""
    SYNTAX        INTEGER
    {
        allowAll(1),
        allowNone(2),
        allowOnly(3)
    }

CucsLstorageReplicationTargetType ::= TEXTUAL-CONVENTION
    STATUS        current
    DESCRIPTION
        ""
    SYNTAX        INTEGER
    {
        cisco(1),
        linuxLVM(2),
        linuxRAW(3),
        windows(4)
    }

CucsLstorageResolveFromRemoteServer ::= TEXTUAL-CONVENTION
    STATUS        current
    DESCRIPTION
        ""
    SYNTAX        INTEGER
    {
        no(0),
        yes(1)
    }

CucsLstorageSasExpanderConfigPolicyConnectionManagement ::= TEXTUAL-CONVENTION
    STATUS        current
    DESCRIPTION
        ""
    SYNTAX        INTEGER
    {
        disabled(0),
        enabled(1),
        unknown(2),
        default(3)
    }

CucsLstorageScsiTransportProtocol ::= TEXTUAL-CONVENTION
    STATUS        current
    DESCRIPTION
        ""
    SYNTAX        INTEGER
    {
        unspecified(0),
        iscsi(1),
        fcp(2),
        sas(3),
        ssa(4),
        uas(5),
        scsiParallel(6)
    }

CucsLstorageServerIssues ::= TEXTUAL-CONVENTION
    STATUS        current
    DESCRIPTION
        ""
    SYNTAX        BITS
    {
        invalidConfig(0),
        processorCardinality(1),
        unsupportedStorageServer(2),
        localRemotePolicyConflict(3),
        invalidProfileReferences(4),
        invalidNumberOfIscsiInterfaces(5),
        computeUnavailable(6),
        computeInoperable(7),
        computeDegraded(8),
        invalidNumberOfDpInterfaces(9),
        invalidDpInterfaceSwitchId(10),
        invalidIscsiInterfaceSwitchId(11),
        missingFirmwareImage(12),
        insufficientResources(13)
    }

CucsLstorageSharing ::= TEXTUAL-CONVENTION
    STATUS        current
    DESCRIPTION
        ""
    SYNTAX        INTEGER
    {
        nonShared(0),
        shared(1)
    }

CucsLstorageStorageClass ::= TEXTUAL-CONVENTION
    STATUS        current
    DESCRIPTION
        ""
    SYNTAX        INTEGER
    {
        san(1),
        das(2)
    }

CucsLstorageStorageIssues ::= TEXTUAL-CONVENTION
    STATUS        current
    DESCRIPTION
        ""
    SYNTAX        BITS
    {
        invalidConfig(0),
        missingFirmwareImage(1),
        invalidIqnFormat(2)
    }

CucsLstorageUpgradeState ::= TEXTUAL-CONVENTION
    STATUS        current
    DESCRIPTION
        ""
    SYNTAX        INTEGER
    {
        unknown(0),
        partnerUpgrading(1),
        configureVmedia(2),
        bootingController(3),
        packageInstallation(4),
        unconfigureVmedia(5),
        ready(6)
    }

CucsLstorageVirtualDriveDefAccessPolicy ::= TEXTUAL-CONVENTION
    STATUS        current
    DESCRIPTION
        ""
    SYNTAX        INTEGER
    {
        unknown(0),
        readWrite(1),
        readOnly(2),
        blocked(3),
        transportReady(4),
        hidden(5)
    }

CucsLstorageVirtualDriveDefDriveCache ::= TEXTUAL-CONVENTION
    STATUS        current
    DESCRIPTION
        ""
    SYNTAX        INTEGER
    {
        unknown(0),
        noChange(1),
        enable(2),
        disable(3)
    }

CucsLstorageVirtualDriveDefIoPolicy ::= TEXTUAL-CONVENTION
    STATUS        current
    DESCRIPTION
        ""
    SYNTAX        INTEGER
    {
        unknown(0),
        direct(1),
        cached(2)
    }

CucsLstorageVirtualDriveDefReadPolicy ::= TEXTUAL-CONVENTION
    STATUS        current
    DESCRIPTION
        ""
    SYNTAX        INTEGER
    {
        unknown(0),
        readAhead(1),
        normal(2)
    }

CucsLstorageVirtualDriveDefStripSize ::= TEXTUAL-CONVENTION
    STATUS        current
    DESCRIPTION
        ""
    SYNTAX        INTEGER
    {
        unspecified(0),
        n8KB(1),
        n16KB(2),
        n32KB(3),
        n64KB(4),
        n128KB(5),
        n256KB(6),
        n512KB(7),
        n1024KB(8)
    }

CucsLstorageVirtualDriveDefWriteCachePolicy ::= TEXTUAL-CONVENTION
    STATUS        current
    DESCRIPTION
        ""
    SYNTAX        INTEGER
    {
        unknown(0),
        writeThrough(1),
        writeBackGoodBbu(2),
        alwaysWriteBack(3)
    }

CucsMacpoolPoolAssignmentOrder ::= TEXTUAL-CONVENTION
    STATUS        current
    DESCRIPTION
        ""
    SYNTAX        INTEGER
    {
        default(0),
        sequential(1)
    }

CucsMemoryAUnitOperability ::= TEXTUAL-CONVENTION
    STATUS        current
    DESCRIPTION
        ""
    SYNTAX        INTEGER
    {
        unknown(0),
        operable(1),
        inoperable(2),
        degraded(3),
        poweredOff(4),
        powerProblem(5),
        removed(6),
        voltageProblem(7),
        thermalProblem(8),
        performanceProblem(9),
        accessibilityProblem(10),
        identityUnestablishable(11),
        biosPostTimeout(12),
        disabled(13),
        malformedFru(14),
        backplanePortProblem(15),
        chassisIntrusion(16),
        nonOptimal(17),
        unsupportedConfig(18),
        nonOptimalSevere(20),
        peerDimmDisabled(21),
        dimmDisabled(22),
        fabricConnProblem(51),
        fabricUnsupportedConn(52),
        config(81),
        equipmentProblem(82),
        decomissioning(83),
        chassisLimitExceeded(84),
        notSupported(100),
        discovery(101),
        discoveryFailed(102),
        identify(103),
        postFailure(104),
        upgradeProblem(105),
        peerCommProblem(106),
        autoUpgrade(107),
        linkActivateBlocked(108)
    }

CucsMemoryAdminState ::= TEXTUAL-CONVENTION
    STATUS        current
    DESCRIPTION
        ""
    SYNTAX        INTEGER
    {
        policy(1),
        resetErrors(2)
    }

CucsMemoryAllSocketId ::= TEXTUAL-CONVENTION
    STATUS        current
    DESCRIPTION
        ""
    SYNTAX        INTEGER
    {
        allSockets(0)
    }

CucsMemoryAnySocketId ::= TEXTUAL-CONVENTION
    STATUS        current
    DESCRIPTION
        ""
    SYNTAX        INTEGER
    {
        socket1(1),
        socket2(2),
        socket3(3),
        socket4(4)
    }

CucsMemoryAnySocketLocalDimmNumber ::= TEXTUAL-CONVENTION
    STATUS        current
    DESCRIPTION
        ""
    SYNTAX        INTEGER
    {
        notApplicable(0),
        n2(2),
        n3(3),
        n4(4),
        n6(6),
        n7(7),
        n8(8),
        n10(10),
        n11(11),
        n12(12),
        n14(14),
        n15(15),
        n16(16)
    }

CucsMemoryArrayId ::= TEXTUAL-CONVENTION
    STATUS        current
    DESCRIPTION
        ""
    SYNTAX        Gauge32 (1..8)

CucsMemoryArrayEnvStatsThresholded ::= TEXTUAL-CONVENTION
    STATUS        current
    DESCRIPTION
        ""
    SYNTAX        BITS
    {
        inputCurrent(0),
        inputCurrentAvg(1),
        inputCurrentMax(2),
        inputCurrentMin(3)
    }

CucsMemoryArrayEnvStatsHistThresholded ::= TEXTUAL-CONVENTION
    STATUS        current
    DESCRIPTION
        ""
    SYNTAX        BITS
    {
        inputCurrent(0),
        inputCurrentAvg(1),
        inputCurrentMax(2),
        inputCurrentMin(3)
    }

CucsMemoryBackupAbility ::= TEXTUAL-CONVENTION
    STATUS        current
    DESCRIPTION
        ""
    SYNTAX        INTEGER
    {
        unknown(0),
        notReady(1),
        ready(2)
    }

CucsMemoryBackupStatus ::= TEXTUAL-CONVENTION
    STATUS        current
    DESCRIPTION
        ""
    SYNTAX        INTEGER
    {
        unknown(0),
        noBackup(1),
        valid(2)
    }

CucsMemoryBackupTriggerStatus ::= TEXTUAL-CONVENTION
    STATUS        current
    DESCRIPTION
        ""
    SYNTAX        INTEGER
    {
        unknown(0),
        enabled(1),
        disabled(2)
    }

CucsMemoryBufferUnitId ::= TEXTUAL-CONVENTION
    STATUS        current
    DESCRIPTION
        ""
    SYNTAX        Gauge32 (1..16)

CucsMemoryBufferUnitEnvStatsThresholded ::= TEXTUAL-CONVENTION
    STATUS        current
    DESCRIPTION
        ""
    SYNTAX        BITS
    {
        temperature(0),
        temperatureAvg(1),
        temperatureMax(2),
        temperatureMin(3)
    }

CucsMemoryBufferUnitEnvStatsHistThresholded ::= TEXTUAL-CONVENTION
    STATUS        current
    DESCRIPTION
        ""
    SYNTAX        BITS
    {
        temperature(0),
        temperatureAvg(1),
        temperatureMax(2),
        temperatureMin(3)
    }

CucsMemoryControllerId ::= TEXTUAL-CONVENTION
    STATUS        current
    DESCRIPTION
        ""
    SYNTAX        Gauge32 (1..8)

CucsMemoryErrorCorrection ::= TEXTUAL-CONVENTION
    STATUS        current
    DESCRIPTION
        ""
    SYNTAX        INTEGER
    {
        undiscovered(0),
        other(1),
        unknown(2),
        none(3),
        parity(4),
        singleBitECC(5),
        multiBitECC(6),
        crc(7)
    }

CucsMemoryErrorStatsThresholded ::= TEXTUAL-CONVENTION
    STATUS        current
    DESCRIPTION
        ""
    SYNTAX        BITS
    {
        dramWriteDataCorrectableCRCErrors(0),
        eccMultibitErrors(1),
        eccSinglebitErrors(2),
        mismatchErrors(3),
        addressParityErrorsUnCorrectable(4),
        eccMultibitErrorsAvg(6),
        eccMultibitErrorsMax(7),
        eccMultibitErrorsMin(8),
        eccMultibitErrorsRunning(9),
        eccSinglebitErrorsAvg(11),
        eccSinglebitErrorsMax(12),
        eccSinglebitErrorsMin(13),
        eccSinglebitErrorsRunning(14),
        mismatchErrorsAvg(16),
        mismatchErrorsMax(17),
        mismatchErrorsMin(18),
        mismatchErrorsRunning(19)
    }

CucsMemoryErrorStatsHistThresholded ::= TEXTUAL-CONVENTION
    STATUS        current
    DESCRIPTION
        ""
    SYNTAX        BITS
    {
        addressParityErrors(0),
        addressParityErrorsAvg(1),
        addressParityErrorsMax(2),
        addressParityErrorsMin(3),
        addressParityErrorsRunning(4),
        eccMultibitErrors(5),
        eccMultibitErrorsAvg(6),
        eccMultibitErrorsMax(7),
        eccMultibitErrorsMin(8),
        eccMultibitErrorsRunning(9),
        eccSinglebitErrors(10),
        eccSinglebitErrorsAvg(11),
        eccSinglebitErrorsMax(12),
        eccSinglebitErrorsMin(13),
        eccSinglebitErrorsRunning(14),
        mismatchErrors(15),
        mismatchErrorsAvg(16),
        mismatchErrorsMax(17),
        mismatchErrorsMin(18),
        mismatchErrorsRunning(19)
    }

CucsMemoryFormFactor ::= TEXTUAL-CONVENTION
    STATUS        current
    DESCRIPTION
        ""
    SYNTAX        INTEGER
    {
        undiscovered(0),
        other(1),
        unknown(2),
        simm(3),
        dimm(9),
        tsop(10),
        rimm(12),
        sodimm(13),
        srimm(14),
        fbDimm(15)
    }

CucsMemoryHeartbeatStatus ::= TEXTUAL-CONVENTION
    STATUS        current
    DESCRIPTION
        ""
    SYNTAX        INTEGER
    {
        unknown(0),
        disabled(1),
        running(2),
        timedOut(3)
    }

CucsMemoryIssues ::= TEXTUAL-CONVENTION
    STATUS        current
    DESCRIPTION
        ""
    SYNTAX        BITS
    {
        uncorrectableEccError(0),
        correctableEccError(1),
        addressParityError(2),
        memoryMismatchError(3),
        dramCorrectableCrcError(4),
        dramUncorrectableCrcError(5),
        addressParityErrorCorrectable(6),
        addressParityErrorUncorrectable(7)
    }

CucsMemoryNamespaceMode ::= TEXTUAL-CONVENTION
    STATUS        current
    DESCRIPTION
        ""
    SYNTAX        INTEGER
    {
        raw(0),
        block(1)
    }

CucsMemoryNvDimmId ::= TEXTUAL-CONVENTION
    STATUS        current
    DESCRIPTION
        ""
    SYNTAX        Gauge32 (1..16)

CucsMemoryNvDimmBatteryId ::= TEXTUAL-CONVENTION
    STATUS        current
    DESCRIPTION
        ""
    SYNTAX        Gauge32 (1..8)

CucsMemoryNvDimmEnvStatsThresholded ::= TEXTUAL-CONVENTION
    STATUS        current
    DESCRIPTION
        ""
    SYNTAX        BITS
    {
        temperature(0),
        temperatureAvg(1),
        temperatureMax(2),
        temperatureMin(3),
        voltage(4),
        voltageAvg(5),
        voltageMax(6),
        voltageMin(7)
    }

CucsMemoryNvDimmEnvStatsHistThresholded ::= TEXTUAL-CONVENTION
    STATUS        current
    DESCRIPTION
        ""
    SYNTAX        BITS
    {
        temperature(0),
        temperatureAvg(1),
        temperatureMax(2),
        temperatureMin(3),
        voltage(4),
        voltageAvg(5),
        voltageMax(6),
        voltageMin(7)
    }

CucsMemoryNvDimmHealth ::= TEXTUAL-CONVENTION
    STATUS        current
    DESCRIPTION
        ""
    SYNTAX        INTEGER
    {
        unknown(0),
        notPresent(1),
        healthy(2),
        hardwareFault(3),
        softwareFault(4),
        batteryFault(5)
    }

CucsMemoryOperationStatus ::= TEXTUAL-CONVENTION
    STATUS        current
    DESCRIPTION
        ""
    SYNTAX        INTEGER
    {
        unknown(0),
        idle(1),
        backup(2),
        restore(3),
        erase(4),
        backupFailed(5),
        restoreFailed(6),
        eraseFailed(7)
    }

CucsMemoryPersistentMemoryAdminAction ::= TEXTUAL-CONVENTION
    STATUS        current
    DESCRIPTION
        ""
    SYNTAX        INTEGER
    {
        noOp(0),
        resetFactoryDefault(1),
        enableSecurity(2),
        disableSecurity(3),
        modifyPassphrase(4),
        secureErase(5),
        unlockDimms(6),
        cancelAll(7)
    }

CucsMemoryPersistentMemoryAdminState ::= TEXTUAL-CONVENTION
    STATUS        current
    DESCRIPTION
        ""
    SYNTAX        INTEGER
    {
        init(0),
        configure(1),
        delete(2),
        matching(3),
        notMatching(4),
        forceFlag(128),
        forceConfigure(129),
        forceDelete(130)
    }

CucsMemoryPersistentMemoryPolicyOperation ::= TEXTUAL-CONVENTION
    STATUS        current
    DESCRIPTION
        ""
    SYNTAX        INTEGER
    {
        noOp(0),
        enableSecurity(1),
        disableSecurity(2),
        modifyPassphrase(3),
        failed(4),
        hostManaged(5),
        policyChanged(6)
    }

CucsMemoryPersistentMemoryType ::= TEXTUAL-CONVENTION
    STATUS        current
    DESCRIPTION
        ""
    SYNTAX        INTEGER
    {
        appDirect(0),
        appDirectNonInterleaved(1)
    }

CucsMemoryPersistentMemoryUnitId ::= TEXTUAL-CONVENTION
    STATUS        current
    DESCRIPTION
        ""
    SYNTAX        Gauge32 (1..256)

CucsMemoryRuntimeThresholded ::= TEXTUAL-CONVENTION
    STATUS        current
    DESCRIPTION
        ""
    SYNTAX        BITS
    {
        available(0),
        availableAvg(1),
        availableMax(2),
        availableMin(3),
        cached(4),
        cachedAvg(5),
        cachedMax(6),
        cachedMin(7),
        total(8),
        totalAvg(9),
        totalMax(10),
        totalMin(11)
    }

CucsMemoryRuntimeType ::= TEXTUAL-CONVENTION
    STATUS        current
    DESCRIPTION
        ""
    SYNTAX        INTEGER
    {
        swap(1),
        total(2)
    }

CucsMemoryRuntimeHistThresholded ::= TEXTUAL-CONVENTION
    STATUS        current
    DESCRIPTION
        ""
    SYNTAX        BITS
    {
        available(0),
        availableAvg(1),
        availableMax(2),
        availableMin(3),
        cached(4),
        cachedAvg(5),
        cachedMax(6),
        cachedMin(7),
        total(8),
        totalAvg(9),
        totalMax(10),
        totalMin(11)
    }

CucsMemorySocketId ::= TEXTUAL-CONVENTION
    STATUS        current
    DESCRIPTION
        ""
    SYNTAX        INTEGER
    {
        socket1(1),
        socket2(2),
        socket3(3),
        socket4(4)
    }

CucsMemorySocketLocalDimmNumber ::= TEXTUAL-CONVENTION
    STATUS        current
    DESCRIPTION
        ""
    SYNTAX        INTEGER
    {
        notApplicable(0),
        n2(2),
        n3(3),
        n4(4),
        n6(6),
        n7(7),
        n8(8),
        n10(10),
        n11(11),
        n12(12),
        n14(14),
        n15(15),
        n16(16)
    }

CucsMemoryType ::= TEXTUAL-CONVENTION
    STATUS        current
    DESCRIPTION
        ""
    SYNTAX        INTEGER
    {
        undiscovered(0),
        other(1),
        unknown(2),
        dram(3),
        edram(4),
        vram(5),
        sram(6),
        ram(7),
        rom(8),
        flash(9),
        eeprom(10),
        feprom(11),
        eprom(12),
        cdram(13),
        n3DRAM(14),
        sdram(15),
        sgram(16),
        rdram(17),
        ddr(18),
        ddr2(19),
        ddr2FbDimm(20),
        ddr3(24),
        fbd2(25),
        ddr4(26),
        logicalNonVolatileDevice(27),
        ddr5(34)
    }

CucsMemoryUnitId ::= TEXTUAL-CONVENTION
    STATUS        current
    DESCRIPTION
        ""
    SYNTAX        Gauge32 (1..256)

CucsMemoryUnitOperability ::= TEXTUAL-CONVENTION
    STATUS        current
    DESCRIPTION
        ""
    SYNTAX        INTEGER
    {
        unknown(0),
        operable(1),
        inoperable(2),
        degraded(3),
        poweredOff(4),
        powerProblem(5),
        removed(6),
        voltageProblem(7),
        thermalProblem(8),
        performanceProblem(9),
        accessibilityProblem(10),
        identityUnestablishable(11),
        biosPostTimeout(12),
        disabled(13),
        malformedFru(14),
        backplanePortProblem(15),
        chassisIntrusion(16),
        nonOptimal(17),
        unsupportedConfig(18),
        nonOptimalSevere(20),
        fabricConnProblem(51),
        fabricUnsupportedConn(52),
        config(81),
        equipmentProblem(82),
        decomissioning(83),
        chassisLimitExceeded(84),
        notSupported(100),
        discovery(101),
        discoveryFailed(102),
        identify(103),
        postFailure(104),
        upgradeProblem(105),
        peerCommProblem(106),
        autoUpgrade(107),
        linkActivateBlocked(108)
    }

CucsMemoryUnitEnvStatsThresholded ::= TEXTUAL-CONVENTION
    STATUS        current
    DESCRIPTION
        ""
    SYNTAX        BITS
    {
        temperature(0),
        temperatureAvg(1),
        temperatureMax(2),
        temperatureMin(3)
    }

CucsMemoryUnitEnvStatsHistThresholded ::= TEXTUAL-CONVENTION
    STATUS        current
    DESCRIPTION
        ""
    SYNTAX        BITS
    {
        temperature(0),
        temperatureAvg(1),
        temperatureMax(2),
        temperatureMin(3)
    }

CucsMemoryVisibility ::= TEXTUAL-CONVENTION
    STATUS        current
    DESCRIPTION
        ""
    SYNTAX        INTEGER
    {
        unknown(0),
        yes(1),
        no(2)
    }

CucsMessageSeverity ::= TEXTUAL-CONVENTION
    STATUS        current
    DESCRIPTION
        ""
    SYNTAX        INTEGER
    {
        emergency(0),
        alert(1),
        critical(2),
        error(3),
        warning(4),
        notification(5),
        information(6),
        debugging(7)
    }

CucsMgmtASecureBootAdminState ::= TEXTUAL-CONVENTION
    STATUS        current
    DESCRIPTION
        ""
    SYNTAX        INTEGER
    {
        disable(0),
        enable(1)
    }

CucsMgmtAbsBackupPostAction ::= TEXTUAL-CONVENTION
    STATUS        current
    DESCRIPTION
        ""
    SYNTAX        INTEGER
    {
        none(0),
        remove(1)
    }

CucsMgmtAbsBackupProto ::= TEXTUAL-CONVENTION
    STATUS        current
    DESCRIPTION
        ""
    SYNTAX        INTEGER
    {
        none(0),
        ftp(1),
        tftp(2),
        scp(3),
        http(4),
        sftp(5),
        nfsCopy(6)
    }

CucsMgmtAbsImporterPostAction ::= TEXTUAL-CONVENTION
    STATUS        current
    DESCRIPTION
        ""
    SYNTAX        INTEGER
    {
        none(0),
        remove(1)
    }

CucsMgmtAbsImporterProto ::= TEXTUAL-CONVENTION
    STATUS        current
    DESCRIPTION
        ""
    SYNTAX        INTEGER
    {
        none(0),
        ftp(1),
        tftp(2),
        scp(3),
        http(4),
        sftp(5),
        nfsCopy(6)
    }

CucsMgmtAccess ::= TEXTUAL-CONVENTION
    STATUS        current
    DESCRIPTION
        ""
    SYNTAX        INTEGER
    {
        unspecified(0),
        inBand(1),
        outOfBand(2),
        internal(4),
        virtual(8)
    }

CucsMgmtAdminOperation ::= TEXTUAL-CONVENTION
    STATUS        current
    DESCRIPTION
        ""
    SYNTAX        INTEGER
    {
        none(0),
        clearKvmCert(1),
        cancelAll(2)
    }

CucsMgmtAdminState ::= TEXTUAL-CONVENTION
    STATUS        current
    DESCRIPTION
        ""
    SYNTAX        INTEGER
    {
        disable(0),
        enable(1)
    }

CucsMgmtBackupPostAction ::= TEXTUAL-CONVENTION
    STATUS        current
    DESCRIPTION
        ""
    SYNTAX        INTEGER
    {
        none(0),
        remove(1)
    }

CucsMgmtBackupProto ::= TEXTUAL-CONVENTION
    STATUS        current
    DESCRIPTION
        ""
    SYNTAX        INTEGER
    {
        none(0),
        ftp(1),
        tftp(2),
        scp(3),
        http(4),
        sftp(5),
        nfsCopy(6)
    }

CucsMgmtBackupFsmCurrentFsm ::= TEXTUAL-CONVENTION
    STATUS        current
    DESCRIPTION
        ""
    SYNTAX        INTEGER
    {
        nop(0),
        backup(290)
    }

CucsMgmtBackupFsmStageName ::= TEXTUAL-CONVENTION
    STATUS        current
    DESCRIPTION
        ""
    SYNTAX        INTEGER
    {
        nop(0),
        backupBegin(290),
        backupBackupLocal(291),
        backupUpload(292),
        backupFail(398),
        backupSuccess(399)
    }

CucsMgmtBackupFsmTaskItem ::= TEXTUAL-CONVENTION
    STATUS        current
    DESCRIPTION
        ""
    SYNTAX        INTEGER
    {
        nop(0),
        backup(290)
    }

CucsMgmtBackupInterval ::= TEXTUAL-CONVENTION
    STATUS        current
    DESCRIPTION
        ""
    SYNTAX        INTEGER
    {
        n1day(86400),
        n1week(604800),
        n2week(1209600)
    }

CucsMgmtBackupIssue ::= TEXTUAL-CONVENTION
    STATUS        current
    DESCRIPTION
        ""
    SYNTAX        INTEGER
    {
        none(0),
        outdated(1)
    }

CucsMgmtBackupJob ::= TEXTUAL-CONVENTION
    STATUS        current
    DESCRIPTION
        ""
    SYNTAX        INTEGER
    {
        immediate(2)
    }

CucsMgmtBackupJobStatus ::= TEXTUAL-CONVENTION
    STATUS        current
    DESCRIPTION
        ""
    SYNTAX        INTEGER
    {
        none(0),
        inProgress(1),
        success(2),
        fail(3)
    }

CucsMgmtBackupOperationAdminState ::= TEXTUAL-CONVENTION
    STATUS        current
    DESCRIPTION
        ""
    SYNTAX        INTEGER
    {
        enabled(1),
        disabled(2)
    }

CucsMgmtBackupOperationPostAction ::= TEXTUAL-CONVENTION
    STATUS        current
    DESCRIPTION
        ""
    SYNTAX        INTEGER
    {
        none(0),
        remove(1)
    }

CucsMgmtBackupPolicyFsmCurrentFsm ::= TEXTUAL-CONVENTION
    STATUS        current
    DESCRIPTION
        ""
    SYNTAX        INTEGER
    {
        nop(0),
        reportConfigCopy(1187)
    }

CucsMgmtBackupPolicyFsmStageName ::= TEXTUAL-CONVENTION
    STATUS        current
    DESCRIPTION
        ""
    SYNTAX        INTEGER
    {
        nop(0),
        reportConfigCopyBegin(1187),
        reportConfigCopyReport(1188),
        reportConfigCopyFail(1411),
        reportConfigCopySuccess(1412)
    }

CucsMgmtBackupTriggerFsmCurrentFsm ::= TEXTUAL-CONVENTION
    STATUS        current
    DESCRIPTION
        ""
    SYNTAX        INTEGER
    {
        nop(0),
        trigger(399)
    }

CucsMgmtBackupTriggerFsmStageName ::= TEXTUAL-CONVENTION
    STATUS        current
    DESCRIPTION
        ""
    SYNTAX        INTEGER
    {
        nop(0),
        triggerBegin(399),
        triggerStateDisable(400),
        triggerStateEnable(401),
        triggerFail(402),
        triggerSuccess(403)
    }

CucsMgmtBackupTriggerFsmTaskItem ::= TEXTUAL-CONVENTION
    STATUS        current
    DESCRIPTION
        ""
    SYNTAX        INTEGER
    {
        nop(0),
        trigger(399)
    }

CucsMgmtBackupType ::= TEXTUAL-CONVENTION
    STATUS        current
    DESCRIPTION
        ""
    SYNTAX        INTEGER
    {
        fullState(1),
        configAll(2),
        configSystem(3),
        configLogical(4)
    }

CucsMgmtCapability ::= TEXTUAL-CONVENTION
    STATUS        current
    DESCRIPTION
        ""
    SYNTAX        BITS
    {
        modifyMaintenanceMode(0),
        factoryReset(1),
        localStorage(2),
        usbNic(3)
    }

CucsMgmtCertStatus ::= TEXTUAL-CONVENTION
    STATUS        current
    DESCRIPTION
        ""
    SYNTAX        INTEGER
    {
        none(0),
        unsupported(1),
        emptyParams(2)
    }

CucsMgmtCertType ::= TEXTUAL-CONVENTION
    STATUS        current
    DESCRIPTION
        ""
    SYNTAX        INTEGER
    {
        pem(1)
    }

CucsMgmtCfgExportPolicyFsmCurrentFsm ::= TEXTUAL-CONVENTION
    STATUS        current
    DESCRIPTION
        ""
    SYNTAX        INTEGER
    {
        nop(0),
        reportConfigCopy(1187)
    }

CucsMgmtCfgExportPolicyFsmStageName ::= TEXTUAL-CONVENTION
    STATUS        current
    DESCRIPTION
        ""
    SYNTAX        INTEGER
    {
        nop(0),
        reportConfigCopyBegin(1187),
        reportConfigCopyReport(1188),
        reportConfigCopyFail(1411),
        reportConfigCopySuccess(1412)
    }

CucsMgmtCimcSecureBootAdminState ::= TEXTUAL-CONVENTION
    STATUS        current
    DESCRIPTION
        ""
    SYNTAX        INTEGER
    {
        disable(0),
        enable(1)
    }

CucsMgmtCmcSecureBootOperationAdminState ::= TEXTUAL-CONVENTION
    STATUS        current
    DESCRIPTION
        ""
    SYNTAX        INTEGER
    {
        disable(0),
        enable(1)
    }

CucsMgmtConfigState ::= TEXTUAL-CONVENTION
    STATUS        current
    DESCRIPTION
        ""
    SYNTAX        INTEGER
    {
        incomplete(0),
        unsupportedVlan(1),
        unsupportedServer(2),
        unresolvedVlan(3),
        valid(4),
        invalidPinning(5)
    }

CucsMgmtConnectionState ::= TEXTUAL-CONVENTION
    STATUS        current
    DESCRIPTION
        ""
    SYNTAX        INTEGER
    {
        unInitialized(0),
        acknowledged(1),
        unsupportedConnectivity(2)
    }

CucsMgmtControllerDefaultGatewaySwitchId ::= TEXTUAL-CONVENTION
    STATUS        current
    DESCRIPTION
        ""
    SYNTAX        INTEGER
    {
        none(0),
        a(1),
        b(2)
    }

CucsMgmtControllerHostagCommMethod ::= TEXTUAL-CONVENTION
    STATUS        current
    DESCRIPTION
        ""
    SYNTAX        INTEGER
    {
        unknown(0),
        serial(1),
        usbNic(2)
    }

CucsMgmtControllerFsmCurrentFsm ::= TEXTUAL-CONVENTION
    STATUS        current
    DESCRIPTION
        ""
    SYNTAX        INTEGER
    {
        nop(0),
        extMgmtIfConfig(17),
        updateSwitch(248),
        updateIOM(253),
        activateIOM(256),
        updateBMC(259),
        activateBMC(262),
        updateUCSManager(467),
        sysConfig(474),
        online(1059),
        registryConfig(1191),
        extMgmtInterfaceConfig(1493),
        lockConfig(1686),
        powerBudgetReclaimConfig(1688),
        updateCMC(1845),
        activateCMC(1848),
        updateAdaptor(1852),
        activateAdaptor(1855),
        updateRaidController(1861),
        updateBoardController(1868),
        powerCap(2024),
        enableSecureBoot(2103),
        updateColusaCMC(2108),
        activateColusaCMC(2111),
        updateColusaBoardController(2138),
        updateSasExpander(2146),
        activateSasExpander(2149),
        activateLocalDisk(2153),
        updateUCSManagerSP(2195),
        kvmCert(2307),
        updateStorageServerCMC(2349),
        activateStorageServerCMC(2352),
        upgradeBoardController(2356),
        updateSecureFPGA(2384),
        configureSwPersonalities(2399)
    }

CucsMgmtControllerFsmStageName ::= TEXTUAL-CONVENTION
    STATUS        current
    DESCRIPTION
        ""
    SYNTAX        INTEGER
    {
        nop(0),
        extMgmtIfConfigBegin(17),
        extMgmtIfConfigPrimary(18),
        extMgmtIfConfigSecondary(19),
        updateSwitchBegin(248),
        updateSwitchUpdateLocal(249),
        updateSwitchResetLocal(250),
        updateSwitchUpdateRemote(251),
        updateSwitchResetRemote(252),
        updateIOMBegin(253),
        updateIOMUpdateRequest(254),
        updateIOMPollUpdateStatus(255),
        activateIOMBegin(256),
        activateIOMActivate(257),
        activateIOMReset(258),
        updateBMCBegin(259),
        updateBMCUpdateRequest(260),
        updateBMCPollUpdateStatus(261),
        activateBMCBegin(262),
        activateBMCActivate(263),
        activateBMCReset(264),
        activateBMCFail(400),
        activateBMCSuccess(401),
        activateIOMFail(402),
        activateIOMSuccess(403),
        extMgmtIfConfigFail(404),
        extMgmtIfConfigSuccess(405),
        updateBMCFail(406),
        updateBMCSuccess(407),
        updateIOMFail(408),
        updateIOMSuccess(409),
        updateSwitchFail(412),
        updateSwitchSuccess(413),
        updateUCSManagerBegin(467),
        updateUCSManagerExecute(468),
        updateUCSManagerFail(469),
        updateUCSManagerSuccess(470),
        updateUCSManagerStart(471),
        updateSwitchVerifyLocal(472),
        updateSwitchVerifyRemote(473),
        sysConfigBegin(474),
        sysConfigPrimary(475),
        sysConfigSecondary(476),
        sysConfigFail(477),
        sysConfigSuccess(478),
        onlineBegin(1059),
        onlineBmcConfigureConnLocal(1060),
        onlineSwConfigureConnLocal(1061),
        onlineBmcConfigureConnPeer(1062),
        onlineSwConfigureConnPeer(1063),
        onlineFail(1075),
        onlineSuccess(1076),
        registryConfigBegin(1191),
        registryConfigRemove(1192),
        updateUCSManagerCopyExtToLocal(1357),
        updateUCSManagerCopyExtToPeer(1358),
        updateSwitchCopyToLocal(1359),
        updateSwitchCopyToPeer(1360),
        registryConfigFail(1409),
        registryConfigSuccess(1410),
        extMgmtInterfaceConfigBegin(1493),
        extMgmtInterfaceConfigCIMCVlanCfgLocal(1494),
        extMgmtInterfaceConfigCIMCVlanCfgPeer(1495),
        extMgmtInterfaceConfigCMCVlanCfg(1496),
        extMgmtInterfaceConfigCMCVlanCfgPeer(1497),
        extMgmtInterfaceConfigActive(1498),
        extMgmtInterfaceConfigFail(1556),
        extMgmtInterfaceConfigSuccess(1557),
        updateIOMCopyImgFromRep(1594),
        updateIOMCopyIOMImgToSub(1597),
        lockConfigBegin(1686),
        lockConfigPowerButtonLockConfig(1687),
        powerBudgetReclaimConfigBegin(1688),
        powerBudgetReclaimConfigPowerOffWait(1689),
        powerBudgetReclaimConfigPowerOffReclaim(1690),
        lockConfigFail(1825),
        lockConfigSuccess(1826),
        powerBudgetReclaimConfigFail(1827),
        powerBudgetReclaimConfigSuccess(1828),
        updateCMCBegin(1845),
        updateCMCUpdateRequest(1846),
        updateCMCPollUpdateStatus(1847),
        activateCMCBegin(1848),
        activateCMCActivate(1849),
        activateCMCReset(1850),
        activateCMCPollActivation(1851),
        updateAdaptorBegin(1852),
        updateAdaptorUpdateRequest(1853),
        updateAdaptorPollUpdateStatus(1854),
        activateAdaptorBegin(1855),
        activateAdaptorActivate(1856),
        activateAdaptorPowerOffServers(1857),
        activateAdaptorServersPowerOffCompletion(1858),
        activateAdaptorReset(1859),
        activateAdaptorPollActivateStatus(1860),
        updateRaidControllerBegin(1861),
        updateRaidControllerUpdateRequest(1862),
        updateRaidControllerPollUpdateStatus(1863),
        updateRaidControllerPowerOffServers(1864),
        updateRaidControllerServersPowerOffCompletion(1865),
        updateRaidControllerActivate(1866),
        updateRaidControllerPollActivation(1867),
        updateBoardControllerBegin(1868),
        updateBoardControllerPrepareForUpdate(1869),
        updateBoardControllerPowerOffServers(1870),
        updateBoardControllerServersPowerOffCompletion(1871),
        updateBoardControllerUpdateRequest(1872),
        updateBoardControllerPollUpdateStatus(1873),
        activateAdaptorFail(1921),
        activateAdaptorSuccess(1922),
        activateCMCFail(1923),
        activateCMCSuccess(1924),
        updateAdaptorFail(1925),
        updateAdaptorSuccess(1926),
        updateBoardControllerFail(1927),
        updateBoardControllerSuccess(1928),
        updateCMCFail(1929),
        updateCMCSuccess(1930),
        updateRaidControllerFail(1931),
        updateRaidControllerSuccess(1932),
        powerCapBegin(2024),
        powerCapConfig(2025),
        extMgmtInterfaceConfigStandbyCMCVlanCfg(2028),
        enableSecureBootBegin(2103),
        enableSecureBootUpdateRequest(2104),
        enableSecureBootPollUpdateStatus(2105),
        enableSecureBootReset(2106),
        enableSecureBootPollSecureBootStatus(2107),
        updateColusaCMCBegin(2108),
        updateColusaCMCUpdateRequest(2109),
        updateColusaCMCPollUpdateStatus(2110),
        activateColusaCMCBegin(2111),
        activateColusaCMCActivate(2112),
        activateColusaCMCReset(2113),
        activateColusaCMCPollActivation(2114),
        updateAdaptorUpdateRequestPeer(2134),
        activateAdaptorActivatePeer(2135),
        activateAdaptorPowerOnServers(2136),
        updateRaidControllerPowerOnServers(2137),
        updateColusaBoardControllerBegin(2138),
        updateColusaBoardControllerPrepareForUpdate(2139),
        updateColusaBoardControllerPowerOffServers(2140),
        updateColusaBoardControllerServersPowerOffCompletion(2141),
        updateColusaBoardControllerUpdateRequest(2142),
        updateColusaBoardControllerPollUpdateStatus(2143),
        updateColusaBoardControllerPowerOnServers(2144),
        updateBoardControllerPowerOnServers(2145),
        updateSasExpanderBegin(2146),
        updateSasExpanderUpdateRequest(2147),
        updateSasExpanderPollUpdateStatus(2148),
        activateSasExpanderBegin(2149),
        activateSasExpanderActivate(2150),
        activateSasExpanderWaitForActivation(2151),
        activateSasExpanderPollActivateStatus(2152),
        activateLocalDiskBegin(2153),
        activateLocalDiskActivate(2154),
        activateLocalDiskPollActivateStatus(2155),
        activateColusaCMCFail(2175),
        activateColusaCMCSuccess(2176),
        activateLocalDiskFail(2177),
        activateLocalDiskSuccess(2178),
        activateSasExpanderFail(2179),
        activateSasExpanderSuccess(2180),
        enableSecureBootFail(2181),
        enableSecureBootSuccess(2182),
        powerCapFail(2183),
        powerCapSuccess(2184),
        updateColusaBoardControllerFail(2185),
        updateColusaBoardControllerSuccess(2186),
        updateColusaCMCFail(2187),
        updateColusaCMCSuccess(2188),
        updateSasExpanderFail(2189),
        updateSasExpanderSuccess(2190),
        updateUCSManagerSPBegin(2195),
        updateUCSManagerSPStart(2196),
        updateUCSManagerSPExecute(2197),
        updateSwitchUpdateSpLocal(2198),
        updateSwitchUpdateSpRemote(2199),
        updateUCSManagerSPFail(2261),
        updateUCSManagerSPSuccess(2262),
        registryConfigRemovePeer(2269),
        kvmCertBegin(2307),
        kvmCertConfig(2308),
        kvmCertResetCimc(2309),
        kvmCertFail(2314),
        kvmCertSuccess(2315),
        updateStorageServerCMCBegin(2349),
        updateStorageServerCMCUpdateRequest(2350),
        updateStorageServerCMCPollUpdateStatus(2351),
        activateStorageServerCMCBegin(2352),
        activateStorageServerCMCActivate(2353),
        activateStorageServerCMCReset(2354),
        activateStorageServerCMCPollActivation(2355),
        upgradeBoardControllerBegin(2356),
        upgradeBoardControllerPrepareForUpdate(2357),
        upgradeBoardControllerPowerOffServers(2358),
        upgradeBoardControllerServersPowerOffCompletion(2359),
        upgradeBoardControllerUpdateRequest(2360),
        upgradeBoardControllerPollUpdateStatus(2361),
        upgradeBoardControllerPowerOnServers(2362),
        activateStorageServerCMCFail(2369),
        activateStorageServerCMCSuccess(2370),
        updateStorageServerCMCFail(2371),
        updateStorageServerCMCSuccess(2372),
        upgradeBoardControllerFail(2373),
        upgradeBoardControllerSuccess(2374),
        updateSecureFPGABegin(2384),
        updateSecureFPGAActivateLocal(2385),
        updateSecureFPGAActivateRemote(2386),
        updateSecureFPGAPollActivate(2387),
        updateSecureFPGAFail(2395),
        updateSecureFPGASuccess(2396),
        configureSwPersonalitiesBegin(2399),
        configureSwPersonalitiesExecute(2400),
        configureSwPersonalitiesFail(2405),
        configureSwPersonalitiesSuccess(2406),
        extMgmtIfConfigConfigGateway(2444)
    }

CucsMgmtControllerFsmTaskFlags ::= TEXTUAL-CONVENTION
    STATUS        current
    DESCRIPTION
        ""
    SYNTAX        BITS
    {
        samDmeMgmtControllerActivateAdaptorAdaptorFwReset(0),
        samDmeMgmtControllerUpgradeBoardControllerPowerOnServers(1),
        samDmeMgmtControllerUpdateRaidControllerLsiFwUpdate(2),
        samDmeMgmtControllerUpdateRaidControllerLsiFwReset(3),
        samDmeMgmtControllerUpgradeBoardControllerPldFwUpdate(4),
        samDmeMgmtControllerUpdateSwitchInstall(6),
        samDmeMgmtControllerUpdateSwitchUninstall(7),
        samDmeMgmtControllerUpdateSwitchResetsp(8),
        samDmeMgmtControllerUpdateSwitchActivate(14),
        samDmeMgmtControllerUpdateSwitchReset(15),
        samDmeMgmtControllerUpgradeBoardControllerPowerDownServers(62)
    }

CucsMgmtControllerFsmTaskItem ::= TEXTUAL-CONVENTION
    STATUS        current
    DESCRIPTION
        ""
    SYNTAX        INTEGER
    {
        nop(0),
        extMgmtIfConfig(17),
        updateSwitch(248),
        updateIOM(253),
        activateIOM(256),
        updateBMC(259),
        activateBMC(262),
        updateUCSManager(467),
        sysConfig(474),
        online(1059),
        registryConfig(1191),
        extMgmtInterfaceConfig(1493),
        lockConfig(1686),
        powerBudgetReclaimConfig(1688),
        updateCMC(1845),
        activateCMC(1848),
        updateAdaptor(1852),
        activateAdaptor(1855),
        updateRaidController(1861),
        updateBoardController(1868),
        powerCap(2024),
        enableSecureBoot(2103),
        updateColusaCMC(2108),
        activateColusaCMC(2111),
        updateColusaBoardController(2138),
        updateSasExpander(2146),
        activateSasExpander(2149),
        activateLocalDisk(2153),
        updateUCSManagerSP(2195),
        kvmCert(2307),
        updateStorageServerCMC(2349),
        activateStorageServerCMC(2352),
        upgradeBoardController(2356),
        updateSecureFPGA(2384),
        configureSwPersonalities(2399)
    }

CucsMgmtDataExporterType ::= TEXTUAL-CONVENTION
    STATUS        current
    DESCRIPTION
        ""
    SYNTAX        INTEGER
    {
        fullState(1),
        configAll(2),
        configSystem(3),
        configLogical(4)
    }

CucsMgmtDataExporterFsmCurrentFsm ::= TEXTUAL-CONVENTION
    STATUS        current
    DESCRIPTION
        ""
    SYNTAX        INTEGER
    {
        nop(0),
        exportData(24)
    }

CucsMgmtDataExporterFsmStageName ::= TEXTUAL-CONVENTION
    STATUS        current
    DESCRIPTION
        ""
    SYNTAX        INTEGER
    {
        nop(0),
        exportDataBegin(24),
        exportDataDmeDataExport(25),
        exportDataUpload(26),
        exportDataFail(111),
        exportDataSuccess(112)
    }

CucsMgmtDataExporterFsmTaskItem ::= TEXTUAL-CONVENTION
    STATUS        current
    DESCRIPTION
        ""
    SYNTAX        INTEGER
    {
        nop(0),
        exportData(24)
    }

CucsMgmtDataImporterFsmCurrentFsm ::= TEXTUAL-CONVENTION
    STATUS        current
    DESCRIPTION
        ""
    SYNTAX        INTEGER
    {
        nop(0),
        importData(27)
    }

CucsMgmtDataImporterFsmStageName ::= TEXTUAL-CONVENTION
    STATUS        current
    DESCRIPTION
        ""
    SYNTAX        INTEGER
    {
        nop(0),
        importDataBegin(27),
        importDataDownload(28),
        importDataDmeImport(29),
        importDataReportResults(30),
        importDataFail(113),
        importDataSuccess(114)
    }

CucsMgmtDataImporterFsmTaskItem ::= TEXTUAL-CONVENTION
    STATUS        current
    DESCRIPTION
        ""
    SYNTAX        INTEGER
    {
        nop(0),
        importData(27)
    }

CucsMgmtDimmBlacklistingOperState ::= TEXTUAL-CONVENTION
    STATUS        current
    DESCRIPTION
        ""
    SYNTAX        INTEGER
    {
        unknown(0),
        enabled(1),
        disabled(2),
        unsupported(3)
    }

CucsMgmtDiskZoningState ::= TEXTUAL-CONVENTION
    STATUS        current
    DESCRIPTION
        ""
    SYNTAX        INTEGER
    {
        unknown(0),
        processing(1),
        deployed(2),
        inventoryStart(3),
        inventoryEnd(4),
        failed(5)
    }

CucsMgmtEntityChassisDeviceIoState1 ::= TEXTUAL-CONVENTION
    STATUS        current
    DESCRIPTION
        ""
    SYNTAX        INTEGER
    {
        unknown(0),
        ok(1),
        openError(2),
        readError(3),
        writeError(4)
    }

CucsMgmtEntityChassisDeviceIoState2 ::= TEXTUAL-CONVENTION
    STATUS        current
    DESCRIPTION
        ""
    SYNTAX        INTEGER
    {
        unknown(0),
        ok(1),
        openError(2),
        readError(3),
        writeError(4)
    }

CucsMgmtEntityChassisDeviceIoState3 ::= TEXTUAL-CONVENTION
    STATUS        current
    DESCRIPTION
        ""
    SYNTAX        INTEGER
    {
        unknown(0),
        ok(1),
        openError(2),
        readError(3),
        writeError(4)
    }

CucsMgmtEntityHaFailureReason ::= TEXTUAL-CONVENTION
    STATUS        current
    DESCRIPTION
        ""
    SYNTAX        INTEGER
    {
        none(0),
        nodeDown(1),
        peerNodeDown(2),
        mgmtServicesUnresponsive(3),
        peerMgmtServicesUnresponsive(4),
        chassisConfigIncomplete(5),
        peerChassisConfigIncomplete(6),
        networkInterfaceDown(7),
        dbVersionMismatch(8)
    }

CucsMgmtEntityHaReadiness ::= TEXTUAL-CONVENTION
    STATUS        current
    DESCRIPTION
        ""
    SYNTAX        INTEGER
    {
        unknown(0),
        ready(1),
        downgraded(2),
        notReady(3)
    }

CucsMgmtEntityLeadIdForAutoInstall ::= TEXTUAL-CONVENTION
    STATUS        current
    DESCRIPTION
        ""
    SYNTAX        INTEGER
    {
        none(0),
        a(1),
        b(2),
        mgmt(3)
    }

CucsMgmtEntityLeadership ::= TEXTUAL-CONVENTION
    STATUS        current
    DESCRIPTION
        ""
    SYNTAX        INTEGER
    {
        unknown(0),
        primary(1),
        subordinate(2),
        inapplicable(3),
        electionInProgress(4),
        electionFailed(5)
    }

CucsMgmtEntityMgmtServicesState ::= TEXTUAL-CONVENTION
    STATUS        current
    DESCRIPTION
        ""
    SYNTAX        INTEGER
    {
        unknown(0),
        up(1),
        unresponsive(2),
        down(3),
        switchoverInProgress(4)
    }

CucsMgmtEntityProblems ::= TEXTUAL-CONVENTION
    STATUS        current
    DESCRIPTION
        ""
    SYNTAX        BITS
    {
        leadership(0),
        membership(1),
        umbilical(2),
        haReady(3),
        versionMismatch(4)
    }

CucsMgmtEntityState ::= TEXTUAL-CONVENTION
    STATUS        current
    DESCRIPTION
        ""
    SYNTAX        INTEGER
    {
        unknown(0),
        up(1),
        down(2)
    }

CucsMgmtEntityUmbilicalState ::= TEXTUAL-CONVENTION
    STATUS        current
    DESCRIPTION
        ""
    SYNTAX        INTEGER
    {
        unknown(0),
        degraded(1),
        full(2),
        failed(3)
    }

CucsMgmtExportPolicyAdminState ::= TEXTUAL-CONVENTION
    STATUS        current
    DESCRIPTION
        ""
    SYNTAX        INTEGER
    {
        disable(0),
        enable(1)
    }

CucsMgmtExportPolicyProto ::= TEXTUAL-CONVENTION
    STATUS        current
    DESCRIPTION
        ""
    SYNTAX        INTEGER
    {
        none(0),
        ftp(1),
        tftp(2),
        scp(3),
        http(4),
        sftp(5),
        nfsCopy(6)
    }

CucsMgmtExportPolicyFsmCurrentFsm ::= TEXTUAL-CONVENTION
    STATUS        current
    DESCRIPTION
        ""
    SYNTAX        INTEGER
    {
        nop(0),
        reportConfigCopy(1187)
    }

CucsMgmtExportPolicyFsmStageName ::= TEXTUAL-CONVENTION
    STATUS        current
    DESCRIPTION
        ""
    SYNTAX        INTEGER
    {
        nop(0),
        reportConfigCopyBegin(1187),
        reportConfigCopyReport(1188),
        reportConfigCopyFail(1411),
        reportConfigCopySuccess(1412)
    }

CucsMgmtExportPolicyFsmTaskItem ::= TEXTUAL-CONVENTION
    STATUS        current
    DESCRIPTION
        ""
    SYNTAX        INTEGER
    {
        nop(0),
        reportConfigCopy(1187)
    }

CucsMgmtFaultLevel ::= TEXTUAL-CONVENTION
    STATUS        current
    DESCRIPTION
        ""
    SYNTAX        INTEGER
    {
        disabled(0),
        partial(1),
        full(2)
    }

CucsMgmtFileTransferProtocol ::= TEXTUAL-CONVENTION
    STATUS        current
    DESCRIPTION
        ""
    SYNTAX        INTEGER
    {
        none(0),
        ftp(1),
        tftp(2),
        scp(3),
        http(4),
        sftp(5),
        nfsCopy(6)
    }

CucsMgmtIPv6IfAddrFsmCurrentFsm ::= TEXTUAL-CONVENTION
    STATUS        current
    DESCRIPTION
        ""
    SYNTAX        INTEGER
    {
        nop(0),
        swMgmtOobIpv6IfConfig(1535)
    }

CucsMgmtIPv6IfAddrFsmStageName ::= TEXTUAL-CONVENTION
    STATUS        current
    DESCRIPTION
        ""
    SYNTAX        INTEGER
    {
        nop(0),
        swMgmtOobIpv6IfConfigBegin(1535),
        swMgmtOobIpv6IfConfigSwitch(1536),
        swMgmtOobIpv6IfConfigFail(1558),
        swMgmtOobIpv6IfConfigSuccess(1559)
    }

CucsMgmtIPv6IfAddrFsmTaskItem ::= TEXTUAL-CONVENTION
    STATUS        current
    DESCRIPTION
        ""
    SYNTAX        INTEGER
    {
        nop(0),
        swMgmtOobIpv6IfConfig(1535)
    }

CucsMgmtIfFsmCurrentFsm ::= TEXTUAL-CONVENTION
    STATUS        current
    DESCRIPTION
        ""
    SYNTAX        INTEGER
    {
        nop(0),
        swMgmtOobIfConfig(277),
        swMgmtInbandIfConfig(279),
        virtualIfConfig(281),
        enableVip(284),
        disableVip(286),
        enableHA(288),
        faPresence(1907),
        faConn(1910)
    }

CucsMgmtIfFsmStageName ::= TEXTUAL-CONVENTION
    STATUS        current
    DESCRIPTION
        ""
    SYNTAX        INTEGER
    {
        nop(0),
        swMgmtOobIfConfigBegin(277),
        swMgmtOobIfConfigSwitch(278),
        swMgmtInbandIfConfigBegin(279),
        swMgmtInbandIfConfigSwitch(280),
        virtualIfConfigBegin(281),
        virtualIfConfigLocal(282),
        virtualIfConfigRemote(283),
        enableVipBegin(284),
        enableVipLocal(285),
        disableVipBegin(286),
        disableVipPeer(287),
        enableHABegin(288),
        enableHALocal(289),
        disableVipLocal(290),
        disableVipFail(414),
        disableVipSuccess(415),
        enableHAFail(416),
        enableHASuccess(417),
        enableVipFail(418),
        enableVipSuccess(419),
        swMgmtInbandIfConfigFail(420),
        swMgmtInbandIfConfigSuccess(421),
        swMgmtOobIfConfigFail(422),
        swMgmtOobIfConfigSuccess(423),
        virtualIfConfigFail(424),
        virtualIfConfigSuccess(425),
        faPresenceBegin(1907),
        faPresenceCheckLicense(1908),
        faPresenceIdentify(1909),
        faConnBegin(1910),
        faConnConfigureVifNs(1911),
        faConnSharedIOModuleInventory(1912),
        faConnDiscoverChassis(1913),
        faConnOobStorageInventory(1914),
        faConnFail(1933),
        faConnSuccess(1934),
        faPresenceFail(1935),
        faPresenceSuccess(1936),
        faConnDiscoverSasExpander(1974)
    }

CucsMgmtIfFsmTaskItem ::= TEXTUAL-CONVENTION
    STATUS        current
    DESCRIPTION
        ""
    SYNTAX        INTEGER
    {
        nop(0),
        swMgmtOobIfConfig(277),
        swMgmtInbandIfConfig(279),
        virtualIfConfig(281),
        enableVip(284),
        disableVip(286),
        enableHA(288),
        faPresence(1907),
        faConn(1910)
    }

CucsMgmtImportAction ::= TEXTUAL-CONVENTION
    STATUS        current
    DESCRIPTION
        ""
    SYNTAX        INTEGER
    {
        merge(0),
        replace(1)
    }

CucsMgmtImportStatus ::= TEXTUAL-CONVENTION
    STATUS        current
    DESCRIPTION
        ""
    SYNTAX        BITS
    {
        downloadSuccess(0),
        configSuccess(1),
        verifyKeySucceeded(2)
    }

CucsMgmtImporterPostAction ::= TEXTUAL-CONVENTION
    STATUS        current
    DESCRIPTION
        ""
    SYNTAX        INTEGER
    {
        none(0),
        remove(1)
    }

CucsMgmtImporterProto ::= TEXTUAL-CONVENTION
    STATUS        current
    DESCRIPTION
        ""
    SYNTAX        INTEGER
    {
        none(0),
        ftp(1),
        tftp(2),
        scp(3),
        http(4),
        sftp(5),
        nfsCopy(6)
    }

CucsMgmtImporterFsmCurrentFsm ::= TEXTUAL-CONVENTION
    STATUS        current
    DESCRIPTION
        ""
    SYNTAX        INTEGER
    {
        nop(0),
        import(293),
        reportConfigImport(1189)
    }

CucsMgmtImporterFsmStageName ::= TEXTUAL-CONVENTION
    STATUS        current
    DESCRIPTION
        ""
    SYNTAX        INTEGER
    {
        nop(0),
        importBegin(293),
        importDownloadLocal(294),
        importFail(426),
        importSuccess(427),
        importConfig(580),
        importReportResults(626),
        reportConfigImportBegin(1189),
        reportConfigImportReport(1190),
        reportConfigImportFail(1413),
        reportConfigImportSuccess(1414),
        importVerifyKey(2441)
    }

CucsMgmtImporterFsmTaskItem ::= TEXTUAL-CONVENTION
    STATUS        current
    DESCRIPTION
        ""
    SYNTAX        INTEGER
    {
        nop(0),
        import(293),
        reportConfigImport(1189)
    }

CucsMgmtIntAuthPolicyMethod ::= TEXTUAL-CONVENTION
    STATUS        current
    DESCRIPTION
        ""
    SYNTAX        INTEGER
    {
        none(0),
        password(1)
    }

CucsMgmtLeaderEntityLeadership ::= TEXTUAL-CONVENTION
    STATUS        current
    DESCRIPTION
        ""
    SYNTAX        INTEGER
    {
        unknown(0),
        primary(1)
    }

CucsMgmtMaintMode ::= TEXTUAL-CONVENTION
    STATUS        current
    DESCRIPTION
        ""
    SYNTAX        INTEGER
    {
        normal(1),
        lpcReset(2)
    }

CucsMgmtMgmtAdminState ::= TEXTUAL-CONVENTION
    STATUS        current
    DESCRIPTION
        ""
    SYNTAX        INTEGER
    {
        enabled(1),
        disabled(2)
    }

CucsMgmtMode ::= TEXTUAL-CONVENTION
    STATUS        current
    DESCRIPTION
        ""
    SYNTAX        INTEGER
    {
        inBand(0)
    }

CucsMgmtOperState ::= TEXTUAL-CONVENTION
    STATUS        current
    DESCRIPTION
        ""
    SYNTAX        INTEGER
    {
        unknown(0),
        notDeployed(1),
        up(2),
        down(3)
    }

CucsMgmtOperationStatus ::= TEXTUAL-CONVENTION
    STATUS        current
    DESCRIPTION
        ""
    SYNTAX        INTEGER
    {
        notStarted(1),
        workInProgress(2),
        allSuccess(3),
        partialFailed(4),
        failed(5),
        domainSuspended(6)
    }

CucsMgmtPmonEntryState ::= TEXTUAL-CONVENTION
    STATUS        current
    DESCRIPTION
        ""
    SYNTAX        INTEGER
    {
        unknown(0),
        idle(1),
        running(2),
        pending(3),
        failed(4),
        error(5),
        exitPending(6),
        terminated(7),
        killed(8)
    }

CucsMgmtRegistryInfoFsmCurrentFsm ::= TEXTUAL-CONVENTION
    STATUS        current
    DESCRIPTION
        ""
    SYNTAX        INTEGER
    {
        nop(0),
        configure(3)
    }

CucsMgmtRegistryInfoFsmStageName ::= TEXTUAL-CONVENTION
    STATUS        current
    DESCRIPTION
        ""
    SYNTAX        INTEGER
    {
        nop(0),
        configureBegin(3),
        configureConfig(4),
        configureFail(117),
        configureSuccess(118)
    }

CucsMgmtRegistryInfoFsmTaskItem ::= TEXTUAL-CONVENTION
    STATUS        current
    DESCRIPTION
        ""
    SYNTAX        INTEGER
    {
        nop(0),
        configure(3)
    }

CucsMgmtRemoteBackupOperType ::= TEXTUAL-CONVENTION
    STATUS        current
    DESCRIPTION
        ""
    SYNTAX        INTEGER
    {
        backupNone(0),
        backupDelete(1)
    }

CucsMgmtRemoteBackupType ::= TEXTUAL-CONVENTION
    STATUS        current
    DESCRIPTION
        ""
    SYNTAX        INTEGER
    {
        fullState(1),
        configAll(2),
        configSystem(3),
        configLogical(4)
    }

CucsMgmtRemoteKmipAdminTrigger ::= TEXTUAL-CONVENTION
    STATUS        current
    DESCRIPTION
        ""
    SYNTAX        INTEGER
    {
        remoteTrigger(0),
        configCaCert(1)
    }

CucsMgmtSchedStatus ::= TEXTUAL-CONVENTION
    STATUS        current
    DESCRIPTION
        ""
    SYNTAX        INTEGER
    {
        unknown(0),
        notFound(1)
    }

CucsMgmtSecureBootOperState ::= TEXTUAL-CONVENTION
    STATUS        current
    DESCRIPTION
        ""
    SYNTAX        INTEGER
    {
        disabled(0),
        enabled(1),
        unsupported(2),
        enabling(3)
    }

CucsMgmtSource ::= TEXTUAL-CONVENTION
    STATUS        current
    DESCRIPTION
        ""
    SYNTAX        INTEGER
    {
        unspecified(0),
        sharedLom(1),
        sideband(2)
    }

CucsMgmtState ::= TEXTUAL-CONVENTION
    STATUS        current
    DESCRIPTION
        ""
    SYNTAX        INTEGER
    {
        ok(0),
        outOfSync(1)
    }

CucsMgmtStateQual ::= TEXTUAL-CONVENTION
    STATUS        current
    DESCRIPTION
        ""
    SYNTAX        INTEGER
    {
        unspecified(0),
        valid(1),
        misconnected(2)
    }

CucsMgmtStorageSubsystemState ::= TEXTUAL-CONVENTION
    STATUS        current
    DESCRIPTION
        ""
    SYNTAX        INTEGER
    {
        unknown(0),
        uninitialized(1),
        initializing(2),
        initialized(3),
        unsupported(4),
        pendingReset(5)
    }

CucsMgmtSubject ::= TEXTUAL-CONVENTION
    STATUS        current
    DESCRIPTION
        ""
    SYNTAX        INTEGER
    {
        unknown(0),
        blade(1),
        chassis(2),
        system(4),
        switch(8),
        adaptor(16),
        iocard(32),
        cmc(33),
        boardController(64),
        serverUnit(128),
        localDisk(1024),
        retimer(2048),
        ubm(4096),
        cpld(8192),
        intelAmc(16384)
    }

CucsMgmtUpgradeStatus ::= TEXTUAL-CONVENTION
    STATUS        current
    DESCRIPTION
        ""
    SYNTAX        BITS
    {
        hwChangeDetected(0),
        fwChangeDetected(1),
        hwIncompatible(2),
        fwIncompatible(3),
        unsupportedHwVersion(4),
        unsupportedFwVersion(5),
        hwChangeSuccess(6),
        fwChangeSuccess(7)
    }

CucsMgmtUsbnicConnSide ::= TEXTUAL-CONVENTION
    STATUS        current
    DESCRIPTION
        ""
    SYNTAX        INTEGER
    {
        unspecified(0),
        hostSide(1),
        fiSide(2)
    }

CucsMoAnnotationOperState ::= TEXTUAL-CONVENTION
    STATUS        current
    DESCRIPTION
        ""
    SYNTAX        INTEGER
    {
        ok(0),
        notSupported(1),
        configFailure(2)
    }

CucsMoAnnotationOverride ::= TEXTUAL-CONVENTION
    STATUS        current
    DESCRIPTION
        ""
    SYNTAX        INTEGER
    {
        disabled(0),
        enabled(1)
    }

CucsMoAnnotationOwner ::= TEXTUAL-CONVENTION
    STATUS        current
    DESCRIPTION
        ""
    SYNTAX        INTEGER
    {
        mgmt(0),
        inventory(1)
    }

CucsMoAnnotationTarget ::= TEXTUAL-CONVENTION
    STATUS        current
    DESCRIPTION
        ""
    SYNTAX        BITS
    {
        host(0),
        mgmt(1)
    }

CucsMoAnnotationType ::= TEXTUAL-CONVENTION
    STATUS        current
    DESCRIPTION
        ""
    SYNTAX        INTEGER
    {
        keyValue(0),
        ipv4Addr(1),
        ipv6Addr(2),
        vlan(3),
        vnic(4)
    }

CucsMoFileTxAdminState ::= TEXTUAL-CONVENTION
    STATUS        current
    DESCRIPTION
        ""
    SYNTAX        INTEGER
    {
        disabled(0),
        enabled(1)
    }

CucsMoIpV4AddrKvType ::= TEXTUAL-CONVENTION
    STATUS        current
    DESCRIPTION
        ""
    SYNTAX        INTEGER
    {
        keyValue(0),
        ipv4Addr(1),
        ipv6Addr(2),
        vlan(3),
        vnic(4)
    }

CucsMoIpV6AddrKvType ::= TEXTUAL-CONVENTION
    STATUS        current
    DESCRIPTION
        ""
    SYNTAX        INTEGER
    {
        keyValue(0),
        ipv4Addr(1),
        ipv6Addr(2),
        vlan(3),
        vnic(4)
    }

CucsMoKvType ::= TEXTUAL-CONVENTION
    STATUS        current
    DESCRIPTION
        ""
    SYNTAX        INTEGER
    {
        keyValue(0),
        ipv4Addr(1),
        ipv6Addr(2),
        vlan(3),
        vnic(4)
    }

CucsMoMoClassId ::= TEXTUAL-CONVENTION
    STATUS        current
    DESCRIPTION
        ""
    SYNTAX        INTEGER
    {
        unspecified(0),
        moTopProps(1),
        topRoot(2),
        topSystem(3),
        fsmTask(4),
        namingNamedObject(5),
        namingNamedIdentifiedObject(6),
        conditionInfo(7),
        namingObject(8),
        namingDefinition(9),
        namingHolder(10),
        namingBinding(11),
        conditionPolicy(12),
        conditionLog(13),
        policyTracker(14),
        policyTracked(15),
        aaaUserAction(16),
        aaaModLR(17),
        aaaSessionLR(18),
        eventEpCtrl(19),
        eventLog(20),
        eventRecord(21),
        eventHolder(22),
        eventInst(23),
        eventPolicy(24),
        faultHolder(25),
        faultInst(26),
        faultPolicy(27),
        statsItem(28),
        statsCurr(29),
        statsHist(30),
        statsHolder(31),
        statsCollectionPolicy(32),
        statsThresholdPolicy(33),
        statsThresholdClass(34),
        statsThresholdDefinition(35),
        statsThr32Definition(36),
        statsThr64Definition(37),
        statsThrFloatDefinition(38),
        statsThresholdValue(39),
        statsThr32Value(40),
        statsThr64Value(41),
        statsThrFloatValue(42),
        equipmentPOSTCodeReporter(43),
        equipmentPOSTCodeData(44),
        equipmentPOSTCode(45),
        equipmentPOST(46),
        swatInjection(47),
        swatTrigger(48),
        swatCondition(49),
        swatTarget(50),
        swatAction(51),
        swatResultstats(52),
        apeControllerManager(53),
        apeControllerChassis(54),
        apeControllerEeprom(55),
        apeNicAgManager(56),
        apeAdapter(57),
        apeMenlo(58),
        apePalo(59),
        apeAdapterVnic(60),
        apeMenloVnic(61),
        apeMenloVnicStats(62),
        apeManager(63),
        apeMc(64),
        apeMcTable(65),
        apeFru(66),
        apeSdr(67),
        apeReading(68),
        apeParam(69),
        apeBootMethod(70),
        firmwareStoragePack(71),
        apeSANBoot(72),
        apeLocalDiskBoot(73),
        apeVirtualMediaBoot(74),
        apeHostAgent(75),
        clitestTypeTest(76),
        clitestTypeTestParent(77),
        clitestTypeTestChild(78),
        clitestTypeTest2(79),
        fabricInternalDceSrv(80),
        fabricDceSrv(81),
        mgmtAbsDataItem(82),
        mgmtDataItem(83),
        mgmtImportItem(84),
        fabricDceSwSrvEp(85),
        fabricSan(86),
        fabricFcSan(87),
        mgmtEp(88),
        mgmtSvc(89),
        fabricFcSanEp(90),
        fabricFcSanPcEp(91),
        fabricSanPc(92),
        fabricFcSanPc(93),
        fabricFcVsanPortEp(94),
        fabricSanPinGroup(95),
        fabricSanPinTarget(96),
        fabricEp(97),
        fabricCloud(98),
        testingServiceProfile(99),
        testingSnmpPolicy(100),
        testingCliPolicy(101),
        testingSnmpSupport(102),
        testingSnmpCommunity(103),
        testingSnmpTrap(104),
        fabricExternalEp(105),
        fabricInternalEp(106),
        fabricCIoEp(107),
        fabricExternalPc(108),
        fabricInternalPc(109),
        fabricPinGroup(110),
        fabricPinTarget(111),
        fabricLan(112),
        fabricEthLan(113),
        licenseLicense(114),
        fabricAEthLanEp(115),
        fabricEthLanEp(116),
        fabricEthLanPcEp(117),
        fabricLanPc(118),
        fabricEthLanPc(119),
        fabricLanPinGroup(120),
        fabricLanPinTarget(121),
        fabricLocale(122),
        fabricPath(123),
        orgAOrg(124),
        fabricPathConn(125),
        fabricVnetEp(126),
        networkCACert(127),
        networkSystemCACert(128),
        fabricAVsan(129),
        fabricEpVsan(130),
        fabricVsan(131),
        fabricVsanEp(132),
        fabricVlan(133),
        fabricSwChEp(134),
        fabricSwChPhEp(135),
        fabricComputeEp(136),
        fabricChassisEp(137),
        fabricComputeSlotEp(138),
        fabricIf(139),
        fabricComputePhEp(140),
        fabricLastAckedSlot(141),
        processorUnit(142),
        trigServerToken(143),
        trigTokenRequestor(144),
        processorThread(145),
        processorRuntime(146),
        processorRuntimeHist(147),
        processorQual(148),
        fcPIo(149),
        fcConfig(150),
        fcIfConfig(151),
        fcSwIfConfig(152),
        fcNicIfConfig(153),
        fcStats(154),
        fcStatsHist(155),
        fcErrStats(156),
        fcErrStatsHist(157),
        poolAsnmt(158),
        vnicTempl(159),
        vnicSanConnTempl(160),
        vnicLanConnTempl(161),
        vnicL3If(162),
        vnicIPIf(163),
        vnicIPv4If(164),
        vnicIpAddr(165),
        vnicIpV4Addr(166),
        vnicIpV4StaticAddr(167),
        vnicIpV4PooledAddr(168),
        vnicIPv4Dhcp(169),
        vnicIPv4Dns(170),
        vnicIPv4StaticRoute(171),
        vnicConnection(172),
        vnicNicConn(173),
        vnicVnic(174),
        vnicIf(175),
        vnicL2Lif(176),
        vnicEthLif(177),
        vnicFcLif(178),
        vnicLifVlan(179),
        vnicLifVsan(180),
        vnicL2If(181),
        vnicAFcIf(182),
        vnicEtherBaseIf(183),
        vnicAEtherIf(184),
        vnicAIpcIf(185),
        vnicAScsiIf(186),
        vnicFcOEIf(187),
        vnicFcIf(188),
        vnicEtherIf(189),
        vnicIpcIf(190),
        vnicScsiIf(191),
        vnicProfileSet(192),
        vnicProfile(193),
        vnicProfileAlias(194),
        vnicDynamicConReq(195),
        vnicDynamicConPolicy(196),
        vnicDynamicCon(197),
        vnicDynamicIdUniverse(198),
        vnicDynamicProvider(199),
        vnicDynamicProviderEp(200),
        vnicFcNode(201),
        vnicFcBase(202),
        vnicFc(203),
        vnicEtherBase(204),
        vnicEther(205),
        vnicIpc(206),
        vnicScsi(207),
        vnicBootTarget(208),
        lsbootItem(209),
        lsbootADef(210),
        lsbootPolicy(211),
        lsbootDef(212),
        lsbootCategory(213),
        lsbootStorage(214),
        lsbootLan(215),
        lsbootVirtualMedia(216),
        lsbootImage(217),
        lsbootRemoteImage(218),
        lsbootSanImage(219),
        lsbootLocalImage(220),
        lsbootLocalStorage(221),
        lsbootImagePath(222),
        lsbootLanImagePath(223),
        lsbootSanImagePath(224),
        procManager(225),
        procProcCounts(226),
        procTxCounts(227),
        procStimulusCounts(228),
        procPrtCounts(229),
        procProcs(230),
        procPrt(231),
        procDoer(232),
        storageController(233),
        storageUnit(234),
        storagePhysical(235),
        storageLogical(236),
        storageLocalLun(237),
        storageLocalDisk(238),
        storageLunDisk(239),
        storageQual(240),
        storageItem(241),
        storageLocalDiskConfig(242),
        storageLocalDiskConfigPolicy(243),
        storageLocalDiskConfigDef(244),
        storageLocalDiskPartition(245),
        memoryArray(246),
        memoryUnit(247),
        orgDomainGroup(248),
        memoryRuntimeHist(249),
        memoryQual(250),
        aaaRealm(251),
        aaaAuthRealm(252),
        aaaEp(253),
        aaaRadiusEp(254),
        aaaLdapEp(255),
        eventApplication(256),
        guiGuiCont(257),
        guiGuiComponent(258),
        aaaLdapProvider(259),
        aaaTacacsPlusProvider(260),
        pkiEp(261),
        pkiItem(262),
        pkiCertReq(263),
        pkiKeyRing(264),
        pkiTP(265),
        aaaDefinition(266),
        commDefinition(267),
        pkiDefinition(268),
        commSvcEp(269),
        commSvcChannel(270),
        commWebChannel(271),
        commEvtChannel(272),
        commSvc(273),
        commWeb(274),
        commHttp(275),
        versionProduct(276),
        commWsman(277),
        commCimxml(278),
        commShell(279),
        commTelnet(280),
        policyLogProfile(281),
        policyDeviceProfile(282),
        commSnmp(283),
        commDateTime(284),
        commSnmpTrap(285),
        commDns(286),
        commClient(287),
        commNtpProvider(288),
        mgmtAbsBackup(289),
        commSyslog(290),
        mgmtAbsImporter(291),
        commSyslogMonitor(292),
        mgmtDataExporter(293),
        mgmtDataImporter(294),
        mgmtRegistryInfo(295),
        aaaSystemUser(296),
        aaaEpAuthProfile(297),
        aaaUserLogin(298),
        aaaShellLogin(299),
        aaaWebLogin(300),
        aaaEpLogin(301),
        aaaRemoteUser(302),
        aaaEpUser(303),
        aaaUser(304),
        aaaSshAuth(305),
        aaaUserRole(306),
        aaaRole(307),
        aaaUserLocale(308),
        aaaLocale(309),
        aaaOrg(310),
        aaaSession(311),
        dcxVifEp(312),
        dcxVc(313),
        dcxVIf(314),
        dcxUniverse(315),
        dcxNs(316),
        adaptorFruCapProvider(317),
        adaptorFwCapProvider(318),
        adaptorCapDef(319),
        adaptorCapQual(320),
        mgmtDataExporterFsmTask(321),
        mgmtDataImporterFsmTask(322),
        adaptorBehCap(323),
        mgmtRegistryInfoFsmTask(324),
        networkElementFsmTask(325),
        adaptorNwMgmtCap(326),
        orgOrgFsmTask(327),
        adaptorUnit(328),
        adaptorHostIf(329),
        adaptorHostEthIf(330),
        adaptorHostFcIf(331),
        adaptorExtIf(332),
        adaptorExtEthIf(333),
        testingServiceProfileFsmTask(334),
        topSystemFsmTask(335),
        versionMatrix(336),
        versionFilter(337),
        adaptorEthPortStatsHist(338),
        adaptorEthPortBySizeSmallStats(341),
        adaptorEthPortBySizeSmallStatsHist(342),
        adaptorEthPortBySizeLargeStats(343),
        adaptorEthPortBySizeLargeStatsHist(344),
        adaptorEthPortOutsizedStats(345),
        adaptorEthPortOutsizedStatsHist(346),
        adaptorEthPortMcastStats(347),
        adaptorEthPortMcastStatsHist(348),
        adaptorEthPortErrStats(349),
        adaptorEthPortErrStatsHist(350),
        adaptorFcPortStats(351),
        adaptorFcPortStatsHist(352),
        adaptorVnicStats(353),
        identpoolMetaVerse(354),
        identpoolMetaSystem(355),
        identpoolUniverse(356),
        identpoolElement(357),
        identpoolPoolable(358),
        identpoolConsumed(359),
        adaptorMenloMcpuStatsHist(360),
        adaptorMenloMcpuErrorStats(361),
        adaptorMenloMcpuErrorStatsHist(362),
        adaptorMenloEthStats(363),
        adaptorMenloEthStatsHist(364),
        adaptorMenloEthErrorStats(365),
        adaptorMenloEthErrorStatsHist(366),
        adaptorMenloFcStats(367),
        adaptorMenloFcStatsHist(368),
        adaptorMenloFcErrorStats(369),
        adaptorMenloFcErrorStatsHist(370),
        adaptorMenloQStats(371),
        adaptorMenloQStatsHist(372),
        adaptorMenloQErrorStats(373),
        adaptorMenloQErrorStatsHist(374),
        identpoolPool(375),
        adaptorMenloNetEgStatsHist(376),
        adaptorMenloNetInStats(377),
        firmwareDownloadPolicy(378),
        adaptorMenloHostPortStats(379),
        adaptorMenloHostPortStatsHist(380),
        adaptorMenloDcePortStats(381),
        adaptorMenloDcePortStatsHist(382),
        adaptorEtherIfStats(383),
        adaptorEtherIfStatsHist(384),
        adaptorFcIfFrameStats(385),
        adaptorFcIfFrameStatsHist(386),
        orgDomainGroupPolicy(387),
        computeSystemQual(388),
        adaptorHostIfProfile(389),
        computeSystemAddrQual(390),
        computeSiteQual(391),
        computeOwnerQual(392),
        adaptorQueueProfile(393),
        configCatalogue(394),
        configConsumerCatalogue(395),
        configBackup(396),
        adaptorEthWorkQueueProfile(397),
        nfsExportDef(398),
        nfsClientDef(399),
        adaptorEthInterruptProfile(400),
        consumerUniverse(401),
        consumerInst(402),
        adaptorTcpIpRssHashProfile(403),
        adaptorIpV4RssHashProfile(404),
        adaptorIpV6RssHashProfile(405),
        adaptorExtIpV6RssHashProfile(406),
        firmwareRemoteCatalogue(407),
        adaptorEthFailoverProfile(408),
        adaptorFcRecvQueueProfile(409),
        firmwareSource(410),
        configBackupFsmTask(411),
        configConsumerCatalogueFsmTask(412),
        consumerInstFsmTask(413),
        adaptorFcPortProfile(414),
        adaptorFcErrorRecoveryProfile(415),
        sysfileEp(416),
        sysfileRepository(417),
        sysfileExporter(418),
        sysfileImporter(419),
        sysfileMutation(420),
        sysfileInstance(421),
        sysdebugEp(422),
        sysdebugRepository(423),
        sysdebugCoreFileRepository(424),
        sysdebugExporter(425),
        sysdebugCoreFileExportTarget(426),
        sysdebugAutoCoreFileExportTarget(427),
        sysdebugManualCoreFileExportTarget(428),
        sysdebugFile(429),
        sysdebugCore(430),
        sysdebugLogControlEp(431),
        sysdebugLogControlDomain(432),
        sysdebugLogControlModule(433),
        sysdebugLogControlDestinationFile(434),
        sysdebugLogControlDestinationSyslog(435),
        ruleDefinition(436),
        ruleItem(437),
        ruleRequirement(438),
        ruleSizeRequirement(439),
        swDomain(440),
        swPIoEp(441),
        swCIoEp(442),
        swBorderDomain(443),
        swBorderEp(444),
        swBorderPc(445),
        swLanBorder(446),
        swLanEp(447),
        swLanPc(448),
        swEthLanBorder(449),
        swEthLanEp(450),
        swEthLanPc(451),
        swVlan(452),
        swUlan(453),
        swAccessDomain(454),
        swAccessEp(455),
        swUtilityDomain(456),
        swSanBorder(457),
        swSanEp(458),
        swFcSanBorder(459),
        swFcSanEp(460),
        swVsan(461),
        swEnvStats(462),
        swEnvStatsHist(463),
        swSystemStats(464),
        swSystemStatsHist(465),
        networkruleDefinition(466),
        networkruleItem(467),
        networkruleRequirement(468),
        etherPIo(469),
        etherServerIntFIo(470),
        etherSwitchIntFIo(471),
        etherConfig(472),
        etherIfConfig(473),
        etherSwIfConfig(474),
        etherNicIfConfig(475),
        etherTxStats(476),
        etherTxStatsHist(477),
        etherRxStats(478),
        etherRxStatsHist(479),
        etherErrStats(480),
        etherErrStatsHist(481),
        etherLossStats(482),
        etherLossStatsHist(483),
        syntheticDirectory(484),
        syntheticFile(485),
        syntheticFsObj(486),
        syntheticTime(487),
        syntheticFileSystem(488),
        firmwareCapProvider(489),
        firmwareCatalogue(490),
        firmwareUnit(491),
        firmwareRunning(492),
        firmwareUpdatable(493),
        firmwareBootUnit(494),
        firmwareBootDefinition(495),
        firmwareImage(496),
        firmwareInstallable(497),
        firmwareDistImage(498),
        firmwareDistributable(499),
        firmwareDownloader(500),
        firmwareCompItem(501),
        firmwareCompSource(502),
        firmwareCompTarget(503),
        firmwarePack(504),
        firmwarePackItem(505),
        firmwareComputePack(506),
        firmwareComputeHostPack(507),
        firmwareComputeMgmtPack(508),
        firmwareType(509),
        firmwareDependency(510),
        osInstance(511),
        osAgent(512),
        capabilityCatalogue(513),
        capabilityProvider(514),
        capabilityDef(515),
        capabilityItem(516),
        portGroup(517),
        portPhysSwitchIo(518),
        portPIo(519),
        portIntFIo(520),
        portServerIntFIo(521),
        portSwitchIntFIo(522),
        portDomainEp(523),
        policyObject(524),
        policyHolder(525),
        policyBinding(526),
        policyDefinition(527),
        orgOrg(528),
        callhomeEp(529),
        callhomeSource(530),
        callhomeSmtp(531),
        callhomePeriodicSystemInventory(532),
        callhomeProfile(533),
        callhomeDest(534),
        callhomePolicy(535),
        callhomeTestAlert(536),
        networkEp(537),
        networkIfEp(538),
        networkPhysEp(539),
        networkPIoEp(540),
        networkCIoEp(541),
        networkVnetEp(542),
        networkDomainEp(543),
        networkElement(544),
        networkConn(545),
        networkIfStats(546),
        uuidpoolPool(547),
        uuidpoolPooled(548),
        uuidpoolBlock(549),
        uuidpoolAddr(550),
        uuidpoolFormat(551),
        uuidpoolPoolable(552),
        uuidpoolUniverse(553),
        mgmtEntity(554),
        mgmtBackup(555),
        mgmtImporter(556),
        mgmtAccessPolicy(557),
        mgmtAccessPolicyItem(558),
        mgmtAccessPort(559),
        mgmtIntAuthPolicy(560),
        mgmtController(561),
        mgmtIf(562),
        ippoolPool(563),
        ippoolPooled(564),
        ippoolBlock(565),
        ippoolAddr(566),
        ippoolPoolable(567),
        ippoolUniverse(568),
        poolUniverse(569),
        poolElement(570),
        poolPoolable(571),
        poolPoolMember(572),
        poolPool(573),
        computeConfigPolicy(574),
        computeInitConfigPolicy(575),
        computeAutoconfigPolicy(576),
        computeBladeInheritPolicy(577),
        computeScrubPolicy(578),
        computeDiscPolicy(579),
        computeBladeDiscPolicy(580),
        computeChassisDiscPolicy(581),
        computePsuDef(582),
        computePsuPolicy(583),
        computePsuControl(584),
        computePool(585),
        computePoolable(586),
        computePooled(587),
        computePooledPhysical(588),
        computePooledSlot(589),
        computePoolingPolicy(590),
        computeQual(591),
        nfsRepositorySpecPolicy(592),
        computeBladePosQual(593),
        computeChassisQual(594),
        computeSlotQual(595),
        computeQualifiedPolicy(596),
        computeContainer(597),
        computeItem(598),
        computePhysical(599),
        computeLogical(600),
        computeVirtualContainer(601),
        computeVirtual(602),
        computePartition(603),
        memoryErrorStatsHist(604),
        computeBoard(605),
        computeMbPowerStats(606),
        computeMbPowerStatsHist(607),
        computeMbTempStats(608),
        computeMbTempStatsHist(609),
        lsTier(614),
        lsServer(615),
        lsPower(616),
        lsComputeBinding(617),
        lsBinding(618),
        lsRequirement(619),
        lsAgentPolicy(620),
        vmEp(621),
        vmInstance(622),
        vmAdaptor(623),
        vmNic(624),
        vmHba(625),
        vmVlan(626),
        vmVsan(627),
        extvmmEp(628),
        extvmmProvider(629),
        fcpoolInitiators(632),
        fcpoolInitiator(633),
        fcpoolBlock(634),
        fcpoolFormat(635),
        fcpoolAddr(636),
        fcpoolPoolable(637),
        fcpoolUniverse(638),
        fcpoolBootTarget(639),
        macpoolPool(640),
        macpoolPooled(641),
        macpoolFormat(642),
        macpoolBlock(643),
        macpoolAddr(644),
        macpoolPoolable(645),
        macpoolUniverse(646),
        solDef(647),
        solConfig(648),
        solPolicy(649),
        solIf(650),
        dpsecMac(651),
        qosclassDefinition(652),
        qosclassItem(653),
        qosclassFc(654),
        qosclassEth(655),
        qosclassEthBE(656),
        qosclassEthClassified(658),
        qosDefinition(659),
        qosItem(660),
        epqosDefinition(661),
        epqosDefinitionDelTask(662),
        epqosItem(663),
        epqosEgress(664),
        equipmentHwCapProvider(665),
        equipmentBehCap(666),
        equipmentFruCapProvider(667),
        equipmentIntegratedComponentCapProvider(668),
        equipmentHolderCapProvider(669),
        equipmentSwitchCapProvider(670),
        equipmentMgmtCapProvider(671),
        equipmentChassisCapProvider(672),
        equipmentBladeCapProvider(673),
        equipmentBaseBoardCapProvider(674),
        equipmentBladeBiosCapProvider(675),
        equipmentLocalDiskCapProvider(676),
        equipmentLocalDiskControllerCapProvider(677),
        equipmentHostIfCapProvider(678),
        equipmentProcessorUnitCapProvider(679),
        equipmentMemoryUnitCapProvider(680),
        equipmentIOCardCapProvider(681),
        equipmentPsuCapProvider(682),
        equipmentFanModuleCapProvider(683),
        equipmentGemCapProvider(684),
        equipmentManufacturingDef(685),
        equipmentPhysicalDef(686),
        equipmentServiceDef(687),
        equipmentAdaptorDef(688),
        equipmentProcessorUnitDef(689),
        equipmentSlotArrayRef(690),
        equipmentSlotArray(691),
        equipmentItem(692),
        equipmentStateful(693),
        equipmentHolder(694),
        equipmentStatefulChComp(695),
        equipmentStatefulBladeComp(696),
        equipmentPsu(697),
        equipmentFanModule(698),
        equipmentFan(699),
        equipmentEnvSensor(700),
        equipmentCard(701),
        equipmentSwitchCard(702),
        equipmentChassis(703),
        equipmentIOCard(704),
        equipmentLed(705),
        processorErrorStatsHist(706),
        equipmentLocatorLed(707),
        equipmentChassisStats(708),
        equipmentChassisStatsHist(709),
        equipmentPsuStats(712),
        equipmentPsuStatsHist(713),
        equipmentPsuInputStats(714),
        equipmentPsuInputStatsHist(715),
        equipmentFanModuleStats(716),
        equipmentFanModuleStatsHist(717),
        equipmentFanStats(718),
        equipmentFanStatsHist(719),
        flowctrlDefinition(720),
        flowctrlItem(721),
        computePCIeFatalStatsHist(722),
        aaaRealmFsmTask(723),
        orgOrgSource(724),
        adaptorHostFcIfFsmTask(725),
        extpolDomain(726),
        commSvcEpFsmTask(727),
        computeBladeFsmTask(728),
        epqosDefinitionDelTaskFsmTask(729),
        epqosDefinitionFsmTask(730),
        equipmentChassisFsmTask(731),
        equipmentIOCardFsmTask(732),
        equipmentLocatorLedFsmTask(733),
        extvmmEpFsmTask(734),
        configAppImpactResponse(736),
        fabricComputeSlotEpFsmTask(737),
        fabricLanCloudFsmTask(738),
        firmwareDownloaderFsmTask(739),
        firmwareImageFsmTask(740),
        mgmtBackupFsmTask(741),
        mgmtControllerFsmTask(742),
        mgmtIfFsmTask(743),
        mgmtImporterFsmTask(744),
        pkiEpFsmTask(745),
        qosclassDefinitionFsmTask(746),
        statsCollectionPolicyFsmTask(747),
        swAccessDomainFsmTask(748),
        swEthLanBorderFsmTask(749),
        swFcSanBorderFsmTask(750),
        swUtilityDomainFsmTask(751),
        syntheticFsObjFsmTask(752),
        sysdebugAutoCoreFileExportTargetFsmTask(753),
        sysdebugLogControlEpFsmTask(754),
        sysdebugManualCoreFileExportTargetFsmTask(755),
        sysfileMutationFsmTask(756),
        vnicProfileSetFsmTask(757),
        vnicDefBeh(758),
        equipmentLocalDiskDef(759),
        sysdebugMEpLog(762),
        identpoolBlockQual(763),
        identpoolQualItem(764),
        identpoolIPQual(765),
        identpoolDomainGroupQual(766),
        nfsExportDefFsmTask(767),
        biosBOT(768),
        biosBootDevGrp(769),
        biosBootDev(770),
        etherPauseStats(771),
        etherPauseStatsHist(772),
        adaptorSanCap(773),
        memoryArrayEnvStats(774),
        memoryArrayEnvStatsHist(775),
        memoryUnitEnvStats(776),
        memoryUnitEnvStatsHist(777),
        processorEnvStats(778),
        processorEnvStatsHist(779),
        aaaExtMgmtCutThruTkn(780),
        nwctrlDefinition(781),
        lsSPMeta(786),
        fabricVCon(789),
        fabricVConProfile(790),
        vmCont(793),
        vmDirCont(794),
        vmDCOrg(795),
        vmDC(796),
        vmOrg(797),
        vmSwitch(798),
        vmVnicProfInst(799),
        vmVnicProfCl(800),
        vmVirtual(801),
        vmHv(802),
        extvmmMasterExtKey(803),
        extvmmKeyInst(804),
        extvmmKeyStore(805),
        extvmmKeyRing(806),
        extvmmSwitchDelTask(807),
        biosVfIntelTurboBoostTech(808),
        biosVfEnhancedIntelSpeedStepTech(809),
        biosVfIntelHyperThreadingTech(810),
        biosVfCoreMultiProcessing(811),
        biosVfExecuteDisableBit(812),
        biosVfIntelVirtualizationTechnology(813),
        biosVfIntelVTForDirectedIO(814),
        biosVfDirectCacheAccess(817),
        biosVfSelectMemoryRASConfiguration(818),
        biosVfNUMAOptimized(819),
        biosVfIntelEntrySASRAIDModule(820),
        biosVfOnboardSATAController(822),
        biosVfSerialPortAEnable(823),
        fabricEtherRef(825),
        biosVfMemoryMappedIOAbove4GB(826),
        biosVfFrontPanelLockout(828),
        changeEp(829),
        biosVfAssertNMIOnSERR(830),
        biosVfAssertNMIOnPERR(831),
        biosVfResumeOnACPowerLoss(832),
        biosVfConsoleRedirection(835),
        policyUniverse(838),
        policyCluster(839),
        policySource(840),
        biosVfPOSTErrorPause(841),
        biosVProfile(842),
        biosVFeat(843),
        powerAGroup(845),
        powerABudget(848),
        powerGroup(849),
        powerBudget(850),
        sysdebugMEpLogDef(851),
        sysdebugMEpLogPolicy(852),
        sysdebugLogBehavior(853),
        sysdebugBackupBehavior(854),
        bmcSELCounter(857),
        computeBehCap(860),
        computePciCap(861),
        extvmmKeyStoreFsmTask(862),
        fabricConsumer(863),
        extvmmSwitchDelTaskFsmTask(864),
        biosVfUSBBootConfig(869),
        biosVfProcessorC3Report(870),
        biosVfProcessorC6Report(871),
        biosVfOSBootWatchdogTimer(873),
        biosVfOSBootWatchdogTimerPolicy(874),
        biosVfACPI10Support(876),
        computeMemoryUnitConstraintDef(879),
        computePCIeFatalProtocolStats(882),
        computePCIeFatalReceiveStats(884),
        computeResourceSetManager(885),
        computeResourceSet(886),
        computeResourceSetMember(887),
        computePCIeFatalStats(888),
        vmLifeCyclePolicy(892),
        diagSrvCapProvider(893),
        diagCtrl(894),
        diagRslt(895),
        diagSrvCtrl(896),
        equipmentSwitchCap(897),
        equipmentMemoryUnitDiscoveryModifierDef(898),
        extvmmMasterExtKeyFsmTask(899),
        adaptorFcInterruptProfile(900),
        capabilityEp(901),
        capabilityUpdater(902),
        capabilityUpdate(903),
        equipmentCatalogCapProvider(904),
        capabilityUpdaterFsmTask(905),
        firmwareDistributableFsmTask(906),
        topMetaInf(907),
        storageRaidBattery(908),
        computeRtcBattery(909),
        vmVif(910),
        memoryBufferUnit(912),
        memoryBufferUnitEnvStats(913),
        memoryBufferUnitEnvStatsHist(914),
        computeIOHub(915),
        computeBoardController(916),
        computeIOHubEnvStats(917),
        computeIOHubEnvStatsHist(918),
        diagRunPolicy(919),
        diagTest(920),
        diagBladeTest(921),
        diagNetworkTest(922),
        biosSettings(926),
        computeDefaults(931),
        computePlatform(932),
        capabilityCatalogueFsmTask(933),
        swVlanPortNs(934),
        processorErrorStats(935),
        biosVfSparingMode(936),
        biosVfMirroringMode(937),
        biosVfLvDIMMSupport(938),
        memoryErrorStats(940),
        commXmlClConnPolicy(941),
        computePhysicalQual(942),
        procSvc(943),
        apeDcosAgManager(944),
        apeSwitchFirmwareInv(945),
        equipmentLocalDiskControllerDef(946),
        equipmentBoardControllerDef(947),
        biosARef(948),
        biosRef(949),
        biosFeatureRef(950),
        biosParameterRef(951),
        biosSettingRef(952),
        adaptorDiagCap(953),
        equipmentPOSTCodeContainer(954),
        equipmentPOSTCodeTemplate(955),
        fabricFcVsanPc(956),
        fabricLanMonCloud(957),
        fabricSanMonCloud(958),
        fabricEthMonLan(959),
        fabricFcMonSan(960),
        fabricMon(961),
        fabricEthMon(962),
        fabricFcMon(963),
        fabricMonDestEp(964),
        fabricEthMonDestEp(965),
        fabricFcMonDestEp(966),
        fabricMonSrcEp(967),
        fabricEthMonSrcEp(968),
        fabricFcMonSrcEp(969),
        fabricMonSrcRef(970),
        fabricEthMonSrcRef(971),
        fabricFcMonSrcRef(972),
        fabricMonSrcFiltEp(973),
        fabricEthMonFiltEp(974),
        fabricFcMonFiltEp(975),
        fabricMonFiltRef(976),
        fabricEthMonFiltRef(977),
        fabricFcMonFiltRef(978),
        fabricFcEstcCloud(979),
        fabricEthEstcCloud(980),
        fabricEthVlanPortEp(981),
        fabricVlanEp(982),
        fabricExternalEstc(983),
        fabricFcEstc(984),
        fabricEthEstc(985),
        fabricEstcEp(986),
        fabricAFcEstcEp(987),
        fabricFcEstcEp(988),
        fabricAFcoeEstcEp(989),
        fabricFcoeEstcEp(990),
        fabricEthEstcEp(991),
        fabricTargetEp(992),
        fabricEthTargetEp(993),
        processorUnitAssocCtx(994),
        biosVfUEFIOSUseLegacyVideo(998),
        vnicIpV4AddrConf(999),
        vnicIpV4AddrExplConf(1000),
        vnicIpV4ProfDerivedAddr(1001),
        storageDevice(1002),
        storageDrive(1003),
        aaaConfig(1004),
        aaaAuthMethod(1005),
        aaaDefaultAuth(1006),
        aaaConsoleAuth(1007),
        aaaDomainAuth(1008),
        aaaDomain(1009),
        aaaLdapGroupRule(1010),
        aaaUserGroup(1011),
        aaaLdapGroup(1012),
        aaaProviderGroup(1013),
        aaaProviderRef(1014),
        adaptorHwAddrCap(1015),
        adaptorUplinkHwAddrCap(1016),
        adaptorHostethHwAddrCap(1017),
        adaptorHostfcHwAddrCap(1018),
        adaptorUnitAssocCtx(1019),
        sysdebugTechSupFileRepository(1020),
        sysdebugTechSupport(1021),
        sysdebugTechSupportCmdOpt(1022),
        powerEp(1023),
        powerPrioWght(1024),
        powerPolicy(1025),
        powerPlacement(1026),
        powerGroupAdditionPolicy(1027),
        powerGroupMember(1028),
        powerChassisMember(1029),
        powerRackUnitMember(1030),
        powerGroupQual(1031),
        powerMgmtPolicy(1032),
        powerGroupStats(1033),
        powerGroupStatsHist(1034),
        swMonSrcEp(1035),
        swEthMonSrcEp(1036),
        swFcMonSrcEp(1037),
        swEstcEp(1038),
        swFcEstcEp(1039),
        swEthEstcEp(1040),
        swTargetEp(1041),
        swEthTargetEp(1042),
        swFcoeEstcEp(1043),
        swMonDomain(1044),
        swLanMon(1045),
        swSanMon(1046),
        swEthLanMon(1047),
        swFcSanMon(1048),
        swMon(1049),
        swEthMon(1050),
        swFcMon(1051),
        swMonDestEp(1052),
        swEthMonDestEp(1053),
        swFcMonDestEp(1054),
        swSanPc(1055),
        swFcSanPc(1056),
        capabilityMgmtExtension(1057),
        pciCard(1058),
        pciUnit(1059),
        licenseEp(1060),
        licenseFeature(1061),
        licenseServerHostId(1062),
        licenseFile(1063),
        licenseSource(1064),
        licenseContents(1065),
        licenseFeatureLine(1066),
        licenseInstance(1067),
        licenseSourceFile(1068),
        licenseProp(1069),
        licenseDownloader(1070),
        licenseCapProvider(1071),
        licenseFeatureCapProvider(1072),
        portTrustMode(1073),
        computePoolPolicyRef(1074),
        computePooledRackUnit(1075),
        computePhysicalAssocCtx(1076),
        computeComputeDiscPolicy(1077),
        computeServerDiscPolicy(1078),
        computeRackUnit(1079),
        lsServerAssocCtx(1080),
        lsmaintMaintPolicy(1081),
        lsmaintAck(1082),
        equipmentPicture(1083),
        equipmentMgmtExtCapProvider(1084),
        equipmentRackUnitCapProvider(1085),
        equipmentBladeAGLibrary(1086),
        equipmentFexCapProvider(1087),
        equipmentPciDef(1088),
        equipmentRaidDef(1089),
        equipmentPortGroupDef(1090),
        equipmentAssocCtx(1091),
        equipmentFexEnvStats(1092),
        equipmentFexEnvStatsHist(1093),
        equipmentFexPowerSummary(1094),
        equipmentFexPowerSummaryHist(1095),
        equipmentFexPsuInputStats(1096),
        equipmentFexPsuInputStatsHist(1097),
        equipmentRackUnitPsuStats(1098),
        equipmentRackUnitPsuStatsHist(1099),
        equipmentRackUnitFanStats(1100),
        equipmentRackUnitFanStatsHist(1101),
        equipmentFex(1102),
        dhcpInst(1103),
        dhcpLease(1104),
        dhcpAcquired(1105),
        trigInst(1106),
        trigWindow(1107),
        trigSched(1108),
        trigSchedWindow(1109),
        trigAbsWindow(1110),
        trigRecurrWindow(1111),
        trigMeta(1112),
        trigTriggered(1113),
        trigTriggerable(1114),
        trigTest(1115),
        trigAck(1116),
        trigConfAck(1117),
        trigResAck(1118),
        capabilityMgmtExtensionFsmTask(1119),
        computePhysicalFsmTask(1120),
        computeRackUnitFsmTask(1121),
        equipmentFexFsmTask(1122),
        fabricSanCloudFsmTask(1124),
        licenseDownloaderFsmTask(1125),
        licenseFileFsmTask(1126),
        licenseInstanceFsmTask(1127),
        lsServerFsmTask(1128),
        swEthMonFsmTask(1129),
        swFcMonFsmTask(1130),
        sysdebugTechSupportFsmTask(1131),
        statsPasadenaCollectionPolicy(1132),
        statsDbMigrationStatus(1133),
        statsCustomEp(1134),
        statsStandardEp(1135),
        statsChartContainer(1136),
        statsChart(1137),
        statsCustomChart(1138),
        statsStandardChart(1139),
        adaptorHBAVnicStats(1140),
        adaptorHBAVnicStatsHist(1141),
        adaptorNICVnicStats(1142),
        equipmentGemPortCap(1143),
        equipmentXcvr(1144),
        portPIoFsmTask(1145),
        vnicBootIpPolicy(1146),
        adaptorLldpCap(1147),
        lldpAcquired(1148),
        extmgmtIf(1149),
        extmgmtIfMonPolicy(1150),
        extmgmtMiiStatus(1151),
        extmgmtGatewayPing(1152),
        extmgmtArpTargets(1153),
        biosVfOptionROMLoad(1154),
        firmwareBundleTypeCapProvider(1155),
        firmwareBundleType(1156),
        storageEnclosure(1157),
        sysdebugCoreFsmTask(1158),
        fabricAEthEstcEp(1159),
        fabricEstcPc(1160),
        fabricEthEstcPc(1161),
        fabricEthEstcPcEp(1162),
        fabricEthVlanPc(1163),
        swEthEstcPc(1164),
        commSyslogSource(1165),
        firmwareSpec(1166),
        computeRackUnitMbTempStats(1167),
        computeRackUnitMbTempStatsHist(1168),
        storageLocalDiskSlotEp(1169),
        computeRackPosQual(1170),
        computeRackQual(1171),
        biosVfCPUPerformance(1172),
        fabricFcoeVsanPortEp(1173),
        pciEquipSlot(1174),
        equipmentDbgPluginCapProvider(1175),
        commSvcLimits(1176),
        commShellSvcLimits(1177),
        commWebSvcLimits(1178),
        adaptorFruCapRef(1179),
        biosVfMaxVariableMTRRSetting(1180),
        biosVfUSBSystemIdlePowerOptimizingSetting(1181),
        biosVfUSBFrontPanelAccessLock(1182),
        biosVfUCSMBootOrderRuleControl(1183),
        equipmentLocalDiskControllerCapRef(1184),
        equipmentDiscoveryCap(1185),
        topSysDefaults(1186),
        iqnpoolPool(1187),
        iqnpoolPooled(1188),
        iqnpoolBlock(1189),
        iqnpoolAddr(1190),
        iqnpoolFormat(1191),
        iqnpoolPoolable(1192),
        iqnpoolUniverse(1193),
        fabricSwSrvPc(1194),
        fabricDceSwSrvPc(1195),
        fabricDceSwSrvPcEp(1196),
        fabricEpMgr(1197),
        biosVfProcessorCState(1198),
        biosVfProcessorC1E(1199),
        biosVIdentityParams(1200),
        vnicIPv4IscsiAddr(1201),
        vnicIPv4PooledIscsiAddr(1202),
        vnicVProfileAlias(1203),
        vnicOProfileAlias(1204),
        vnicInternalProfile(1205),
        vnicVlan(1206),
        vnicIScsiNode(1207),
        vnicIScsi(1208),
        vnicIScsiTargetIf(1209),
        vnicIScsiStaticTargetIf(1210),
        vnicLun(1211),
        vnicIScsiAutoTargetIf(1212),
        lsbootIScsi(1213),
        lsbootIScsiImagePath(1214),
        aaaBanner(1215),
        featureCatalogEp(1216),
        aaaPwdProfile(1217),
        featureServerDef(1218),
        featureStorageDef(1219),
        featureNetworkDef(1220),
        featureEnvDef(1221),
        domainEp(1222),
        domainFeatureCatalog(1223),
        adaptorExtIfPc(1224),
        adaptorExtEthIfPc(1225),
        adaptorPIoEp(1226),
        sysdebugTechSupportOperation(1227),
        lsServerOperation(1228),
        fabricComputeSlotEpOperation(1229),
        fabricComputePhEpOperation(1230),
        fabricSwChPhEpOperation(1231),
        computeAOperation(1232),
        computePhysicalOperation(1233),
        swPhys(1234),
        swPhysEtherEp(1235),
        swPhysFcEp(1236),
        swVlanPortNsOverride(1237),
        etherPortChanIdElem(1238),
        etherPortChanIdUniverse(1239),
        etherCIoEp(1240),
        etherPc(1241),
        etherInternalPc(1242),
        vnicMgmtBase(1243),
        vnicMgmt(1244),
        vnicMgmtIf(1245),
        vnicFault(1246),
        etherExternalEp(1247),
        etherIntFIoEp(1248),
        etherServerIntFIoPcEp(1249),
        identDomainSyncEp(1250),
        mgmtPmonEntry(1251),
        iscsiAuthProfile(1252),
        iscsiProtocolProfile(1253),
        configSearchResult(1254),
        queryEp(1255),
        vmClientContainer(1256),
        vmComputeEp(1257),
        queryDependencyContext(1258),
        queryImportContext(1259),
        queryDependencyRef(1260),
        queryresultDestOrgEp(1261),
        queryresultDomainGroupEp(1262),
        queryresultOrgEp(1263),
        equipmentPortGroupAggregationDef(1264),
        equipmentPortGroupSwComplexDef(1265),
        equipmentPortSwComplexRef(1266),
        equipmentBeaconLed(1267),
        identpoolDomain(1268),
        equipmentPsuOutputStatsHist(1269),
        equipmentNetworkElementFanStats(1270),
        policySystemProfile(1271),
        equipmentBeaconLedFsmTask(1272),
        firmwareInfraPolicy(1273),
        swPhysFsmTask(1274),
        vmLifeCyclePolicyFsmTask(1275),
        firmwareUpgradeConstraint(1276),
        adaptorFamilyTypeDef(1277),
        adaptorUnitExtn(1278),
        extpolRegistryCapability(1279),
        orgExtension(1280),
        domainFamilyCapProvider(1281),
        trigPendingAckCount(1282),
        lsVersionBeh(1287),
        equipmentBiosDef(1288),
        equipmentDimmMapping(1289),
        equipmentDimmEntry(1290),
        equipmentBladeConnDef(1291),
        equipmentAdaptorConnDef(1292),
        equipmentIOCardTypeDef(1293),
        computePnuOSImage(1294),
        etherServerIntFIoFsmTask(1295),
        equipmentServerFeatureCap(1296),
        equipmentBladeIOMConnDef(1297),
        lsbootUpgradeStatus(1298),
        biosVfOSBootWatchdogTimerTimeout(1299),
        fsmFsm(1300),
        fsmStage(1301),
        faultBaseHolder(1302),
        faultLocalTypedHolder(1303),
        faultBasePolicy(1304),
        policyControlEpOperation(1305),
        faultSuppressPolicy(1306),
        faultSuppressPolicyItem(1307),
        faultSuppressTask(1308),
        faultAffectedClass(1309),
        fabricDceSwSrvEpOperation(1310),
        apeVnicStats(1311),
        apePaloVnicStats(1312),
        vnicFcGroupTempl(1313),
        vnicSanConnPolicy(1314),
        vnicLanConnPolicy(1315),
        vnicAGroup(1316),
        vnicFcGroupDef(1317),
        vnicIScsiBase(1318),
        vnicIScsiLCP(1319),
        vnicDynamicConPolicyRef(1320),
        vnicConnDef(1321),
        vnicABeh(1322),
        vnicVnicBehPolicy(1323),
        vnicVhbaBehPolicy(1324),
        biosVfSriovConfig(1325),
        fabricVnetPermit(1326),
        statsInventoryMeta(1327),
        fabricMulticastPolicy(1328),
        storageIniGroup(1329),
        storageInitiator(1330),
        storageADef(1331),
        storageConnectionPolicy(1332),
        policyItem(1333),
        fsmStatus(1334),
        swVlanGroup(1335),
        swVlanRef(1336),
        swFcoeSanEp(1337),
        swFcoeSanPc(1338),
        swFcZoneSet(1339),
        swFcServerZoneGroup(1340),
        swZoneInitiatorMember(1341),
        swFcZone(1342),
        swFcZoneMember(1343),
        swZoneTargetMember(1344),
        swFabricZoneNs(1345),
        swFabricZoneNsOverride(1346),
        swCardEnvStats(1347),
        swCardEnvStatsHist(1348),
        etherPIoEndPoint(1349),
        etherFcoeInterfaceStats(1350),
        etherFcoeInterfaceStatsHist(1351),
        mgmtExportPolicy(1352),
        mgmtCfgExportPolicy(1353),
        mgmtBackupPolicy(1354),
        mgmtConnection(1355),
        commClientItem(1356),
        aaaItem(1357),
        commItem(1358),
        vnicRackServerDiscoveryProfile(1359),
        vnicIScsiBootParams(1360),
        vnicIScsiBootVnic(1361),
        sysfileDigest(1362),
        versionEp(1363),
        versionVersion(1364),
        versionApplication(1365),
        fcpoolInitiatorEp(1366),
        lsFcLocale(1367),
        lsFcZoneGroup(1368),
        lsZoneInitiatorMember(1369),
        lsFcZone(1370),
        lsFcZoneMember(1371),
        vnicLstorageIScsi(1372),
        lsVConAssign(1373),
        storageMeta(1374),
        vnicIScsiTargetParams(1375),
        vnicIScsiInitiatorParams(1376),
        policyPolicyScope(1377),
        policyPolicyRequestor(1378),
        policyDigest(1379),
        policyControlEp(1380),
        policyControl(1381),
        policyDateTime(1382),
        policyCommunication(1383),
        policyDns(1384),
        policySecurity(1385),
        policyMonitoring(1386),
        policyFault(1387),
        policyInfraFirmware(1388),
        policyConfigBackup(1389),
        policyMEp(1390),
        policyDiscovery(1391),
        policyPowerMgmt(1392),
        policyPsu(1393),
        policyControlled(1394),
        policyControlledInstance(1395),
        policyControlledType(1396),
        orgFirmwareVersionCount(1397),
        nfsEp(1398),
        nfsMountDef(1399),
        nfsMountInst(1400),
        trigToken(1401),
        trigClientToken(1402),
        trigBaseSched(1403),
        trigLocalSched(1404),
        trigBaseAbsWindow(1405),
        trigLocalAbsWindow(1406),
        capabilityFeatureLimits(1407),
        capabilitySystemLimits(1408),
        capabilityNetworkLimits(1409),
        capabilityStorageLimits(1410),
        identIdentCtx(1411),
        identSysInfo(1412),
        identMetaVerse(1413),
        identMetaSystem(1414),
        identIdentRequest(1415),
        identRequestEp(1416),
        fabricLanAccessMgr(1417),
        fabricZoneIdUniverse(1418),
        fabricAFcoeSanEp(1419),
        fabricFcoeSanEp(1420),
        fabricFcoeSanPcEp(1421),
        fabricFcoeSanPc(1422),
        fabricFcoeVsanPc(1423),
        fabricNetGroup(1424),
        fabricPooledVlan(1425),
        fabricPoolableVlan(1426),
        fabricVsanMembership(1427),
        fabricVnetReq(1428),
        fabricVlanReq(1429),
        fabricVnetGroupReq(1430),
        fabricVlanGroupReq(1431),
        fabricOrgVlanPolicy(1432),
        observeObservedCont(1433),
        observeObserved(1434),
        observeFilter(1435),
        configSorter(1436),
        extpolConnectorContainer(1437),
        extpolEp(1438),
        extpolConnector(1439),
        extpolSvc(1440),
        extpolRegistry(1441),
        faultDomainInst(1442),
        faultSummaryInst(1443),
        faultDomainEp(1444),
        extpolController(1445),
        extpolClientCont(1446),
        extpolClient(1447),
        extpolSystemContext(1448),
        callhomeItem(1449),
        firmwareBundleInfo(1450),
        firmwareInfraPack(1451),
        firmwareCatalogPack(1452),
        firmwareSystem(1453),
        firmwareInfra(1454),
        firmwareHost(1455),
        firmwareBlade(1456),
        firmwareRack(1457),
        firmwareStatus(1458),
        firmwareSystemCompCheckResult(1459),
        firmwareInstallImpact(1460),
        firmwareHostPackModImpact(1461),
        firmwareAck(1462),
        firmwareUpgradeInfo(1463),
        firmwareUpgradeDetail(1464),
        firmwareBundleInfoDigest(1465),
        storageDomainEp(1466),
        storageVirtualDrive(1467),
        storageConnectionDef(1468),
        storageTarget(1469),
        storageFcTargetEp(1470),
        storageVsanRef(1471),
        initiatorEp(1472),
        initiatorRequestorEp(1473),
        initiatorGroupEp(1474),
        initiatorInitiatorEp(1475),
        initiatorIScsiInitiatorEp(1476),
        initiatorFcInitiatorEp(1477),
        initiatorStoreEp(1478),
        initiatorUnitEp(1479),
        initiatorLunEp(1480),
        initiatorRequestorGrpEp(1481),
        initiatorMemberEp(1482),
        storageEp(1483),
        storageNodeEp(1484),
        storageEpUser(1485),
        storageAuthKey(1486),
        storageTransportIf(1487),
        storageTargetIf(1488),
        storageIScsiTargetIf(1489),
        storageFcTargetIf(1490),
        storageL2If(1491),
        storageFcIf(1492),
        storageEtherIf(1493),
        storageSystem(1494),
        ipIpV4Addr(1495),
        ipIPv4Dns(1496),
        ipServiceIf(1497),
        ipIpV4StaticAddr(1498),
        fabricCartridgeSlotEpOperation(1499),
        extpolEpFsmTask(1500),
        extpolRegistryFsmTask(1501),
        firmwareSystemFsmTask(1502),
        identIdentRequestFsmTask(1503),
        identMetaSystemFsmTask(1504),
        mgmtExportPolicyFsmTask(1505),
        nfsMountDefFsmTask(1506),
        nfsMountInstFsmTask(1507),
        observeObservedFsmTask(1508),
        policyControlEpFsmTask(1509),
        policyPolicyScopeFsmTask(1510),
        storageSystemFsmTask(1511),
        aaaEpFsm(1512),
        storageLocalDiskOperation(1513),
        aaaLdapEpFsm(1514),
        storageVirtualDriveOperation(1515),
        aaaRadiusEpFsm(1516),
        storageVirtualDriveRefOperation(1517),
        aaaTacacsPlusEpFsm(1518),
        storageControllerOperation(1519),
        aaaRealmFsm(1520),
        storageComputeBladeOperation(1521),
        aaaAuthRealmFsm(1522),
        aaaAuthRealmFsmStage(1523),
        aaaUserEpFsm(1524),
        mgmtBackupOperation(1525),
        adaptorExtEthIfFsm(1526),
        adaptorExtEthIfFsmStage(1527),
        adaptorHostEthIfFsm(1528),
        adaptorHostEthIfFsmStage(1529),
        adaptorHostFcIfFsm(1530),
        adaptorHostFcIfFsmStage(1531),
        callhomeEpFsm(1532),
        callhomeEpFsmStage(1533),
        capabilityCatalogueFsm(1534),
        capabilityCatalogueFsmStage(1535),
        capabilityMgmtExtensionFsm(1536),
        capabilityMgmtExtensionFsmStage(1537),
        capabilityUpdaterFsm(1538),
        capabilityUpdaterFsmStage(1539),
        commSvcEpFsm(1540),
        commSvcEpFsmStage(1541),
        computeBladeFsm(1542),
        computeBladeFsmStage(1543),
        computePhysicalFsm(1544),
        computePhysicalFsmStage(1545),
        computeRackUnitFsm(1546),
        computeRackUnitFsmStage(1547),
        computeServerDiscPolicyFsm(1548),
        computeServerDiscPolicyFsmStage(1549),
        epqosDefinitionDelTaskFsm(1550),
        epqosDefinitionDelTaskFsmStage(1551),
        epqosDefinitionFsm(1552),
        epqosDefinitionFsmStage(1553),
        equipmentBeaconLedFsm(1554),
        equipmentBeaconLedFsmStage(1555),
        equipmentChassisFsm(1556),
        equipmentChassisFsmStage(1557),
        equipmentFexFsm(1558),
        equipmentFexFsmStage(1559),
        equipmentIOCardFsm(1560),
        equipmentIOCardFsmStage(1561),
        equipmentLocatorLedFsm(1562),
        equipmentLocatorLedFsmStage(1563),
        etherServerIntFIoFsm(1564),
        etherServerIntFIoFsmStage(1565),
        extpolEpFsm(1566),
        extpolEpFsmStage(1567),
        extpolRegistryFsm(1568),
        extpolRegistryFsmStage(1569),
        extvmmEpFsm(1570),
        extvmmEpFsmStage(1571),
        extvmmKeyStoreFsm(1572),
        extvmmKeyStoreFsmStage(1573),
        extvmmMasterExtKeyFsm(1574),
        extvmmMasterExtKeyFsmStage(1575),
        extvmmProviderFsm(1576),
        extvmmProviderFsmStage(1577),
        extvmmSwitchDelTaskFsm(1578),
        extvmmSwitchDelTaskFsmStage(1579),
        fabricComputeSlotEpFsm(1580),
        fabricComputeSlotEpFsmStage(1581),
        fabricEpMgrFsm(1582),
        fabricEpMgrFsmStage(1583),
        fabricLanCloudFsm(1584),
        fabricLanCloudFsmStage(1585),
        fabricSanCloudFsm(1586),
        fabricSanCloudFsmStage(1587),
        firmwareDistributableFsm(1588),
        firmwareDistributableFsmStage(1589),
        firmwareDownloaderFsm(1590),
        firmwareDownloaderFsmStage(1591),
        firmwareImageFsm(1592),
        firmwareImageFsmStage(1593),
        firmwareSystemFsm(1594),
        firmwareSystemFsmStage(1595),
        identIdentRequestFsm(1596),
        identIdentRequestFsmStage(1597),
        identMetaSystemFsm(1598),
        policyProxyMo(1599),
        licenseDownloaderFsm(1600),
        licenseDownloaderFsmStage(1601),
        licenseFileFsm(1602),
        licenseFileFsmStage(1603),
        licenseInstanceFsm(1604),
        licenseInstanceFsmStage(1605),
        lsServerFsm(1606),
        lsServerFsmStage(1607),
        mgmtBackupFsm(1608),
        policyEquipment(1609),
        mgmtControllerFsm(1610),
        mgmtControllerFsmStage(1611),
        mgmtExportPolicyFsm(1612),
        mgmtExportPolicyFsmStage(1613),
        mgmtBackupPolicyFsm(1614),
        mgmtBackupPolicyFsmStage(1615),
        mgmtCfgExportPolicyFsm(1616),
        mgmtCfgExportPolicyFsmStage(1617),
        mgmtIfFsm(1618),
        mgmtIfFsmStage(1619),
        mgmtImporterFsm(1620),
        mgmtImporterFsmStage(1621),
        nfsMountDefFsm(1622),
        smartcallhomeProfile(1623),
        smartcallhomeSource(1624),
        smartcallhomePolicy(1625),
        smartcallhomePeriodicSystemInventory(1626),
        smartcallhomeHttpProxy(1627),
        smartcallhomeTransportGateway(1628),
        pkiEpFsmStage(1629),
        policyControlEpFsm(1630),
        storageAScsiLunCtx(1631),
        storageScsiLunCtx(1632),
        policyPolicyScopeFsmStage(1633),
        storageASnapReplicaLunCtx(1634),
        storageSnapshotCtx(1635),
        storageReplicationCtx(1636),
        etherPIoFsmStage(1637),
        fcPIoFsm(1638),
        fcPIoFsmStage(1639),
        qosclassDefinitionFsm(1640),
        qosclassDefinitionFsmStage(1641),
        vnicIniGrpFcBase(1642),
        vnicIniGrpFc(1643),
        vnicIniGrpFcIf(1644),
        storageSystemFsmStage(1645),
        swAccessDomainFsm(1646),
        swAccessDomainFsmStage(1647),
        swEthLanBorderFsm(1648),
        swEthLanBorderFsmStage(1649),
        swEthMonFsm(1650),
        swEthMonFsmStage(1651),
        swFcMonFsm(1652),
        swFcMonFsmStage(1653),
        swFcSanBorderFsm(1654),
        swFcSanBorderFsmStage(1655),
        swPhysFsm(1656),
        swPhysFsmStage(1657),
        swUtilityDomainFsm(1658),
        swUtilityDomainFsmStage(1659),
        syntheticFsObjFsm(1660),
        syntheticFsObjFsmStage(1661),
        sysdebugAutoCoreFileExportTargetFsm(1662),
        sysdebugAutoCoreFileExportTargetFsmStage(1663),
        sysdebugCoreFsm(1664),
        sysdebugCoreFsmStage(1665),
        sysdebugLogControlEpFsm(1666),
        sysdebugLogControlEpFsmStage(1667),
        sysdebugManualCoreFileExportTargetFsm(1668),
        sysdebugManualCoreFileExportTargetFsmStage(1669),
        sysdebugTechSupportFsm(1670),
        sysdebugTechSupportFsmStage(1671),
        sysfileMutationFsm(1672),
        sysfileMutationFsmStage(1673),
        vmLifeCyclePolicyFsm(1674),
        vmLifeCyclePolicyFsmStage(1675),
        vnicProfileSetFsm(1676),
        vnicProfileSetFsmStage(1677),
        configMotherboardItem(1678),
        gmetaEp(1681),
        gmetaHolder(1682),
        gmetaClass(1683),
        gmetaProp(1684),
        gmetaPolicyMapHolder(1685),
        fabricSanPinTargetOperation(1686),
        fabricSanPinGroupOperation(1687),
        changeChangedObjectRef(1688),
        aaaCimcSession(1689),
        lsServerExtension(1690),
        fabricFcoeSanPcEpOperation(1691),
        fabricVnetEpSyncEp(1692),
        vnicMacHistory(1693),
        vnicWwpnHistory(1694),
        vnicWwnnHistory(1695),
        vnicIqnHistory(1696),
        vnicIpV4History(1697),
        fabricFcEstcEpOperation(1698),
        fabricFcoeEstcEpOperation(1699),
        equipmentRackFanModuleDef(1700),
        equipmentFirmwareConstraint(1701),
        equipmentVersionConstraint(1702),
        networkOperLevel(1703),
        orgSourceMask(1704),
        storageTransportableFlashModule(1705),
        policyLocalMap(1706),
        policyElement(1707),
        policyRefReq(1708),
        fabricVnetEpSyncEpFsmTask(1709),
        gmetaHolderFsmTask(1710),
        fabricVnetEpSyncEpFsm(1711),
        fabricVnetEpSyncEpFsmStage(1712),
        gmetaHolderFsm(1713),
        gmetaHolderFsmStage(1714),
        lsUuidHistory(1715),
        fabricEthEstcEpOperation(1716),
        fabricEthEstcPcOperation(1717),
        policyControlledTypeFsmTask(1718),
        fabricEthEstcPcEpOperation(1719),
        fabricEthLanPcEpOperation(1720),
        fabricLanPinGroupOperation(1721),
        fabricLanPinTargetOperation(1722),
        policyControlledTypeFsm(1723),
        policyControlledTypeFsmStage(1724),
        graphicsCard(1725),
        graphicsController(1726),
        domainFeature(1727),
        fabricFcMap(1728),
        equipmentGraphicsCardCapProvider(1729),
        equipmentGraphicsCardCapRef(1730),
        equipmentDowngradeConstraint(1731),
        domainEnvironmentFeature(1732),
        smartlicenseHolder(1733),
        smartlicenseAgent(1734),
        lstorageControllerDef(1735),
        lstorageControllerModeConfig(1736),
        smartlicenseTest(1737),
        queryresultUsage(1738),
        smartlicenseEntitlementEp(1739),
        smartlicenseEntitlement(1740),
        securityUnit(1741),
        lsbootSanCatSanImage(1742),
        lsbootLocalMediaItem(1743),
        lsbootDefaultLocalImage(1744),
        lsbootUsbFlashStorageImage(1745),
        lsbootLocalHddImage(1746),
        lsbootUsbInternalImage(1747),
        lsbootUsbExternalImage(1748),
        lsbootSanCatSanImagePath(1749),
        fabricUdldPolicy(1750),
        fabricEthLinkProfile(1751),
        smartlicenseAgentFsmTask(1752),
        smartlicenseEntitlementEpFsmTask(1753),
        smartlicenseHolderFsmTask(1754),
        smartlicenseTestFsmTask(1755),
        fabricCdpLinkPolicy(1756),
        fabricLinkPolicy(1757),
        commCimcWebService(1758),
        certRepairEpFsmStage(1759),
        changeEpFsm(1760),
        vnicVmqConReq(1761),
        vnicVmqConPolicy(1762),
        vnicVmqConPolicyRef(1763),
        vnicConReq(1764),
        vnicConPolicyRef(1765),
        vnicIpV6Addr(1766),
        vnicIpV6AddrConf(1767),
        vnicIpV6AddrExplConf(1768),
        vnicIpV6StaticAddr(1769),
        vnicIpV4MgmtPooledAddr(1770),
        vnicIpV6MgmtPooledAddr(1771),
        vnicUsnicConReq(1772),
        vnicUsnicConPolicy(1773),
        vnicUsnicConPolicyRef(1774),
        fabricEthEstcPcOperationFsmStage(1775),
        fabricEthLanEpOperationFsm(1776),
        storageControllerBase(1777),
        storageFlexFlashController(1778),
        storageLocalDiskBase(1779),
        storageFlexFlashCard(1780),
        storageFlexFlashDrive(1781),
        storageFlexFlashVirtualDrive(1782),
        lsIssues(1783),
        firmwareAutoSyncPolicy(1784),
        ipIpV4StaticTargetAddr(1785),
        fabricNetflowIPv4Addr(1786),
        fabricFlowMon(1787),
        fabricLanFlowMon(1788),
        fabricFcoeSanEpOperationFsmStage(1789),
        fabricNetflowMonSession(1790),
        fabricFlowMonSrcEp(1791),
        fabricLanFlowMonSrcEp(1792),
        fabricEthLanFlowMonSrcEp(1793),
        fabricNetflowMonSrcEp(1794),
        fabricFlowMonSrcRef(1795),
        fabricEthFlowMonSrcRef(1796),
        fabricNetflowMonSrcRef(1797),
        fabricFlowMonExporterProfile(1798),
        fabricFlowMonDefinition(1799),
        fabricFlowMonItem(1800),
        fabricFlowMonitoringCategory(1801),
        fabricEthLanFlowMonitoring(1802),
        fabricEthFlowMonLan(1803),
        smartlicenseAgentFsm(1804),
        smartlicenseAgentFsmStage(1805),
        smartlicenseEntitlementEpFsm(1806),
        smartlicenseEntitlementEpFsmStage(1807),
        smartlicenseHolderFsm(1808),
        smartlicenseHolderFsmStage(1809),
        smartlicenseTestFsm(1810),
        smartlicenseTestFsmStage(1811),
        policyPortConfig(1812),
        fabricFlowMonExporter(1813),
        fabricLanFlowMonExporter(1814),
        fabricFcPortOperation(1815),
        fabricNetflowMonExporter(1816),
        fabricNetflowMonExporterRef(1817),
        fabricNetflowTimeoutPolicy(1818),
        fabricFIPortOperationFsmTask(1819),
        fabricFIPortOperationFsm(1820),
        vnicProfileRef(1821),
        fabricEthPortOperationFsm(1822),
        fabricEthPortOperationFsmStage(1823),
        fabricFcPortOperationFsm(1824),
        fabricFcPortOperationFsmStage(1825),
        fabricFcoeSanPcOperationFsm(1826),
        fabricFcoeSanPcOperationFsmStage(1827),
        equipmentSecureController(1830),
        equipmentTpm(1831),
        mgmtIPv6IfConfig(1833),
        mgmtIPv6Addr(1834),
        mgmtIPv6IfAddr(1835),
        mgmtCimcInterface(1836),
        mgmtInbandProfile(1837),
        mgmtInterface(1838),
        mgmtProfDerivedInterface(1839),
        mgmtVnet(1840),
        extmgmtNdiscTargets(1841),
        swEthLanFlowMon(1842),
        swFlowMonitor(1843),
        swEthLanFlowMonitor(1844),
        swNetflowMonitor(1845),
        swNetflowMonitorRef(1846),
        swFlowRecordDef(1847),
        swEthLanFlowRecordDef(1848),
        swNetflowRecordDef(1849),
        swFlowMonExporter(1850),
        swEthLanFlowMonExporter(1851),
        swNetflowExporter(1852),
        swEthFlowMonSession(1853),
        swNetflowMonSession(1854),
        swNFExporterRef(1855),
        swIpRoute(1856),
        swVirtL3Intf(1857),
        swCmclan(1858),
        ippoolIpV6Pooled(1859),
        ippoolIpV6Block(1860),
        testingServiceProfileFsm(1861),
        testingServiceProfileFsmStage(1862),
        topSystemFsm(1863),
        topSystemFsmStage(1864),
        extvmmNetworkSets(1865),
        extvmmVMNetworkSets(1866),
        extvmmFabricNetwork(1867),
        extvmmFabricNetworkDefinition(1868),
        extvmmVMNetworkDefinition(1869),
        extvmmVMNetwork(1870),
        extvmmVMNDRef(1871),
        extvmmUpLinkPP(1872),
        extvmmFNDReference(1873),
        extvmmNetworkSetsFsmTask(1874),
        mgmtIPv6IfAddrFsmTask(1875),
        swEthLanFlowMonFsmTask(1876),
        extvmmNetworkSetsFsm(1877),
        extvmmNetworkSetsFsmStage(1878),
        mgmtIPv6IfAddrFsm(1879),
        mgmtIPv6IfAddrFsmStage(1880),
        topInfoSyncPolicy(1881),
        swEthLanFlowMonFsmStage(1882),
        vnicIpV6History(1883),
        equipmentInbandMgmtCap(1884),
        domainServerFeatureCont(1885),
        domainNetworkFeatureCont(1886),
        domainStorageFeatureCont(1887),
        domainEnvironmentFeatureCont(1888),
        configBackupFsmStage(1889),
        configConsumerCatalogueFsm(1890),
        configConsumerCatalogueFsmStage(1891),
        consumerInstFsm(1892),
        consumerInstFsmStage(1893),
        controllerEpFsm(1894),
        controllerEpFsmStage(1895),
        cimcvmediaActualMountList(1896),
        cimcvmediaActualMountEntry(1897),
        cimcvmediaExtMgmtRuleEntry(1898),
        cimcvmediaConfigMountEntry(1899),
        computeABoard(1900),
        computeExtBoard(1901),
        computeBoardConnector(1902),
        adaptorEthArfsProfile(1903),
        equipmentBladeAggregationCapRef(1904),
        equipmentPhysDevicesPerBoard(1905),
        mgmtBackupTriggerFsm(1906),
        mgmtBackupTriggerFsmStage(1907),
        mgmtDataExporterFsm(1908),
        mgmtDataExporterFsmStage(1909),
        mgmtDataImporterFsm(1910),
        mgmtDataImporterFsmStage(1911),
        fabricLacpPolicy(1912),
        storageMezzFlashLife(1913),
        nfsClientDefFsm(1914),
        nfsClientDefFsmStage(1915),
        nfsExportDefFsm(1916),
        nfsExportDefFsmStage(1917),
        firmwareAExcludeComponent(1918),
        firmwareExcludeChassisComponent(1919),
        firmwareDomainInfraProfile(1920),
        firmwareInfraPackConfig(1921),
        firmwareCatalogPackConfig(1922),
        firmwareDomainInfo(1923),
        mgmtASecureBoot(1924),
        mgmtCmcSecureBoot(1925),
        hcDownloadPolicy(1926),
        firmwareConnectionPolicy(1927),
        tagADef(1928),
        tagAInstance(1929),
        tagDefEp(1930),
        tagInstanceEp(1931),
        tagDef(1932),
        tagItem(1933),
        tagInstance(1934),
        tagSoftwareInst(1935),
        tagDriver(1936),
        topInfoPolicy(1937),
        sysdebugLogExportPolicyFsm(1938),
        sysdebugLogExportPolicyFsmStage(1939),
        configFilterGroup(1940),
        configFilterItem(1941),
        configPolicyUsageItem(1942),
        commDateTimeFsmTask(1943),
        mgmtCimcSecureBoot(1944),
        licenseTarget(1945),
        adaptorHostPort(1946),
        adaptorHostPortCap(1947),
        callhomeAnonymousReporting(1948),
        policyIdResolvePolicy(1949),
        firmwareConstraints(1950),
        firmwareConstraint(1951),
        fabricFcUserZone(1952),
        etherNiErrStatsHist(1953),
        equipmentUuidFeatureCap(1954),
        networkLanNeighbors(1955),
        networkANeighborEntry(1956),
        networkLanNeighborEntry(1957),
        networkSanNeighbors(1958),
        networkSanNeighborEntry(1959),
        storageFlexFlashControllerFsmTask(1960),
        storageFlexFlashControllerFsm(1961),
        storageFlexFlashControllerFsmStage(1962),
        lstorageDiskZoningConfig(1963),
        lstorageDiskZoningPolicy(1964),
        lstorageDiskZoningConfigDef(1965),
        lstorageDiskSlot(1966),
        lstorageASlot(1967),
        lstorageControllerRef(1968),
        storageArray(1969),
        storagePartition(1970),
        storageClusterIdUniverse(1971),
        storageAppliance(1972),
        storageContainer(1973),
        storageProcessor(1974),
        storageProcessorRuntime(1975),
        storageProcessorEp(1976),
        storageDiskGroup(1977),
        storageBackstore(1978),
        storageAVolume(1979),
        storageVolume(1980),
        storageALun(1981),
        storageAScsiLun(1982),
        storageScsiLun(1983),
        storageScsiDeviceDescriptor(1984),
        storageScsiLunRef(1985),
        storageVirtualDriveContainer(1986),
        storageControllerEp(1987),
        storageVirtualDriveEp(1988),
        storageVirtualDriveRef(1989),
        storageLunResourceSelectionLog(1990),
        storageDiskEp(1991),
        storageLunMaskGroup(1992),
        storageScsiLunMask(1993),
        storageIScsiInitiatorEp(1994),
        storageUsageCounters(1995),
        storageLunCounters(1996),
        storageSnapshot(1997),
        storageLunSnapshot(1998),
        storageLunReplica(1999),
        storageCloud(2000),
        storageCtrlStorageStats(2001),
        storageCtrlStorageStatsHist(2002),
        storageStorageStats(2003),
        storageStorageStatsHist(2004),
        storageEthLif(2005),
        storageIpV4StaticAddr(2006),
        storageIpV4PooledAddr(2007),
        vnicInitiatorAutoConfigPolicy(2008),
        vnicIScsiInitAutoConfigPolicy(2009),
        vnicEthConfig(2010),
        vnicIScsiConfig(2011),
        vnicIfRole(2012),
        vnicIPv6If(2013),
        vnicStorageLif(2014),
        hcAdmin(2015),
        hcReport(2016),
        hcAComponent(2017),
        policySystemEp(2018),
        policyStorageAutoConfig(2019),
        hcAStatusItem(2020),
        hcItemNote(2021),
        hcAdapterItem(2022),
        trigBaseRecurrWindow(2023),
        hcOsItem(2024),
        hcDriverItem(2025),
        lstorageArrayAutoconfigPolicy(2026),
        lstorageLogical(2027),
        lstorageArray(2028),
        lstorageProcessor(2029),
        lstorageCtrlService(2030),
        lstoragePhysicalBindingBase(2031),
        lstorageArrayBinding(2032),
        lstorageProcessorBinding(2033),
        lstorageIssues(2034),
        lstorageTargetIdentity(2035),
        lstorageBackstoreQual(2036),
        lstorageQualItem(2037),
        lstorageQualifiedPolicy(2038),
        lstorageBackstorePoolingPolicy(2039),
        lstorageRecurrWindow(2040),
        lstorageReplicationPolicy(2041),
        lstorageSnapshotPolicy(2042),
        lstorageLunReplicationPeerEp(2043),
        lstorageAbsReplicationExt(2044),
        lstorageInvictaReplicationExt(2045),
        lstorageLunReplicationPolicy(2046),
        lstorageLunSnapshotPolicy(2047),
        lstorageSvcWindow(2048),
        sysdebugTechSupportOp(2049),
        lstorageSvcSched(2050),
        lstorageReplicationConnect(2051),
        mgmtCmcSecureBootOperation(2052),
        lstorageReplicationService(2053),
        lstorageLunReplicationService(2054),
        lstorageCredentialBase(2055),
        lstorageSharedCredential(2056),
        lstorageReplicationSources(2057),
        lstorageReplicationSourceEp(2058),
        lstorageProfileBase(2059),
        lstorageProfile(2060),
        lstorageProfileDef(2061),
        lstorageProfileBindingBase(2062),
        lstorageProfileBinding(2063),
        lstorageItem(2064),
        lstorageScsiLun(2065),
        lstorageSanScsiLun(2066),
        lstorageDasScsiLun(2067),
        lstorageDiskGroupConfig(2068),
        lstorageDiskGroupConfigPolicy(2069),
        lstorageDiskGroupConfigDef(2070),
        lstorageDiskGroupQualifier(2071),
        lstorageLocalDiskRef(2072),
        lstorageLocalDiskConfigRef(2073),
        lstorageVirtualDriveDef(2074),
        lstorageMaintPolicy(2075),
        lstorageAck(2076),
        lstorageRequestCtx(2077),
        policyControlEpOp(2078),
        policyControlOp(2079),
        policyDateTimeOp(2080),
        policyCommunicationOp(2081),
        policyDnsOp(2082),
        policySecurityOp(2083),
        policyMonitoringOp(2084),
        policyFaultOp(2085),
        policyInfraFirmwareOp(2086),
        policyConfigBackupOp(2087),
        policyMEpOp(2088),
        policyDiscoveryOp(2089),
        policyPowerMgmtOp(2090),
        policyPsuOp(2091),
        policyEquipmentOp(2092),
        storageEnclosureDiskSlotEp(2093),
        storageVDMemberEp(2094),
        storageLocalDiskEp(2095),
        storageBlade(2096),
        storageDeviceBridge(2097),
        storageSasExpander(2098),
        swSubGroup(2099),
        memoryController(2100),
        vnicMonSesFcBase(2101),
        vnicMonSesFc(2102),
        vnicMonSesFcIf(2103),
        memoryNvDimmEnvStats(2104),
        policyControlEpOpFsmTask(2105),
        pkiLocale(2106),
        powerProfiledPower(2107),
        storageSvcItem(2108),
        storageSnapshotProfile(2109),
        storageReplicationProfile(2110),
        storageReplicaRestoreProfile(2111),
        storageTargetIdentity(2112),
        storageTargetNode(2113),
        vnicStorageEthLif(2114),
        dupeScope(2115),
        dupeScopeResult(2116),
        firmwareAInfraPack(2117),
        fabricDceSwSrvPcOperation(2118),
        featureChassisDef(2119),
        fabricDceSwSrvPcOperationFsm(2120),
        fabricDceSwSrvPcOperationFsmStage(2121),
        equipmentSwitchIOCard(2122),
        inventoryEp(2123),
        inventoryHolder(2124),
        inventoryInventoryEp(2125),
        inventoryGlobalEp(2126),
        inventoryDomainEp(2127),
        inventoryInventoryMoMeta(2128),
        featureFruCapProviderInstance(2129),
        featureContextEp(2130),
        featureProviderInstance(2131),
        equipmentSwitchIOCardCapProvider(2132),
        equipmentPortCap(2133),
        equipmentSystemFruCapProvider(2134),
        equipmentPowerCapDef(2135),
        equipmentImpliedStorageEnclosureDef(2136),
        equipmentStorageControllerSlotDef(2137),
        fabricAGroupReq(2138),
        equipmentSwitchTypeDef(2139),
        fabricNetGroupReq(2140),
        equipmentStorageProviderDriverLibrary(2141),
        portSubGroup(2142),
        fabricSubGroup(2143),
        fabricSwSubGroup(2144),
        fabricBaseSlotEp(2145),
        fabricBasePhEp(2146),
        fabricEnclosureSlotEp(2147),
        fabricEnclosurePhEp(2148),
        lstorageProcessorBase(2149),
        lstoragePooledBackstore(2150),
        lstoragePooledArrayVolume(2151),
        lstorageExtension(2152),
        adaptorHostVnicHwAddrCap(2153),
        adaptorNwStatsMgmtCap(2154),
        adaptorDynamicConfigCap(2155),
        osController(2156),
        osImageDefinition(2157),
        osEthBondModeActiveBackup(2158),
        osEthBondModeBalancedRR(2159),
        osEthBondModeLB(2160),
        osEthBondModeBalancedTLB(2161),
        osEthBondModeBroadcast(2162),
        osEthBondModeBalancedXOR(2163),
        osEthBondModeBalancedALB(2164),
        osMiiLinkMonitoringPolicy(2165),
        osARPLinkMonitoringPolicy(2166),
        osARPTarget(2167),
        firmwareFileUnit(2168),
        firmwareStoragePackModImpact(2169),
        firmwareABundleTypeCapProvider(2170),
        firmwarePlatformBundleTypeCapProvider(2171),
        storageDiskEnvStats(2172),
        storageDiskEnvStatsHist(2173),
        equipmentIOCardBaseFsmTask(2174),
        equipmentPsuFsmTask(2175),
        lstorageProcessorFsmTask(2176),
        osControllerFsmTask(2177),
        storagePartitionFsmTask(2178),
        storageProcessorFsmTask(2179),
        equipmentIOCardBaseFsm(2180),
        mgmtAKmipCertPolicy(2181),
        equipmentSwitchIOCardFsm(2182),
        mgmtNamedKmipCertPolicy(2183),
        equipmentPsuFsm(2184),
        equipmentPsuFsmStage(2185),
        netNetGroupPermit(2186),
        lstorageProcessorFsmStage(2187),
        osControllerFsm(2188),
        osControllerFsmStage(2189),
        storagePartitionFsm(2190),
        storagePartitionFsmStage(2191),
        storageProcessorFsm(2192),
        storageProcessorFsmStage(2193),
        fabricEquipmentEp(2194),
        fabricCartridgeSlotEp(2195),
        fabricComputeMSlotEp(2196),
        fabricCartridgePhEp(2197),
        biosVfASPMSupport(2198),
        biosVfDDR3VoltageSelection(2199),
        computePooledEnclosureComputeSlot(2200),
        computeInstanceIdQual(2201),
        apeAttribute(2202),
        firmwareActivity(2203),
        equipmentCartridgeCapProvider(2204),
        equipmentServerUnitCapProvider(2205),
        equipmentStorageLimitCap(2206),
        equipmentSharedIOModule(2207),
        adaptorUplinkPortStats(2208),
        adaptorHostScsiIf(2209),
        adaptorHostScsiLunRef(2210),
        computeSlotEntity(2211),
        computeCartridge(2212),
        inbandPolicy(2213),
        computeServerUnitFsmTask(2214),
        fabricCartridgeSlotEpFsmTask(2215),
        glDomainEp(2216),
        glAbsEp(2217),
        glIdable(2218),
        glEp(2219),
        glAbsRequest(2220),
        glRequest(2221),
        glPolicyResolutionEp(2222),
        lsbootUEFIBootParam(2223),
        glLsp(2224),
        glVnicTemplateEp(2225),
        glVnicTemplate(2226),
        glOperationEp(2227),
        glPoolEp(2228),
        glAbsResEp(2229),
        glPolicyEp(2230),
        glVxanEp(2231),
        glGlobalDefaultPolicyEp(2232),
        glSpDefEp(2233),
        glIdentCtxEp(2234),
        glTemplateEp(2235),
        glAbsOperation(2236),
        lsIdentityInfo(2237),
        networkALanNeighborEntry(2238),
        networkLldpNeighbors(2239),
        networkLldpNeighborEntry(2240),
        glIdentCtxOp(2241),
        glIdentCtxResOp(2242),
        glByMo(2243),
        glAbsPolicyOp(2244),
        glPolicyAlgorithmedOp(2245),
        glPolicyResOp(2246),
        storageADiskEp(2247),
        storageSasPhyLink(2248),
        storageSasUpLink(2249),
        storageASlot(2250),
        storageControllerRef(2251),
        storageSasPort(2252),
        sesEnclosure(2253),
        sesDiskSlotEp(2254),
        storageSasLinkDescriptor(2255),
        storageSasPortDescriptor(2256),
        storageEnclosureCap(2257),
        storageADiskSlotEp(2258),
        glRequestorEp(2259),
        glRequestor(2260),
        glRefsEp(2261),
        glBlockEp(2262),
        glBlockOp(2263),
        glInventoryEp(2264),
        glSPInvEp(2265),
        glPoolInvEp(2266),
        glPolicyInvEp(2267),
        glAbsInv(2268),
        glAbsPolicyInv(2269),
        glServiceProfile(2270),
        glPolicy(2271),
        glUsageEp(2272),
        glUsage(2273),
        glPool(2274),
        glMcastPolicy(2275),
        glAbsVnetInv(2276),
        glVlan(2277),
        glVsan(2278),
        glVnetInvHolder(2279),
        mgmtHealthAttr(2280),
        mgmtHealthStatus(2281),
        glAbsRule(2282),
        glAbsPolicyRule(2283),
        glAppendRule(2284),
        glRequestVnetEpHolder(2285),
        swPortBreakout(2286),
        swExtUtility(2287),
        swVIFRef(2288),
        swExtUtilityFsmTask(2289),
        swExtUtilityFsm(2290),
        swExtUtilityFsmStage(2291),
        networkElementOperation(2292),
        adaptorHostEthIfOperation(2293),
        adaptorHostFcIfOperation(2294),
        adaptorHostIscsiIfOperation(2295),
        adaptorExtEthIfOperation(2296),
        fdChassis(2297),
        fdPhysical(2298),
        fdRackUnit(2299),
        fdBlade(2300),
        fdOperable(2301),
        storageVsanRefIvt(2302),
        equipmentStorageSasExpanderCapRef(2303),
        vnicOutbandMgmtEp(2304),
        firmwareVicSlotConstraint(2305),
        firmwarePCHStorageConfigConstraint(2306),
        equipmentSwitchIOCardFsmTask(2307),
        adaptorHostIfConfig(2308),
        lsbootEFIShell(2309),
        storageOnboardDevice(2310),
        fabricNetGroupEp(2311),
        mgmtMgmtDbState(2312),
        equipmentServerCorrectUuidBehavior(2313),
        fabricFcZoneProfileIvt(2314),
        fabricFcUserZoneIvt(2315),
        equipmentOnboardDeviceDef(2316),
        morefImportRoot(2317),
        morefRef(2318),
        morefProp(2319),
        morefFruRef(2320),
        glRequestFsmTask(2321),
        glRequestVnetEpDomainEpFsmTask(2322),
        morefImportRootFsmTask(2323),
        morefImportRootFsm(2324),
        morefImportRootFsmStage(2325),
        vnicOutbandMgmtEpFsmTask(2326),
        equipmentHwRevisionModifier(2327),
        diagSrvCtrlOperationFsmStage(2328),
        domainProfileFsm(2329),
        domainProfileFsmStage(2330),
        equipmentInitConfigPolicy(2332),
        fabricFcZoneProfileFsm(2333),
        fabricFcZoneProfileFsmStage(2334),
        fdPhysicalFsm(2335),
        fdPhysicalFsmStage(2336),
        fdBladeFsm(2337),
        fdBladeFsmStage(2338),
        fdRackUnitFsm(2339),
        fdRackUnitFsmStage(2340),
        glIdentCtxResOpFsm(2341),
        glIdentCtxResOpFsmStage(2342),
        glRequestFsm(2343),
        glRequestFsmStage(2344),
        glRequestVnetEpDomainEpFsm(2345),
        glRequestVnetEpDomainEpFsmStage(2346),
        glRequestVnetEpFsm(2347),
        glRequestVnetEpFsmStage(2348),
        vnicOutbandMgmtEpFsm(2353),
        vnicOutbandMgmtEpFsmStage(2354),
        vnicIniGrpFcB(2355),
        vnicIniGrpFcBIf(2356),
        biosVfRedirectionAfterBIOSPOST(2357),
        vnicNetGroup(2358),
        vnicNetGroupRef(2359),
        biosVfSIOC1OptionROM(2360),
        biosVfSIOC2OptionROM(2361),
        biosVfSBMezz1OptionROM(2362),
        biosVfIOESlot1OptionROM(2363),
        biosVfIOEMezz1OptionROM(2364),
        biosVfIOESlot2OptionROM(2365),
        biosVfIOENVMe1OptionROM(2366),
        biosVfIOENVMe2OptionROM(2367),
        biosVfSBNVMe1OptionROM(2368),
        biosVfWorkloadConfiguration(2369),
        computeFabricEthMonSrcEpCont(2371),
        computeFabricFcMonSrcEpCont(2372),
        computeFabricMonSrcEp(2373),
        computeFabricEthMonSrcEp(2374),
        computeFabricFcMonSrcEp(2375),
        equipmentStorageEncCapProvider(2376),
        equipmentIOExpanderCapProvider(2377),
        equipmentCiscoOsOpenGate(2378),
        equipmentBootDeviceConstraints(2379),
        equipmentFruVariant(2380),
        equipmentStorageSasExpanderDef(2381),
        equipmentEmbeddedStorageDef(2382),
        equipmentPciSlotIdMapping(2383),
        equipmentPciSlotIdEntry(2384),
        equipmentPciSlotSubOEMIdEntry(2385),
        equipmentIOExpander(2387),
        equipmentAutoconfigPolicy(2395),
        equipmentChassisInheritPolicy(2396),
        apeMcStats(2397),
        fabricFcZoneProfile(2398),
        fabricFcEndpoint(2400),
        storageNvmeStats(2401),
        storageNvmeStatsHist(2402),
        aaaLocalMgmtCmdLog(2403),
        powerFIMember(2404),
        powerFexMember(2405),
        swFcUserZoneGroup(2406),
        swFcUserZone(2407),
        swFcEndpoint(2408),
        firmwareRackPowerCapConstraint(2414),
        firmwareActivityTrigger(2415),
        controllerHaController(2416),
        controllerPreferedVersionHolder(2417),
        controllerOperationalVersionHolder(2418),
        equipmentSystemIOControllerFsmTask(2422),
        storageEnclosureFsmTask(2423),
        storageLocalDiskFsmTask(2424),
        equipmentSystemIOControllerFsm(2427),
        equipmentSystemIOControllerFsmStage(2428),
        storageEnclosureFsm(2429),
        storageEnclosureFsmStage(2430),
        storageLocalDiskFsm(2431),
        storageLocalDiskFsmStage(2432),
        equipmentDriveSecCap(2433),
        policySourceApp(2434),
        policyContext(2435),
        policyScope(2436),
        policyPolicyDestClass(2437),
        policyRequestor(2438),
        policyADestEp(2439),
        policyDestEp(2440),
        policyDestClass(2441),
        policyChildClass(2442),
        lstorageSecurity(2443),
        lstorageDriveSecurity(2444),
        lstorageLocalConfig(2445),
        lstorageLocal(2446),
        lstorageLocalDef(2447),
        lstorageRemoteConfig(2448),
        lstorageRemote(2449),
        lstorageRemoteDef(2450),
        lstorageLogin(2451),
        diagMemoryTest(2452),
        diagLogEp(2453),
        equipmentInventoryStatus(2454),
        fabricBaseNetGroup(2455),
        fabricANetGroup(2456),
        fabricASanGroup(2457),
        fabricSanGroup(2458),
        fabricANetGroupRef(2459),
        fabricNetGroupRef(2460),
        fabricSanGroupRef(2461),
        domainChassisFeature(2462),
        domainChassisParam(2463),
        computePhysicalExtension(2464),
        computePortDiscPolicy(2465),
        storageNvmeStorage(2466),
        firmwareServicePack(2467),
        firmwareModule(2468),
        firmwareAChassisConstraint(2469),
        firmwareDualVicChassisConstraint(2470),
        firmwareSecondControllerChassisConstraint(2471),
        firmwareSecondControllerServerConstraint(2472),
        firmwareDualVicServerConstraint(2473),
        firmwareDriveSecurityConstraint(2474),
        networkLimit(2475),
        mgmtKmipCertPolicy(2476),
        mgmtDbState(2477),
        mgmtSecurity(2478),
        mgmtKmip(2479),
        equipmentComputeConnPolicy(2480),
        equipmentComputeConn(2481),
        equipmentBiosTokenOverride(2482),
        equipmentHxCap(2483),
        equipmentMgmtControllerCap(2484),
        equipmentHostMgmtControllerCap(2485),
        fabricVnetGroupPermit(2486),
        fabricVlanGroupPermit(2487),
        moKvCfgHolder(2488),
        moKvInvHolder(2489),
        moAbstractKv(2490),
        moAbstractCfgKv(2491),
        moAbstractInvKv(2492),
        moInvKv(2493),
        moKv(2494),
        moIpAddrKv(2495),
        moIpV4AddrKv(2496),
        moIpV6AddrKv(2497),
        moVnicKv(2498),
        swPortDiscover(2499),
        swEtherPort(2500),
        controllerMgmtDbCheckPol(2501),
        policyConfigError(2502),
        sysdebugDiagnosticLogRepository(2503),
        sysdebugDiagnosticLog(2504),
        computeRebootLog(2505),
        computeGraphicsCardPolicy(2506),
        computeHwChangeDiscPolicy(2507),
        domainChassisFeatureCont(2508),
        storageSsdHealthStats(2509),
        storageSsdHealthStatsHist(2510),
        policyPolicyScopeContFsmTask(2511),
        policyRequestorFsmTask(2512),
        swPortDiscoverFsmTask(2513),
        policyPolicyScopeContFsm(2514),
        policyPolicyScopeContFsmStage(2515),
        policyRequestorFsm(2516),
        policyRequestorFsmStage(2517),
        swPortDiscoverFsm(2518),
        swPortDiscoverFsmStage(2519),
        biosTokenFeatureGroup(2520),
        biosTokenParam(2521),
        biosTokenSettings(2522),
        lsbootNvme(2523),
        lsbootNvmeDevice(2524),
        lsbootNvmeDiskSsd(2525),
        lsbootNvmePciSsd(2526),
        storageMiniStorage(2527),
        storageControllerReference(2528),
        equipmentMiniStorageCapProvider(2529),
        equipmentNvmeDef(2530),
        biosVfBMEDMAMitigation(2531),
        coprocessorCard(2532),
        equipmentCoprocessorUnitCapProvider(2533),
        storageNvmeSwitch(2534),
        computeRackConnLinkPolicy(2535),
        adaptorVmmqConnDef(2536),
        lstorageSasExpanderConfigPolicy(2537),
        firmwareServerChassisConstraint(2538),
        firmwareSinglePathChassisConstraint(2539),
        firmwareConnectionManagementChassisConstraint(2540),
        firmwareWaterbaySiocServerConstraint(2541),
        firmwareChassisPackModImpact(2542),
        firmwareBackupVersionHolder(2543),
        computeHostUtilityOs(2544),
        fabricReservedVlan(2545),
        aaaLoginProfile(2546),
        capabilityASolutionStack(2547),
        capabilityAEndPointConfig(2548),
        equipmentSpeedCompatibility(2549),
        equipmentSiocCapProvider(2550),
        equipmentPcieSlotOrientation(2551),
        equipmentRackEnclosureCapProvider(2552),
        equipmentPnuosBootMode(2553),
        equipmentFlexFlashNonRemovable(2554),
        equipmentFanPresenceDef(2555),
        equipmentEmbeddedControllerConfig(2556),
        equipmentDiagFeatureSupport(2557),
        equipmentStorageNvmeSwitchCapProvider(2558),
        equipmentStorageNvmeSwitchDef(2559),
        equipmentNvmeSwitchConfig(2560),
        equipmentSlot(2561),
        equipmentSlotEp(2562),
        equipmentRackEnclosure(2563),
        mgmtLeaderEntity(2564),
        mgmtAbstractIf(2565),
        mgmtUsbNicMgmtIf(2566),
        mgmtKvmCertificate(2567),
        fabricReservedVlanFsmTask(2568),
        fabricReservedVlanFsm(2569),
        fabricReservedVlanFsmStage(2570),
        pciLink(2571),
        pciSwitch(2572),
        lstorageLunSetDiskSlot(2573),
        lstorageLunSetConfig(2574),
        adaptorFcVhbaTypeProfile(2575),
        qosclassSlowDrain(2576),
        equipmentPciSwitchCapProvider(2577),
        cloudMgmtSvc(2578),
        cloudDeviceConnectorEp(2579),
        qosclassSlowDrainFsmTask(2580),
        qosclassSlowDrainFsm(2581),
        qosclassSlowDrainFsmStage(2582),
        memoryAUnit(2583),
        memoryPersistentMemoryUnit(2584),
        memoryPersistentMemoryPolicy(2585),
        memoryPersistentMemoryGoal(2586),
        memoryPersistentMemoryANamespace(2587),
        memoryPersistentMemoryLogicalNamespace(2588),
        memoryPersistentMemoryConfiguration(2589),
        memoryPersistentMemoryConfigResult(2590),
        memoryPersistentMemoryNamespaceConfigResult(2591),
        memoryPersistentMemoryRegion(2592),
        memoryPersistentMemoryNamespace(2593),
        memoryPersistentMemorySecurity(2594),
        memoryPersistentMemoryLocalSecurity(2595),
        computeFanPolicy(2596),
        computeAdminAck(2597),
        equipmentPersistentMemoryUnitCapProvider(2598),
        adaptorAzureQosProfile(2599),
        adaptorEthGENEVEProfile(2600),
        processorExecStats(2601),
        processorCacheMemStats(2602),
        processorPCIBusStats(2603),
        processorPMUStats(2604),
        processorIOStats(2605),
        processorSecurityStats(2606),
        processorMiscStats(2607),
        computePowerSavePolicy(2608),
        fcpoolOuis(2609),
        fcpoolOui(2610),
        firmwareSecureFPGA(2611),
        pfcWatchDog(2612),
        fcpoolOuisFsmTask(2613),
        pfcWatchDogFsmTask(2614),
        fcpoolOuisFsm(2615),
        fcpoolOuisFsmStage(2616),
        pfcWatchDogFsm(2617),
        pfcWatchDogFsmStage(2618),
        biosVfPanicAndHighWatermark(2619),
        mgmtSwPersonalities(2620),
        mgmtSwPersonality(2621),
        mgmtSwPersonalitiesInventory(2622),
        mgmtSpdmCertificatePolicy(2623),
        mgmtSpdmCertificate(2624),
        mgmtSpdmCertificateInventory(2625),
        mgmtSpdmCertificateData(2626),
        computePersonality(2627),
        equipmentAutoConfigMode(2628),
        equipmentPersonality(2629),
        equipmentSpdmCertificateCap(2630),
        equipmentFanAggressiveCoolingCap(2631),
        adaptorPTP(2632),
        equipmentBiosPasswordReset(2633),
        adaptorSriovHpnConnDef(2634),
        adaptorQinQVlan(2635),
        vnicSriovHpnConReq(2636),
        vnicSriovHpnConPolicy(2637),
        vnicSriovHpnConPolicyRef(2638),
        computePowerExtendedPolicy(2639),
        computeModularChassisFanPolicy(2640),
        equipmentChassisTypeCap(2641),
        equipmentRetimerCapProvider(2642),
        equipmentUbmCapProvider(2643),
        equipmentCpldCapProvider(2644),
        equipmentCrossFabricModuleCapProvider(2645),
        equipmentFanModulesDef(2646),
        equipmentIOCardAdaptorConnDef(2647),
        equipmentFruComponent(2648),
        equipmentCrossFabricModule(2649),
        equipmentCrossFabricModuleStats(2650),
        equipmentCrossFabricModuleStatsHist(2651),
        equipmentIOCardFanModuleStats(2652),
        equipmentIOCardFanModuleStatsHist(2653),
        equipmentIOCardFanStats(2654),
        equipmentIOCardFanStatsHist(2655),
        equipmentCrossFabricModuleFanStats(2656),
        equipmentCrossFabricModuleFanStatsHist(2657),
        etherMacSecSession(2658),
        lstorageHybridDriveSlotConfig(2659),
        policyPowerExtended(2660),
        policyModularChassisFan(2661),
        policyPowerSave(2662),
        mgmtHybridSlot(2663),
        computeDataSanitize(2664),
        computeSanitizeComponent(2665),
        equipmentFirmwareUpdateRestriction(2666),
        equipmentPcieConnectorCapProvider(2667),
        equipmentPcieNodeCapProvider(2668),
        equipmentIntelAmcCapProvider(2669),
        equipmentDataSanitize(2670),
        equipmentXFMTypeDef(2671),
        equipmentDriveSupportedStripSizes(2672),
        equipmentPcieNode(2673),
        equipmentPcieConnectorUnit(2674),
        etherMacSecTxStats(2675),
        etherMacSecTxStatsHist(2676),
        etherMacSecRxStats(2677),
        etherMacSecRxStatsHist(2678),
        fabricRemoteConfig(2679),
        fabricRMonEp(2680),
        fabricMonOriginSVI(2681),
        fabricMonOriginIP(2682),
        fabricMacSec(2683),
        fabricMacSecPolicy(2684),
        fabricMacSecKeyChain(2685),
        fabricAbsSecureKey(2686),
        fabricMacSecKey(2687),
        fabricLifeTime(2688),
        fabricMacSecIfConfig(2689),
        fabricAbsEapol(2690),
        fabricMacSecEapol(2691),
        fabricAbsEthLanEp(2692),
        firmwarePcieNodeConstraint(2693),
        adaptorEthPortPfcStats(2694),
        adaptorEthPortPfcStatsHist(2695),
        swRMonEp(2696),
        swRMonSVI(2697),
        swMonIpRoute(2698),
        swRemoteConfig(2699),
        swRMonEpFsmTask(2700),
        swRMonEpFsm(2701),
        swRMonEpFsmStage(2702),
        securityEp(2703),
        securityEncryptionEp(2704),
        securityAEncryption(2705),
        securityAesEncryption(2706),
        securityDeployedAesEncryption(2707),
        securityEncryptionEpFsmTask(2708),
        securityEncryptionEpFsm(2709),
        securityEncryptionEpFsmStage(2710),
        biosVfPreBootDMAProtection(2711),
        equipmentFanPolicyMaxCooling(2712),
        adaptorTemperature(2713),
        powerPackagePowerLimit(2714),
        vnicIPv6IscsiAddrConf(2715),
        vnicIPv6IscsiAddr(2716),
        vnicIPv6PooledIscsiAddr(2717),
        vnicIPv6Dhcp(2718),
        vnicIPv6IScsiStaticTargetIf(2719),
        vnicAbsIScsiStaticTargetIf(2720),
        equipmentMacSecCap(2721),
        firmwareDualKnoxControllerConstraint(2722),
        commFabricInterconnectAuditLogs(2723)
    }

CucsMoModificationStatus ::= TEXTUAL-CONVENTION
    STATUS        current
    DESCRIPTION
        ""
    SYNTAX        BITS
    {
        created(1),
        modified(2),
        deleted(3),
        removed(4)
    }

CucsMoSrcDme ::= TEXTUAL-CONVENTION
    STATUS        current
    DESCRIPTION
        ""
    SYNTAX        INTEGER
    {
        unknown(0),
        serviceReg(1),
        mgmtController(2),
        policyMgr(3),
        resourceMgr(4),
        identifierMgr(5),
        operationMgr(6),
        statsMgr(7),
        centralMgr(8),
        serverMgr(9)
    }

CucsMoVnicKvType ::= TEXTUAL-CONVENTION
    STATUS        current
    DESCRIPTION
        ""
    SYNTAX        INTEGER
    {
        keyValue(0),
        ipv4Addr(1),
        ipv6Addr(2),
        vlan(3),
        vnic(4)
    }

CucsMorefAdminState ::= TEXTUAL-CONVENTION
    STATUS        current
    DESCRIPTION
        ""
    SYNTAX        INTEGER
    {
        unapplied(1),
        applied(2),
        deleted(3)
    }

CucsMorefImportRootFsmCurrentFsm ::= TEXTUAL-CONVENTION
    STATUS        current
    DESCRIPTION
        ""
    SYNTAX        INTEGER
    {
        nop(0),
        applyMoRefs(2012)
    }

CucsMorefImportRootFsmStageName ::= TEXTUAL-CONVENTION
    STATUS        current
    DESCRIPTION
        ""
    SYNTAX        INTEGER
    {
        nop(0),
        applyMoRefsBegin(2012),
        applyMoRefsApplyMoProps(2013),
        applyMoRefsDeleteAllMoRefs(2014),
        applyMoRefsFail(2015),
        applyMoRefsSuccess(2016)
    }

CucsMorefImportRootFsmTaskItem ::= TEXTUAL-CONVENTION
    STATUS        current
    DESCRIPTION
        ""
    SYNTAX        INTEGER
    {
        nop(0),
        applyMoRefs(2012)
    }

CucsNetworkConfigIssues ::= TEXTUAL-CONVENTION
    STATUS        current
    DESCRIPTION
        ""
    SYNTAX        BITS
    {
        conflictingVlanAccess(0),
        namedVlanInaccessible(1),
        permitUnresolved(2),
        pinningInvalid(3),
        switchVirtualIfCapacity(4),
        unsupportedMulticastPolicy(5),
        vlanPortCapacity(6),
        networkFeatureCapabilityMismatch(7),
        unsupportedUsnicConfig(8),
        unsupportedVmqConfig(9),
        unsupportedDynamicVnicConfig(10)
    }

CucsNetworkConnectionType ::= TEXTUAL-CONVENTION
    STATUS        current
    DESCRIPTION
        ""
    SYNTAX        BITS
    {
        lan(0),
        san(1),
        ipc(2)
    }

CucsNetworkCountStatus ::= TEXTUAL-CONVENTION
    STATUS        current
    DESCRIPTION
        ""
    SYNTAX        INTEGER
    {
        withinLimit(0),
        aboveLimit(1),
        aboveThresholdLimit(2)
    }

CucsNetworkElementOperability ::= TEXTUAL-CONVENTION
    STATUS        current
    DESCRIPTION
        ""
    SYNTAX        INTEGER
    {
        unknown(0),
        operable(1),
        inoperable(2),
        removed(3),
        deprecated(4)
    }

CucsNetworkElementFsmCurrentFsm ::= TEXTUAL-CONVENTION
    STATUS        current
    DESCRIPTION
        ""
    SYNTAX        INTEGER
    {
        nop(0),
        updateElement(35)
    }

CucsNetworkElementFsmStageName ::= TEXTUAL-CONVENTION
    STATUS        current
    DESCRIPTION
        ""
    SYNTAX        INTEGER
    {
        nop(0),
        updateElementBegin(35),
        updateElementUpdateAttr(36),
        updateElementFail(119),
        updateElementSuccess(120)
    }

CucsNetworkElementFsmTaskFlags ::= TEXTUAL-CONVENTION
    STATUS        current
    DESCRIPTION
        ""
    SYNTAX        BITS
    {
        samDmeNetworkElementUpdateElementPropogateSettings(0)
    }

CucsNetworkElementFsmTaskItem ::= TEXTUAL-CONVENTION
    STATUS        current
    DESCRIPTION
        ""
    SYNTAX        INTEGER
    {
        nop(0),
        updateElement(35)
    }

CucsNetworkEvacState ::= TEXTUAL-CONVENTION
    STATUS        current
    DESCRIPTION
        ""
    SYNTAX        INTEGER
    {
        drain(0),
        fill(1),
        unknown(2)
    }

CucsNetworkIfStatsType ::= TEXTUAL-CONVENTION
    STATUS        current
    DESCRIPTION
        ""
    SYNTAX        INTEGER
    {
        generic(0),
        broadcast(1),
        multicast(2),
        unicast(3),
        total(4)
    }

CucsNetworkIfStatsUnits ::= TEXTUAL-CONVENTION
    STATUS        current
    DESCRIPTION
        ""
    SYNTAX        INTEGER
    {
        raw(0),
        packets(1),
        octets(2)
    }

CucsNetworkIfStatus ::= TEXTUAL-CONVENTION
    STATUS        current
    DESCRIPTION
        ""
    SYNTAX        INTEGER
    {
        unknown(0),
        down(1),
        up(2)
    }

CucsNetworkInventoryStatus ::= TEXTUAL-CONVENTION
    STATUS        current
    DESCRIPTION
        ""
    SYNTAX        BITS
    {
        switchFru(0),
        vlanPortCount(1),
        cardInventory(2),
        ethPortInventory(3),
        fcPortInventory(4),
        mgmtPortInventory(5),
        ethPcInventory(6),
        fcPcInventory(7),
        switchInventory(8),
        xcvrInventory(9),
        remoteEthPortInventory(10),
        vlanCompGrpInventory(11),
        macsecStateInventory(12)
    }

CucsNetworkLimitType ::= TEXTUAL-CONVENTION
    STATUS        current
    DESCRIPTION
        ""
    SYNTAX        INTEGER
    {
        unicastMac(0),
        multicastMac(1),
        pvLifVlanMbr(2),
        pvSystem(3),
        igmpGroup(4),
        iftmcPv(5),
        dvif(6),
        unicastMacLimit(7)
    }

CucsNetworkLocale ::= TEXTUAL-CONVENTION
    STATUS        current
    DESCRIPTION
        ""
    SYNTAX        BITS
    {
        server(0),
        chassis(1),
        internal(2),
        external(3)
    }

CucsNetworkNetworkAdminState ::= TEXTUAL-CONVENTION
    STATUS        current
    DESCRIPTION
        ""
    SYNTAX        INTEGER
    {
        enabled(1),
        disabled(2)
    }

CucsNetworkOperLevelNumPrimaryVlansStatus ::= TEXTUAL-CONVENTION
    STATUS        current
    DESCRIPTION
        ""
    SYNTAX        INTEGER
    {
        withinLimit(0),
        aboveLimit(1)
    }

CucsNetworkOperLevelPrimaryVlanCountStatus ::= TEXTUAL-CONVENTION
    STATUS        current
    DESCRIPTION
        ""
    SYNTAX        INTEGER
    {
        withinLimit(0),
        aboveLimit(1)
    }

CucsNetworkPhysEpIfType ::= TEXTUAL-CONVENTION
    STATUS        current
    DESCRIPTION
        ""
    SYNTAX        INTEGER
    {
        unknown(0),
        physical(1),
        aggregation(2),
        virtual(3)
    }

CucsNetworkPortOperState ::= TEXTUAL-CONVENTION
    STATUS        current
    DESCRIPTION
        ""
    SYNTAX        INTEGER
    {
        indeterminate(0),
        up(1),
        adminDown(2),
        linkDown(3),
        failed(4),
        noLicense(5),
        linkUp(6),
        hardwareFailure(7),
        softwareFailure(8),
        errorDisabled(9),
        sfpNotPresent(10),
        udldAggrDown(11),
        down(12)
    }

CucsNetworkPortRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsNetworkPortType ::= TEXTUAL-CONVENTION
    STATUS        current
    DESCRIPTION
        ""
    SYNTAX        INTEGER
    {
        unknown(0),
        physical(1),
        aggregation(2),
        virtual(3)
    }

CucsNetworkSensorThresholdStatus ::= TEXTUAL-CONVENTION
    STATUS        current
    DESCRIPTION
        ""
    SYNTAX        INTEGER
    {
        unknown(0),
        ok(1),
        upperNonRecoverable(2),
        upperCritical(3),
        upperNonCritical(4),
        lowerNonCritical(5),
        lowerCritical(6),
        lowerNonRecoverable(7),
        notSupported(100)
    }

CucsNetworkSide ::= TEXTUAL-CONVENTION
    STATUS        current
    DESCRIPTION
        ""
    SYNTAX        INTEGER
    {
        left(0),
        right(1)
    }

CucsNetworkSwitchId ::= TEXTUAL-CONVENTION
    STATUS        current
    DESCRIPTION
        ""
    SYNTAX        INTEGER
    {
        none(0),
        a(1),
        b(2),
        mgmt(3)
    }

CucsNetworkTransport ::= TEXTUAL-CONVENTION
    STATUS        current
    DESCRIPTION
        ""
    SYNTAX        BITS
    {
        ether(0),
        dce(1),
        fc(2)
    }

CucsNetworkVlanCountStatus ::= TEXTUAL-CONVENTION
    STATUS        current
    DESCRIPTION
        ""
    SYNTAX        INTEGER
    {
        withinLimit(0),
        aboveLimit(1)
    }

CucsNetworkVnetEpIfType ::= TEXTUAL-CONVENTION
    STATUS        current
    DESCRIPTION
        ""
    SYNTAX        INTEGER
    {
        unknown(0),
        physical(1),
        aggregation(2),
        virtual(3)
    }

CucsNfsClientAdminState ::= TEXTUAL-CONVENTION
    STATUS        current
    DESCRIPTION
        ""
    SYNTAX        INTEGER
    {
        none(0),
        add(1),
        remove(2)
    }

CucsNfsClientConfigState ::= TEXTUAL-CONVENTION
    STATUS        current
    DESCRIPTION
        ""
    SYNTAX        INTEGER
    {
        unregistered(0),
        registered(1),
        configured(2),
        failed(3)
    }

CucsNfsClientDefFsmCurrentFsm ::= TEXTUAL-CONVENTION
    STATUS        current
    DESCRIPTION
        ""
    SYNTAX        INTEGER
    {
        nop(0),
        addConfig(187),
        deleteConfig(190)
    }

CucsNfsClientDefFsmStageName ::= TEXTUAL-CONVENTION
    STATUS        current
    DESCRIPTION
        ""
    SYNTAX        INTEGER
    {
        nop(0),
        addConfigBegin(187),
        addConfigInternalAdd(189),
        deleteConfigBegin(190),
        deleteConfigInternalDelete(191),
        addConfigFail(208),
        addConfigSuccess(209),
        deleteConfigFail(210),
        deleteConfigSuccess(211),
        addConfigPeerAdd(336),
        deleteConfigPeerDelete(337)
    }

CucsNfsClientDefFsmTaskItem ::= TEXTUAL-CONVENTION
    STATUS        current
    DESCRIPTION
        ""
    SYNTAX        INTEGER
    {
        nop(0),
        addConfig(187),
        deleteConfig(190)
    }

CucsNfsClusterConfigState ::= TEXTUAL-CONVENTION
    STATUS        current
    DESCRIPTION
        ""
    SYNTAX        BITS
    {
        a(0),
        b(1)
    }

CucsNfsDefAdminState ::= TEXTUAL-CONVENTION
    STATUS        current
    DESCRIPTION
        ""
    SYNTAX        INTEGER
    {
        disabled(0),
        enabled(1),
        suspended(2)
    }

CucsNfsExportConfigState ::= TEXTUAL-CONVENTION
    STATUS        current
    DESCRIPTION
        ""
    SYNTAX        INTEGER
    {
        none(0),
        added(1),
        remove(2)
    }

CucsNfsExportDefFsmCurrentFsm ::= TEXTUAL-CONVENTION
    STATUS        current
    DESCRIPTION
        ""
    SYNTAX        INTEGER
    {
        nop(0),
        imageSync(338),
        addRepo(340)
    }

CucsNfsExportDefFsmStageName ::= TEXTUAL-CONVENTION
    STATUS        current
    DESCRIPTION
        ""
    SYNTAX        INTEGER
    {
        nop(0),
        imageSyncBegin(338),
        imageSyncLocal(339),
        addRepoBegin(340),
        addRepoLocal(341),
        addRepoFail(344),
        addRepoSuccess(345),
        imageSyncFail(346),
        imageSyncSuccess(347)
    }

CucsNfsExportDefFsmTaskItem ::= TEXTUAL-CONVENTION
    STATUS        current
    DESCRIPTION
        ""
    SYNTAX        INTEGER
    {
        nop(0),
        imageSync(338),
        addRepo(340)
    }

CucsNfsExportMonitorState ::= TEXTUAL-CONVENTION
    STATUS        current
    DESCRIPTION
        ""
    SYNTAX        INTEGER
    {
        unregistered(0),
        monitoring(1),
        monitored(2),
        failed(3)
    }

CucsNfsExportOperState ::= TEXTUAL-CONVENTION
    STATUS        current
    DESCRIPTION
        ""
    SYNTAX        INTEGER
    {
        unregistered(0),
        syncing(1),
        synced(2),
        failed(3)
    }

CucsNfsMntAdminState ::= TEXTUAL-CONVENTION
    STATUS        current
    DESCRIPTION
        ""
    SYNTAX        INTEGER
    {
        none(0),
        unmount(1),
        mount(2),
        remount(3)
    }

CucsNfsMntOperState ::= TEXTUAL-CONVENTION
    STATUS        current
    DESCRIPTION
        ""
    SYNTAX        INTEGER
    {
        unmounted(0),
        mounted(1)
    }

CucsNfsMountDefFsmCurrentFsm ::= TEXTUAL-CONVENTION
    STATUS        current
    DESCRIPTION
        ""
    SYNTAX        INTEGER
    {
        nop(0),
        reportNfsMountSuspend(1241)
    }

CucsNfsMountDefFsmStageName ::= TEXTUAL-CONVENTION
    STATUS        current
    DESCRIPTION
        ""
    SYNTAX        INTEGER
    {
        nop(0),
        reportNfsMountSuspendBegin(1241),
        reportNfsMountSuspendReport(1242),
        reportNfsMountSuspendFail(1415),
        reportNfsMountSuspendSuccess(1416)
    }

CucsNfsMountDefFsmTaskItem ::= TEXTUAL-CONVENTION
    STATUS        current
    DESCRIPTION
        ""
    SYNTAX        INTEGER
    {
        nop(0),
        reportNfsMountSuspend(1241)
    }

CucsNfsMountInstFsmCurrentFsm ::= TEXTUAL-CONVENTION
    STATUS        current
    DESCRIPTION
        ""
    SYNTAX        INTEGER
    {
        nop(0),
        mount(1233),
        unmount(1238)
    }

CucsNfsMountInstFsmStageName ::= TEXTUAL-CONVENTION
    STATUS        current
    DESCRIPTION
        ""
    SYNTAX        INTEGER
    {
        nop(0),
        mountBegin(1233),
        mountRegisterClient(1234),
        mountVerifyRegistration(1235),
        mountMountLocal(1236),
        mountMountPeer(1237),
        unmountBegin(1238),
        unmountUnmountLocal(1239),
        unmountUnmountPeer(1240),
        mountFail(1417),
        mountSuccess(1418),
        unmountFail(1419),
        unmountSuccess(1420)
    }

CucsNfsMountInstFsmTaskItem ::= TEXTUAL-CONVENTION
    STATUS        current
    DESCRIPTION
        ""
    SYNTAX        INTEGER
    {
        nop(0),
        mount(1233),
        unmount(1238)
    }

CucsNfsPurpose ::= TEXTUAL-CONVENTION
    STATUS        current
    DESCRIPTION
        ""
    SYNTAX        INTEGER
    {
        image(0),
        backup(1)
    }

CucsNwctrlAdminState ::= TEXTUAL-CONVENTION
    STATUS        current
    DESCRIPTION
        ""
    SYNTAX        INTEGER
    {
        disabled(0),
        enabled(1)
    }

CucsNwctrlLinkFailAction ::= TEXTUAL-CONVENTION
    STATUS        current
    DESCRIPTION
        ""
    SYNTAX        INTEGER
    {
        linkDown(0),
        warning(1)
    }

CucsNwctrlLldpAdminStateBitmask ::= TEXTUAL-CONVENTION
    STATUS        current
    DESCRIPTION
        ""
    SYNTAX        BITS
    {
        transmit(0),
        receive(1)
    }

CucsNwctrlRegistrationMode ::= TEXTUAL-CONVENTION
    STATUS        current
    DESCRIPTION
        ""
    SYNTAX        INTEGER
    {
        onlyNativeVlan(0),
        allHostVlans(1)
    }

CucsObserveObservedFsmCurrentFsm ::= TEXTUAL-CONVENTION
    STATUS        current
    DESCRIPTION
        ""
    SYNTAX        INTEGER
    {
        nop(0),
        resolvePolicyFsm(1341),
        resolveResourceFsm(1343),
        resolveVMFsm(1345),
        resolveControllerFsm(1347)
    }

CucsObserveObservedFsmStageName ::= TEXTUAL-CONVENTION
    STATUS        current
    DESCRIPTION
        ""
    SYNTAX        INTEGER
    {
        nop(0),
        resolvePolicyFsmBegin(1341),
        resolvePolicyFsmExecute(1342),
        resolveResourceFsmBegin(1343),
        resolveResourceFsmExecute(1344),
        resolveVMFsmBegin(1345),
        resolveVMFsmExecute(1346),
        resolveControllerFsmBegin(1347),
        resolveControllerFsmExecute(1348),
        resolveControllerFsmFail(1421),
        resolveControllerFsmSuccess(1422),
        resolvePolicyFsmFail(1423),
        resolvePolicyFsmSuccess(1424),
        resolveResourceFsmFail(1425),
        resolveResourceFsmSuccess(1426),
        resolveVMFsmFail(1427),
        resolveVMFsmSuccess(1428)
    }

CucsObserveObservedFsmTaskItem ::= TEXTUAL-CONVENTION
    STATUS        current
    DESCRIPTION
        ""
    SYNTAX        INTEGER
    {
        nop(0),
        resolvePolicyFsm(1341),
        resolveResourceFsm(1343),
        resolveVMFsm(1345),
        resolveControllerFsm(1347)
    }

CucsOrgDeleteSource ::= TEXTUAL-CONVENTION
    STATUS        current
    DESCRIPTION
        ""
    SYNTAX        INTEGER
    {
        notDeleting(0),
        resourceMgr(1),
        policyMgr(2)
    }

CucsOrgLevel ::= TEXTUAL-CONVENTION
    STATUS        current
    DESCRIPTION
        ""
    SYNTAX        INTEGER
    {
        root(0),
        n1(1),
        n2(2),
        n3(3),
        n4(4),
        n5(5)
    }

CucsOrgOrgFsmCurrentFsm ::= TEXTUAL-CONVENTION
    STATUS        current
    DESCRIPTION
        ""
    SYNTAX        INTEGER
    {
        nop(0),
        configure(5),
        configurePeer(291)
    }

CucsOrgOrgFsmStageName ::= TEXTUAL-CONVENTION
    STATUS        current
    DESCRIPTION
        ""
    SYNTAX        INTEGER
    {
        nop(0),
        configureBegin(5),
        configureConfig(6),
        configureFail(129),
        configureSuccess(130),
        configurePeerBegin(291),
        configurePeerConfig(292),
        configurePeerFail(301),
        configurePeerSuccess(302)
    }

CucsOrgOrgFsmTaskItem ::= TEXTUAL-CONVENTION
    STATUS        current
    DESCRIPTION
        ""
    SYNTAX        INTEGER
    {
        nop(0),
        configure(5),
        configurePeer(291)
    }

CucsOrgSrcMask ::= TEXTUAL-CONVENTION
    STATUS        current
    DESCRIPTION
        ""
    SYNTAX        BITS
    {
        policyMgr(0),
        managedEndpoint(1)
    }

CucsOsCarrierQueryMethod ::= TEXTUAL-CONVENTION
    STATUS        current
    DESCRIPTION
        ""
    SYNTAX        INTEGER
    {
        netif(0),
        ethtool(1)
    }

CucsOsControllerFsmCurrentFsm ::= TEXTUAL-CONVENTION
    STATUS        current
    DESCRIPTION
        ""
    SYNTAX        INTEGER
    {
        nop(0),
        deployOS(1772)
    }

CucsOsControllerFsmStageName ::= TEXTUAL-CONVENTION
    STATUS        current
    DESCRIPTION
        ""
    SYNTAX        INTEGER
    {
        nop(0),
        deployOSBegin(1772),
        deployOSDownloadImages(1773),
        deployOSCopyRemote(1774),
        deployOSHostBootForUpgrade(1775),
        deployOSWaitForSMEConnection(1776),
        deployOSHostBmcPreConfigLocal(1777),
        deployOSHostBmcPreConfigPeer(1778),
        deployOSHostSetupVmediaLocal(1779),
        deployOSHostSetupVmediaPeer(1780),
        deployOSHostClearOsInstallStatus(1781),
        deployOSHostSolRedirectEnable(1782),
        deployOSHostSerialDebugConnect(1783),
        deployOSHostBoot(1784),
        deployOSHostBootWait(1785),
        deployOSHostBiosPostCompletion(1786),
        deployOSHostReadSmbios(1787),
        deployOSHostPreInstall(1788),
        deployOSHostPostInstall(1789),
        deployOSHostPreFirstBoot(1790),
        deployOSHostPostFirstBoot(1791),
        deployOSHostPostUpgrade(1792),
        deployOSHostTeardownVmediaLocal(1793),
        deployOSHostTeardownVmediaPeer(1794),
        deployOSHostSerialDebugDisconnect(1795),
        deployOSHostSolRedirectDisable(1796),
        deployOSDeleteCurlDownloadedImages(1797),
        deployOSSuccess(1798),
        deployOSFail(1799)
    }

CucsOsControllerFsmTaskFlags ::= TEXTUAL-CONVENTION
    STATUS        current
    DESCRIPTION
        ""
    SYNTAX        BITS
    {
        samDmeOsControllerDeployOSOsInstall(30),
        samDmeOsControllerDeployOSOsUpgrade(31)
    }

CucsOsControllerFsmTaskItem ::= TEXTUAL-CONVENTION
    STATUS        current
    DESCRIPTION
        ""
    SYNTAX        INTEGER
    {
        nop(0),
        deployOS(1772)
    }

CucsOsDeployState ::= TEXTUAL-CONVENTION
    STATUS        current
    DESCRIPTION
        ""
    SYNTAX        INTEGER
    {
        undefined(0),
        inProgress(1),
        complete(2),
        retry(3),
        failed(4),
        throttled(5),
        undeployed(6)
    }

CucsOsEthBondModeActiveBackupType ::= TEXTUAL-CONVENTION
    STATUS        current
    DESCRIPTION
        ""
    SYNTAX        INTEGER
    {
        activePassive(0),
        activeActive(1)
    }

CucsOsEthBondModeBalancedRRType ::= TEXTUAL-CONVENTION
    STATUS        current
    DESCRIPTION
        ""
    SYNTAX        INTEGER
    {
        activePassive(0),
        activeActive(1)
    }

CucsOsEthBondModeBroadcastType ::= TEXTUAL-CONVENTION
    STATUS        current
    DESCRIPTION
        ""
    SYNTAX        INTEGER
    {
        activePassive(0),
        activeActive(1)
    }

CucsOsEthBondModeLBType ::= TEXTUAL-CONVENTION
    STATUS        current
    DESCRIPTION
        ""
    SYNTAX        INTEGER
    {
        activePassive(0),
        activeActive(1)
    }

CucsOsEthBondModeLBXmitHashType ::= TEXTUAL-CONVENTION
    STATUS        current
    DESCRIPTION
        ""
    SYNTAX        INTEGER
    {
        layer2(0),
        layer2Plus3(1),
        layer3Plus4(2),
        encap2Plus3(3),
        encap3Plus4(4)
    }

CucsOsLBType ::= TEXTUAL-CONVENTION
    STATUS        current
    DESCRIPTION
        ""
    SYNTAX        INTEGER
    {
        xmitOnly(0),
        receiveXmit(1)
    }

CucsOsMacFailOverPolicy ::= TEXTUAL-CONVENTION
    STATUS        current
    DESCRIPTION
        ""
    SYNTAX        INTEGER
    {
        none(0),
        active(1),
        follow(2)
    }

CucsOsOsType ::= TEXTUAL-CONVENTION
    STATUS        current
    DESCRIPTION
        ""
    SYNTAX        INTEGER
    {
        unspecified(0),
        pnuOS(1),
        linux(2),
        windows(3),
        solaris(4),
        vmwareESX(5)
    }

CucsOsPrimaryReselection ::= TEXTUAL-CONVENTION
    STATUS        current
    DESCRIPTION
        ""
    SYNTAX        INTEGER
    {
        always(0),
        better(1),
        failure(2)
    }

CucsPciEquipSlotId ::= TEXTUAL-CONVENTION
    STATUS        current
    DESCRIPTION
        ""
    SYNTAX        Gauge32 (1..5000)

CucsPfcWatchDogWdAdminState ::= TEXTUAL-CONVENTION
    STATUS        current
    DESCRIPTION
        ""
    SYNTAX        INTEGER
    {
        off(0),
        on(1)
    }

CucsPfcWatchDogFsmCurrentFsm ::= TEXTUAL-CONVENTION
    STATUS        current
    DESCRIPTION
        ""
    SYNTAX        INTEGER
    {
        nop(0),
        configPfcWatchDog(2388)
    }

CucsPfcWatchDogFsmStageName ::= TEXTUAL-CONVENTION
    STATUS        current
    DESCRIPTION
        ""
    SYNTAX        INTEGER
    {
        nop(0),
        configPfcWatchDogBegin(2388),
        configPfcWatchDogSetPeer(2389),
        configPfcWatchDogSetLocal(2390),
        configPfcWatchDogFail(2397),
        configPfcWatchDogSuccess(2398)
    }

CucsPfcWatchDogFsmTaskItem ::= TEXTUAL-CONVENTION
    STATUS        current
    DESCRIPTION
        ""
    SYNTAX        INTEGER
    {
        nop(0),
        configPfcWatchDog(2388)
    }

CucsPkiCertStatus ::= TEXTUAL-CONVENTION
    STATUS        current
    DESCRIPTION
        ""
    SYNTAX        INTEGER
    {
        valid(0),
        expired(1),
        revoked(2),
        notYetValid(3),
        emptyCert(4),
        unknown(5),
        failedToVerifyWithTp(6),
        failedToVerifyWithPrivateKey(7),
        certChainTooLong(8),
        selfSignedCertificate(9)
    }

CucsPkiEpFsmCurrentFsm ::= TEXTUAL-CONVENTION
    STATUS        current
    DESCRIPTION
        ""
    SYNTAX        INTEGER
    {
        nop(0),
        updateEp(206)
    }

CucsPkiEpFsmStageName ::= TEXTUAL-CONVENTION
    STATUS        current
    DESCRIPTION
        ""
    SYNTAX        INTEGER
    {
        nop(0),
        updateEpBegin(206),
        updateEpSetKeyRingLocal(207),
        updateEpSetKeyRingPeer(208),
        updateEpSetCertConfLocal(389),
        updateEpFail(428),
        updateEpSuccess(429),
        updateEpPostSetKeyRingLocal(1491),
        updateEpPostSetKeyRingPeer(1492)
    }

CucsPkiEpFsmTaskItem ::= TEXTUAL-CONVENTION
    STATUS        current
    DESCRIPTION
        ""
    SYNTAX        INTEGER
    {
        nop(0),
        updateEp(206)
    }

CucsPkiKeyringState ::= TEXTUAL-CONVENTION
    STATUS        current
    DESCRIPTION
        ""
    SYNTAX        INTEGER
    {
        started(1),
        created(2),
        reqCreated(3),
        tpSet(4),
        completed(5)
    }

CucsPkiModulus ::= TEXTUAL-CONVENTION
    STATUS        current
    DESCRIPTION
        ""
    SYNTAX        INTEGER
    {
        modinvalid(0),
        mod512(512),
        mod1024(1024),
        mod1536(1536),
        mod2048(2048),
        mod2560(2560),
        mod3072(3072),
        mod3584(3584),
        mod4096(4096)
    }

CucsPolicyAdminState ::= TEXTUAL-CONVENTION
    STATUS        current
    DESCRIPTION
        ""
    SYNTAX        INTEGER
    {
        disabled(0),
        enabled(1)
    }

CucsPolicyCleanupMode ::= TEXTUAL-CONVENTION
    STATUS        current
    DESCRIPTION
        ""
    SYNTAX        INTEGER
    {
        localizeGlobal(0),
        deepRemoveGlobal(1)
    }

CucsPolicyControlSource ::= TEXTUAL-CONVENTION
    STATUS        current
    DESCRIPTION
        ""
    SYNTAX        INTEGER
    {
        local(0),
        policy(1),
        pendingPolicy(2),
        unspecified(3)
    }

CucsPolicyControlEpFsmCurrentFsm ::= TEXTUAL-CONVENTION
    STATUS        current
    DESCRIPTION
        ""
    SYNTAX        INTEGER
    {
        nop(0),
        operate(1199)
    }

CucsPolicyControlEpFsmStageName ::= TEXTUAL-CONVENTION
    STATUS        current
    DESCRIPTION
        ""
    SYNTAX        INTEGER
    {
        nop(0),
        operateBegin(1199),
        operateResolve(1200),
        operateFail(1429),
        operateSuccess(1430)
    }

CucsPolicyControlEpFsmTaskItem ::= TEXTUAL-CONVENTION
    STATUS        current
    DESCRIPTION
        ""
    SYNTAX        INTEGER
    {
        nop(0),
        operate(1199)
    }

CucsPolicyControlEpOpFsmCurrentFsm ::= TEXTUAL-CONVENTION
    STATUS        current
    DESCRIPTION
        ""
    SYNTAX        INTEGER
    {
        nop(0),
        remoteDomainReg(560),
        remoteDomainUnReg(564)
    }

CucsPolicyControlEpOpFsmStageName ::= TEXTUAL-CONVENTION
    STATUS        current
    DESCRIPTION
        ""
    SYNTAX        INTEGER
    {
        nop(0),
        remoteDomainRegBegin(560),
        remoteDomainRegRegistration(561),
        remoteDomainRegPushSharedSecret(562),
        remoteDomainRegCheckStatus(563),
        remoteDomainUnRegBegin(564),
        remoteDomainUnRegUnRegistration(565),
        remoteDomainRegFail(577),
        remoteDomainRegSuccess(578),
        remoteDomainUnRegFail(579),
        remoteDomainUnRegSuccess(580)
    }

CucsPolicyControlEpOpFsmTaskItem ::= TEXTUAL-CONVENTION
    STATUS        current
    DESCRIPTION
        ""
    SYNTAX        INTEGER
    {
        nop(0),
        remoteDomainReg(560),
        remoteDomainUnReg(564)
    }

CucsPolicyControlEpType ::= TEXTUAL-CONVENTION
    STATUS        current
    DESCRIPTION
        ""
    SYNTAX        INTEGER
    {
        policy(0)
    }

CucsPolicyControlOpSource ::= TEXTUAL-CONVENTION
    STATUS        current
    DESCRIPTION
        ""
    SYNTAX        INTEGER
    {
        local(0),
        policy(1),
        pendingPolicy(2),
        unspecified(3)
    }

CucsPolicyControlledTypeFsmCurrentFsm ::= TEXTUAL-CONVENTION
    STATUS        current
    DESCRIPTION
        ""
    SYNTAX        INTEGER
    {
        nop(0),
        operate(1479)
    }

CucsPolicyControlledTypeFsmStageName ::= TEXTUAL-CONVENTION
    STATUS        current
    DESCRIPTION
        ""
    SYNTAX        INTEGER
    {
        nop(0),
        operateBegin(1479),
        operateResolveAll(1480),
        operateFail(1489),
        operateSuccess(1490)
    }

CucsPolicyControlledTypeFsmTaskItem ::= TEXTUAL-CONVENTION
    STATUS        current
    DESCRIPTION
        ""
    SYNTAX        INTEGER
    {
        nop(0),
        operate(1479)
    }

CucsPolicyDeferenceAction ::= TEXTUAL-CONVENTION
    STATUS        current
    DESCRIPTION
        ""
    SYNTAX        INTEGER
    {
        delete(0),
        noAction(1),
        localize(2)
    }

CucsPolicyDeviceProfileMigrateAdminSetting ::= TEXTUAL-CONVENTION
    STATUS        current
    DESCRIPTION
        ""
    SYNTAX        INTEGER
    {
        enabled(1),
        disabled(2)
    }

CucsPolicyDomainActionEvent ::= TEXTUAL-CONVENTION
    STATUS        current
    DESCRIPTION
        ""
    SYNTAX        INTEGER
    {
        unknown(0),
        register(1),
        unregister(2)
    }

CucsPolicyDomainAuthStatus ::= TEXTUAL-CONVENTION
    STATUS        current
    DESCRIPTION
        ""
    SYNTAX        INTEGER
    {
        unknown(0),
        fail(1),
        ok(2)
    }

CucsPolicyDomainCleanupMode ::= TEXTUAL-CONVENTION
    STATUS        current
    DESCRIPTION
        ""
    SYNTAX        INTEGER
    {
        localizeGlobal(0),
        deepRemoveGlobal(1)
    }

CucsPolicyDomainRegistrationStateType ::= TEXTUAL-CONVENTION
    STATUS        current
    DESCRIPTION
        ""
    SYNTAX        INTEGER
    {
        inprogress(0),
        registered(1),
        failed(2),
        lostVisibility(3),
        unregistered(4)
    }

CucsPolicyDomainSrcAddrFmt ::= TEXTUAL-CONVENTION
    STATUS        current
    DESCRIPTION
        ""
    SYNTAX        INTEGER
    {
        ipv4(0),
        ipv6(1),
        hostname(2)
    }

CucsPolicyDomainUnRegistrationStateType ::= TEXTUAL-CONVENTION
    STATUS        current
    DESCRIPTION
        ""
    SYNTAX        INTEGER
    {
        unknown(0),
        fail(1),
        ok(2)
    }

CucsPolicyIdResolvePolicyType ::= TEXTUAL-CONVENTION
    STATUS        current
    DESCRIPTION
        ""
    SYNTAX        INTEGER
    {
        noDuplicateCheck(0),
        looseDuplicateCheck(1),
        strictDuplicateCheck(2)
    }

CucsPolicyLogControlLevel ::= TEXTUAL-CONVENTION
    STATUS        current
    DESCRIPTION
        ""
    SYNTAX        INTEGER
    {
        debug0(0),
        debug1(1),
        debug2(2),
        debug3(3),
        debug4(4),
        info(5),
        warning(6),
        minor(7),
        major(8),
        critical(9)
    }

CucsPolicyLogProfileAdminState ::= TEXTUAL-CONVENTION
    STATUS        current
    DESCRIPTION
        ""
    SYNTAX        INTEGER
    {
        disabled(0),
        enabled(1)
    }

CucsPolicyPolicyOperStatus ::= TEXTUAL-CONVENTION
    STATUS        current
    DESCRIPTION
        ""
    SYNTAX        INTEGER
    {
        ok(0),
        resolved(1),
        released(2)
    }

CucsPolicyPolicyOwner ::= TEXTUAL-CONVENTION
    STATUS        current
    DESCRIPTION
        ""
    SYNTAX        INTEGER
    {
        local(0),
        policy(1),
        pendingPolicy(2),
        unspecified(3)
    }

CucsPolicyPolicyResolveType ::= TEXTUAL-CONVENTION
    STATUS        current
    DESCRIPTION
        ""
    SYNTAX        INTEGER
    {
        name(0),
        rn(1)
    }

CucsPolicyPolicyScopeContFsmCurrentFsm ::= TEXTUAL-CONVENTION
    STATUS        current
    DESCRIPTION
        ""
    SYNTAX        INTEGER
    {
        nop(0),
        reportPolicyFailFsm(2251)
    }

CucsPolicyPolicyScopeContFsmStageName ::= TEXTUAL-CONVENTION
    STATUS        current
    DESCRIPTION
        ""
    SYNTAX        INTEGER
    {
        nop(0),
        reportPolicyFailFsmBegin(2251),
        reportPolicyFailFsmReportError(2252),
        reportPolicyFailFsmFail(2263),
        reportPolicyFailFsmSuccess(2264)
    }

CucsPolicyPolicyScopeContFsmTaskItem ::= TEXTUAL-CONVENTION
    STATUS        current
    DESCRIPTION
        ""
    SYNTAX        INTEGER
    {
        nop(0),
        reportPolicyFailFsm(2251)
    }

CucsPolicyPolicyScopeFsmCurrentFsm ::= TEXTUAL-CONVENTION
    STATUS        current
    DESCRIPTION
        ""
    SYNTAX        INTEGER
    {
        nop(0),
        releasePolicyFsm(1201),
        releaseOperationFsm(1203),
        releaseStorageFsm(1205),
        resolveManyPolicyFsm(1207),
        resolveManyOperationFsm(1209),
        resolveManyStorageFsm(1211),
        releaseManyPolicyFsm(1213),
        releaseManyOperationFsm(1215),
        releaseManyStorageFsm(1217),
        resolveAllPolicyFsm(1219),
        resolveAllOperationFsm(1221),
        resolveAllStorageFsm(1223),
        releaseAllPolicyFsm(1225),
        releaseAllOperationFsm(1227),
        releaseAllStorageFsm(1229)
    }

CucsPolicyPolicyScopeFsmStageName ::= TEXTUAL-CONVENTION
    STATUS        current
    DESCRIPTION
        ""
    SYNTAX        INTEGER
    {
        nop(0),
        releasePolicyFsmBegin(1201),
        releasePolicyFsmRelease(1202),
        releaseOperationFsmBegin(1203),
        releaseOperationFsmRelease(1204),
        releaseStorageFsmBegin(1205),
        releaseStorageFsmRelease(1206),
        resolveManyPolicyFsmBegin(1207),
        resolveManyPolicyFsmResolveMany(1208),
        resolveManyOperationFsmBegin(1209),
        resolveManyOperationFsmResolveMany(1210),
        resolveManyStorageFsmBegin(1211),
        resolveManyStorageFsmResolveMany(1212),
        releaseManyPolicyFsmBegin(1213),
        releaseManyPolicyFsmReleaseMany(1214),
        releaseManyOperationFsmBegin(1215),
        releaseManyOperationFsmReleaseMany(1216),
        releaseManyStorageFsmBegin(1217),
        releaseManyStorageFsmReleaseMany(1218),
        resolveAllPolicyFsmBegin(1219),
        resolveAllPolicyFsmResolveAll(1220),
        resolveAllOperationFsmBegin(1221),
        resolveAllOperationFsmResolveAll(1222),
        resolveAllStorageFsmBegin(1223),
        resolveAllStorageFsmResolveAll(1224),
        releaseAllPolicyFsmBegin(1225),
        releaseAllPolicyFsmReleaseAll(1226),
        releaseAllOperationFsmBegin(1227),
        releaseAllOperationFsmReleaseAll(1228),
        releaseAllStorageFsmBegin(1229),
        releaseAllStorageFsmReleaseAll(1230),
        releaseAllOperationFsmFail(1431),
        releaseAllOperationFsmSuccess(1432),
        releaseAllPolicyFsmFail(1433),
        releaseAllPolicyFsmSuccess(1434),
        releaseAllStorageFsmFail(1435),
        releaseAllStorageFsmSuccess(1436),
        releaseManyOperationFsmFail(1437),
        releaseManyOperationFsmSuccess(1438),
        releaseManyPolicyFsmFail(1439),
        releaseManyPolicyFsmSuccess(1440),
        releaseManyStorageFsmFail(1441),
        releaseManyStorageFsmSuccess(1442),
        releaseOperationFsmFail(1443),
        releaseOperationFsmSuccess(1444),
        releasePolicyFsmFail(1445),
        releasePolicyFsmSuccess(1446),
        releaseStorageFsmFail(1447),
        releaseStorageFsmSuccess(1448),
        resolveAllOperationFsmFail(1449),
        resolveAllOperationFsmSuccess(1450),
        resolveAllPolicyFsmFail(1451),
        resolveAllPolicyFsmSuccess(1452),
        resolveAllStorageFsmFail(1453),
        resolveAllStorageFsmSuccess(1454),
        resolveManyOperationFsmFail(1455),
        resolveManyOperationFsmSuccess(1456),
        resolveManyPolicyFsmFail(1457),
        resolveManyPolicyFsmSuccess(1458),
        resolveManyStorageFsmFail(1459),
        resolveManyStorageFsmSuccess(1460)
    }

CucsPolicyPolicyScopeFsmTaskItem ::= TEXTUAL-CONVENTION
    STATUS        current
    DESCRIPTION
        ""
    SYNTAX        INTEGER
    {
        nop(0),
        releasePolicyFsm(1201),
        releaseOperationFsm(1203),
        releaseStorageFsm(1205),
        resolveManyPolicyFsm(1207),
        resolveManyOperationFsm(1209),
        resolveManyStorageFsm(1211),
        releaseManyPolicyFsm(1213),
        releaseManyOperationFsm(1215),
        releaseManyStorageFsm(1217),
        resolveAllPolicyFsm(1219),
        resolveAllOperationFsm(1221),
        resolveAllStorageFsm(1223),
        releaseAllPolicyFsm(1225),
        releaseAllOperationFsm(1227),
        releaseAllStorageFsm(1229)
    }

CucsPolicyRegistrationStateType ::= TEXTUAL-CONVENTION
    STATUS        current
    DESCRIPTION
        ""
    SYNTAX        INTEGER
    {
        registering(0),
        registered(1),
        failed(2),
        lostVisibility(3),
        unregistered(4)
    }

CucsPolicyRepairStateType ::= TEXTUAL-CONVENTION
    STATUS        current
    DESCRIPTION
        ""
    SYNTAX        INTEGER
    {
        done(0),
        notDone(1)
    }

CucsPolicyRequestorFsmCurrentFsm ::= TEXTUAL-CONVENTION
    STATUS        current
    DESCRIPTION
        ""
    SYNTAX        INTEGER
    {
        nop(0),
        resolveFromCentral(2253)
    }

CucsPolicyRequestorFsmStageName ::= TEXTUAL-CONVENTION
    STATUS        current
    DESCRIPTION
        ""
    SYNTAX        INTEGER
    {
        nop(0),
        resolveFromCentralBegin(2253),
        resolveFromCentralResolveFromPolicyMgr(2254),
        resolveFromCentralResolveFromOpsMgr(2255),
        resolveFromCentralFail(2265),
        resolveFromCentralSuccess(2266)
    }

CucsPolicyRequestorFsmTaskItem ::= TEXTUAL-CONVENTION
    STATUS        current
    DESCRIPTION
        ""
    SYNTAX        INTEGER
    {
        nop(0),
        resolveFromCentral(2253)
    }

CucsPolicyResumeAckState ::= TEXTUAL-CONVENTION
    STATUS        current
    DESCRIPTION
        ""
    SYNTAX        INTEGER
    {
        noAck(0),
        acked(1),
        remoteTrigger(2)
    }

CucsPolicySharedSecretPushStateType ::= TEXTUAL-CONVENTION
    STATUS        current
    DESCRIPTION
        ""
    SYNTAX        INTEGER
    {
        unknown(0),
        fail(1),
        ok(2)
    }

CucsPolicyState ::= TEXTUAL-CONVENTION
    STATUS        current
    DESCRIPTION
        ""
    SYNTAX        INTEGER
    {
        ok(0),
        outOfSync(1)
    }

CucsPolicySuspendState ::= TEXTUAL-CONVENTION
    STATUS        current
    DESCRIPTION
        ""
    SYNTAX        INTEGER
    {
        off(0),
        on(1),
        remoteTrigger(2)
    }

CucsPolicySystemDualStack ::= TEXTUAL-CONVENTION
    STATUS        current
    DESCRIPTION
        ""
    SYNTAX        INTEGER
    {
        off(0),
        on(1)
    }

CucsPolicyUniverseType ::= TEXTUAL-CONVENTION
    STATUS        current
    DESCRIPTION
        ""
    SYNTAX        INTEGER
    {
        server(0),
        client(1)
    }

CucsPoolElementOwner ::= TEXTUAL-CONVENTION
    STATUS        current
    DESCRIPTION
        ""
    SYNTAX        INTEGER
    {
        endPoint(0),
        pool(1)
    }

CucsPoolPoolAssignmentOrder ::= TEXTUAL-CONVENTION
    STATUS        current
    DESCRIPTION
        ""
    SYNTAX        INTEGER
    {
        default(0),
        sequential(1)
    }

CucsPoolPoolType ::= TEXTUAL-CONVENTION
    STATUS        current
    DESCRIPTION
        ""
    SYNTAX        INTEGER
    {
        nonQualifer(0),
        qualifer(1)
    }

CucsPoolPoolableOwner ::= TEXTUAL-CONVENTION
    STATUS        current
    DESCRIPTION
        ""
    SYNTAX        INTEGER
    {
        endPoint(0),
        pool(1)
    }

CucsPoolScope ::= TEXTUAL-CONVENTION
    STATUS        current
    DESCRIPTION
        ""
    SYNTAX        INTEGER
    {
        public(0),
        private(1)
    }

CucsPortAutoNegotiation ::= TEXTUAL-CONVENTION
    STATUS        current
    DESCRIPTION
        ""
    SYNTAX        INTEGER
    {
        disabled(0),
        enabled(1)
    }

CucsPortEncap ::= TEXTUAL-CONVENTION
    STATUS        current
    DESCRIPTION
        ""
    SYNTAX        INTEGER
    {
        unknown(0),
        dot1q(1),
        isl(2),
        negotiate(3),
        proprietary(4)
    }

CucsPortEthAdminSpeed ::= TEXTUAL-CONVENTION
    STATUS        current
    DESCRIPTION
        ""
    SYNTAX        INTEGER
    {
        indeterminate(0),
        n1gbps(1),
        n10gbps(2),
        n20gbps(3),
        n40gbps(4),
        n25gbps(5),
        n100gbps(6),
        auto(7)
    }

CucsPortEthSpeed ::= TEXTUAL-CONVENTION
    STATUS        current
    DESCRIPTION
        ""
    SYNTAX        INTEGER
    {
        indeterminate(0),
        n1gbps(1),
        n10gbps(2),
        n20gbps(3),
        n40gbps(4),
        n25gbps(5),
        n100gbps(6),
        auto(7)
    }

CucsPortFEC ::= TEXTUAL-CONVENTION
    STATUS        current
    DESCRIPTION
        ""
    SYNTAX        INTEGER
    {
        auto(0),
        cl74(1),
        cl91(2),
        rsCons16(3),
        rsIeee(4),
        off(5)
    }

CucsPortFcSpeed ::= TEXTUAL-CONVENTION
    STATUS        current
    DESCRIPTION
        ""
    SYNTAX        INTEGER
    {
        indeterminate(0),
        n1gbps(1),
        n2gbps(2),
        n4gbps(3),
        n8gbps(4),
        auto(5),
        n16gbps(6),
        n32gbps(7),
        n64gbps(8)
    }

CucsPortGroupType ::= TEXTUAL-CONVENTION
    STATUS        current
    DESCRIPTION
        ""
    SYNTAX        INTEGER
    {
        switchEther(1),
        switchFc(4),
        host(8),
        fabric(16),
        fabricPc(32),
        hostPc(64),
        adaptorExt(128),
        adaptorPc(256),
        serverPc(512)
    }

CucsPortMode ::= TEXTUAL-CONVENTION
    STATUS        current
    DESCRIPTION
        ""
    SYNTAX        INTEGER
    {
        unknown(0),
        access(1),
        trunk(2),
        fabric(3),
        nProxy(4),
        f(5),
        e(6),
        sd(7),
        vntag(8),
        promiscuousTrunk(9)
    }

CucsPortPIoFsmCurrentFsm ::= TEXTUAL-CONVENTION
    STATUS        current
    DESCRIPTION
        ""
    SYNTAX        INTEGER
    {
        nop(0),
        inCompatSfpPresence(1014),
        inCompatSfpReplaced(1334)
    }

CucsPortPIoFsmStageName ::= TEXTUAL-CONVENTION
    STATUS        current
    DESCRIPTION
        ""
    SYNTAX        INTEGER
    {
        nop(0),
        inCompatSfpPresenceBegin(1014),
        inCompatSfpPresenceShutdown(1015),
        inCompatSfpPresenceFail(1034),
        inCompatSfpPresenceSuccess(1035),
        inCompatSfpReplacedBegin(1334),
        inCompatSfpReplacedEnablePort(1335),
        inCompatSfpReplacedFail(1461),
        inCompatSfpReplacedSuccess(1462)
    }

CucsPortPIoFsmTaskItem ::= TEXTUAL-CONVENTION
    STATUS        current
    DESCRIPTION
        ""
    SYNTAX        INTEGER
    {
        nop(0),
        inCompatSfpPresence(1014),
        inCompatSfpReplaced(1334)
    }

CucsPortSpeed ::= TEXTUAL-CONVENTION
    STATUS        current
    DESCRIPTION
        ""
    SYNTAX        INTEGER
    {
        indeterminate(0),
        n1gbps(1),
        n2gbps(2),
        n4gbps(3),
        n8gbps(4),
        auto(5),
        n16gbps(6),
        n32gbps(7)
    }

CucsPortSpeedBitmask ::= TEXTUAL-CONVENTION
    STATUS        current
    DESCRIPTION
        ""
    SYNTAX        BITS
    {
        n1gbps(0),
        n2gbps(1),
        n4gbps(2),
        n8gbps(3),
        auto(4),
        n16gbps(5),
        n32gbps(6),
        n64gbps(7)
    }

CucsPortSubGroupConfigState ::= TEXTUAL-CONVENTION
    STATUS        current
    DESCRIPTION
        ""
    SYNTAX        INTEGER
    {
        enabled(1),
        disabled(2)
    }

CucsPortSubGroupSlotId ::= TEXTUAL-CONVENTION
    STATUS        current
    DESCRIPTION
        ""
    SYNTAX        Gauge32 (1..4)

CucsPortTrust ::= TEXTUAL-CONVENTION
    STATUS        current
    DESCRIPTION
        ""
    SYNTAX        INTEGER
    {
        trusted(0),
        untrusted(1)
    }

CucsPortapiPeerCapability ::= TEXTUAL-CONVENTION
    STATUS        current
    DESCRIPTION
        ""
    SYNTAX        INTEGER
    {
        unknown(0),
        ethRackServerPort(1),
        ethFexServerPort(2),
        ethAppliantPort(3),
        ethUplinkPort(4),
        notApplicable(5)
    }

CucsPowerBudgetAggressiveCooling ::= TEXTUAL-CONVENTION
    STATUS        current
    DESCRIPTION
        ""
    SYNTAX        INTEGER
    {
        disable(0),
        enable(1)
    }

CucsPowerBudgetFanSpeed ::= TEXTUAL-CONVENTION
    STATUS        current
    DESCRIPTION
        ""
    SYNTAX        INTEGER
    {
        lowPower(0),
        balanced(1),
        performance(2),
        highPower(3),
        maxPower(4),
        na(5),
        err(6),
        noUpdate(7),
        notSupported(8),
        any(9),
        acoustic(10),
        maxCooling(11)
    }

CucsPowerCapAction ::= TEXTUAL-CONVENTION
    STATUS        current
    DESCRIPTION
        ""
    SYNTAX        INTEGER
    {
        nothing(0),
        clockDown(1),
        throttled(2)
    }

CucsPowerChThrAction ::= TEXTUAL-CONVENTION
    STATUS        current
    DESCRIPTION
        ""
    SYNTAX        INTEGER
    {
        nothing(0),
        throttleBladeDisc(1),
        stopBladeDisc(2)
    }

CucsPowerFanSpeed ::= TEXTUAL-CONVENTION
    STATUS        current
    DESCRIPTION
        ""
    SYNTAX        INTEGER
    {
        lowPower(0),
        balanced(1),
        performance(2),
        highPower(3),
        maxPower(4),
        na(5),
        err(6),
        noUpdate(7),
        notSupported(8),
        any(9),
        acoustic(10),
        maxCooling(11)
    }

CucsPowerGroupState ::= TEXTUAL-CONVENTION
    STATUS        current
    DESCRIPTION
        ""
    SYNTAX        BITS
    {
        capOk(0),
        capMismatch(1)
    }

CucsPowerGroupStatsThresholded ::= TEXTUAL-CONVENTION
    STATUS        current
    DESCRIPTION
        ""
    SYNTAX        BITS
    {
        power(0),
        powerAvg(1),
        powerMax(2),
        powerMin(3)
    }

CucsPowerGroupStatsHistThresholded ::= TEXTUAL-CONVENTION
    STATUS        current
    DESCRIPTION
        ""
    SYNTAX        BITS
    {
        power(0),
        powerAvg(1),
        powerMax(2),
        powerMin(3)
    }

CucsPowerLockState ::= TEXTUAL-CONVENTION
    STATUS        current
    DESCRIPTION
        ""
    SYNTAX        INTEGER
    {
        unknown(0),
        locked(1),
        unlocked(2)
    }

CucsPowerMemberState ::= TEXTUAL-CONVENTION
    STATUS        current
    DESCRIPTION
        ""
    SYNTAX        INTEGER
    {
        uninitialized(0),
        capOk(1),
        fwMismatch(2),
        psuInsufficient(3),
        psuRedundancyFailed(4),
        capInsufficient(5)
    }

CucsPowerMgmtStyle ::= TEXTUAL-CONVENTION
    STATUS        current
    DESCRIPTION
        ""
    SYNTAX        INTEGER
    {
        manualPerBlade(0),
        intelligentPolicyDriven(1)
    }

CucsPowerOperState ::= TEXTUAL-CONVENTION
    STATUS        current
    DESCRIPTION
        ""
    SYNTAX        INTEGER
    {
        notCapped(0),
        discoveryRetry(3),
        nonCompliant(6),
        firmwareMismatch(7),
        discoveryBudgeted(8),
        unbudgeted(9),
        budgeting(10),
        budgeted(11),
        deploying(12),
        deployed(13)
    }

CucsPowerPackagePowerLimitConfigStatus ::= TEXTUAL-CONVENTION
    STATUS        current
    DESCRIPTION
        ""
    SYNTAX        INTEGER
    {
        unknown(0),
        pending(1),
        success(2),
        failure(3)
    }

CucsPowerPackagePowerLimitConfiguredPpl ::= TEXTUAL-CONVENTION
    STATUS        current
    DESCRIPTION
        ""
    SYNTAX        INTEGER
    {
        default(0),
        min(1),
        max(2)
    }

CucsPowerPackagePowerLimitPolicyConfiguredPpl ::= TEXTUAL-CONVENTION
    STATUS        current
    DESCRIPTION
        ""
    SYNTAX        INTEGER
    {
        default(0),
        min(1),
        max(2)
    }

CucsPowerPolicyAggressiveCooling ::= TEXTUAL-CONVENTION
    STATUS        current
    DESCRIPTION
        ""
    SYNTAX        INTEGER
    {
        disable(0),
        enable(1)
    }

CucsPowerPolicyConfiguredPpl ::= TEXTUAL-CONVENTION
    STATUS        current
    DESCRIPTION
        ""
    SYNTAX        INTEGER
    {
        default(0),
        min(1),
        max(2)
    }

CucsPowerPolicyFanSpeed ::= TEXTUAL-CONVENTION
    STATUS        current
    DESCRIPTION
        ""
    SYNTAX        INTEGER
    {
        lowPower(0),
        balanced(1),
        performance(2),
        highPower(3),
        maxPower(4),
        na(5),
        err(6),
        noUpdate(7),
        notSupported(8),
        any(9),
        acoustic(10),
        maxCooling(11)
    }

CucsPowerPowerAvailState ::= TEXTUAL-CONVENTION
    STATUS        current
    DESCRIPTION
        ""
    SYNTAX        INTEGER
    {
        unknown(0),
        unavailable(1),
        available(2)
    }

CucsPowerPowerDeployState ::= TEXTUAL-CONVENTION
    STATUS        current
    DESCRIPTION
        ""
    SYNTAX        INTEGER
    {
        unknown(0),
        deployed(1),
        deployNeeded(2)
    }

CucsPowerPrioritySharing ::= TEXTUAL-CONVENTION
    STATUS        current
    DESCRIPTION
        ""
    SYNTAX        INTEGER
    {
        noPreference(0),
        highestPrioInChassis(1),
        highestPrioInPowerGroup(2)
    }

CucsPowerProfilingMethod ::= TEXTUAL-CONVENTION
    STATUS        current
    DESCRIPTION
        ""
    SYNTAX        INTEGER
    {
        unknown(0),
        default(1),
        static(2),
        pnuos(3),
        nodemgr(4)
    }

CucsPowerPsuLineMode ::= TEXTUAL-CONVENTION
    STATUS        current
    DESCRIPTION
        ""
    SYNTAX        INTEGER
    {
        unknown(0),
        undetermined(1),
        highLine(2),
        lowLine(3),
        mixedLine(4)
    }

CucsPowerPsuState ::= TEXTUAL-CONVENTION
    STATUS        current
    DESCRIPTION
        ""
    SYNTAX        INTEGER
    {
        ok(0),
        insufficient(1)
    }

CucsPowerReallocation ::= TEXTUAL-CONVENTION
    STATUS        current
    DESCRIPTION
        ""
    SYNTAX        BITS
    {
        chassis(0)
    }

CucsPowerReqConflict ::= TEXTUAL-CONVENTION
    STATUS        current
    DESCRIPTION
        ""
    SYNTAX        INTEGER
    {
        ignore(0),
        failPlacement(1)
    }

CucsProcStatAdminState ::= TEXTUAL-CONVENTION
    STATUS        current
    DESCRIPTION
        ""
    SYNTAX        INTEGER
    {
        on(1),
        clearStats(2),
        logStats(3)
    }

CucsProcessorArchitecture ::= TEXTUAL-CONVENTION
    STATUS        current
    DESCRIPTION
        ""
    SYNTAX        INTEGER
    {
        any(0),
        intelP4C(1),
        opteron(132),
        turion64(134),
        dualCoreOpteron(135),
        pentium4(178),
        xeon(179),
        xeonMP(181)
    }

CucsProcessorCacheMemStatsThresholded ::= TEXTUAL-CONVENTION
    STATUS        current
    DESCRIPTION
        ""
    SYNTAX        BITS
    {
        l2cacheUnitCorrectableErrors(0),
        l2cacheUnitUncorrectableErrors(1),
        l3cacheUnitCorrectableErrors(2),
        l3cacheUnitUncorrectableErrors(3),
        memTestcorrectableErrors(4)
    }

CucsProcessorEnvStatsThresholded ::= TEXTUAL-CONVENTION
    STATUS        current
    DESCRIPTION
        ""
    SYNTAX        BITS
    {
        inputCurrent(0),
        inputCurrentAvg(1),
        inputCurrentMax(2),
        inputCurrentMin(3),
        temperature(4),
        temperatureAvg(5),
        temperatureMax(6),
        temperatureMin(7)
    }

CucsProcessorEnvStatsHistThresholded ::= TEXTUAL-CONVENTION
    STATUS        current
    DESCRIPTION
        ""
    SYNTAX        BITS
    {
        inputCurrent(0),
        inputCurrentAvg(1),
        inputCurrentMax(2),
        inputCurrentMin(3),
        temperature(4),
        temperatureAvg(5),
        temperatureMax(6),
        temperatureMin(7)
    }

CucsProcessorErrorStatsThresholded ::= TEXTUAL-CONVENTION
    STATUS        current
    DESCRIPTION
        ""
    SYNTAX        BITS
    {
        mirroringInterSockErrors(0),
        uncorrectableLinkCRCErrors(1),
        smiLinkCorrErrors(2),
        smiLinkUncorrErrors(3),
        sparingErrors(4),
        mirroringIntraSockErrorsAvg(6),
        mirroringIntraSockErrorsMax(7),
        mirroringIntraSockErrorsMin(8),
        mirroringIntraSockErrorsRunning(9),
        smiLinkCorrErrorsAvg(11),
        smiLinkCorrErrorsMax(12),
        smiLinkCorrErrorsMin(13),
        smiLinkCorrErrorsRunning(14),
        smiLinkUncorrErrorsAvg(16),
        smiLinkUncorrErrorsMax(17),
        smiLinkUncorrErrorsMin(18),
        smiLinkUncorrErrorsRunning(19),
        sparingErrorsAvg(21),
        sparingErrorsMax(22),
        sparingErrorsMin(23),
        sparingErrorsRunning(24)
    }

CucsProcessorErrorStatsHistThresholded ::= TEXTUAL-CONVENTION
    STATUS        current
    DESCRIPTION
        ""
    SYNTAX        BITS
    {
        mirroringInterSockErrors(0),
        mirroringInterSockErrorsAvg(1),
        mirroringInterSockErrorsMax(2),
        mirroringInterSockErrorsMin(3),
        mirroringInterSockErrorsRunning(4),
        mirroringIntraSockErrors(5),
        mirroringIntraSockErrorsAvg(6),
        mirroringIntraSockErrorsMax(7),
        mirroringIntraSockErrorsMin(8),
        mirroringIntraSockErrorsRunning(9),
        smiLinkCorrErrors(10),
        smiLinkCorrErrorsAvg(11),
        smiLinkCorrErrorsMax(12),
        smiLinkCorrErrorsMin(13),
        smiLinkCorrErrorsRunning(14),
        smiLinkUncorrErrors(15),
        smiLinkUncorrErrorsAvg(16),
        smiLinkUncorrErrorsMax(17),
        smiLinkUncorrErrorsMin(18),
        smiLinkUncorrErrorsRunning(19),
        sparingErrors(20),
        sparingErrorsAvg(21),
        sparingErrorsMax(22),
        sparingErrorsMin(23),
        sparingErrorsRunning(24)
    }

CucsProcessorExecStatsThresholded ::= TEXTUAL-CONVENTION
    STATUS        current
    DESCRIPTION
        ""
    SYNTAX        BITS
    {
        decodeUnitCorrectableErrors(0),
        decodeUnitUncorrectableErrors(1),
        executionUnitCorrectableErrors(2),
        executionUnitUncorrectableErrors(3),
        instructionFetchUnitCorrectableErrors(4),
        instructionFetchUnitUncorrectableErrors(5),
        loadStoreUnitCorrectableErrors(6),
        loadStoreUnitUncorrectableErrors(7)
    }

CucsProcessorIOStatsThresholded ::= TEXTUAL-CONVENTION
    STATUS        current
    DESCRIPTION
        ""
    SYNTAX        BITS
    {
        pcieBankCorrectableErrors(0),
        pcieBankUncorrectableErrors(1),
        satauncorrectableErrors(2),
        satacorrectableErrors(3),
        smnuncorrectableErrors(4),
        smncorrectableErrors(5),
        usbuncorrectableErrors(6),
        usbcorrectableErrors(7)
    }

CucsProcessorMiscStatsThresholded ::= TEXTUAL-CONVENTION
    STATUS        current
    DESCRIPTION
        ""
    SYNTAX        BITS
    {
        coherentSlaveCorrectableErrors(0),
        coherentSlaveUncorrectableErrors(1),
        floatingPointUnitCorrectableErrors(2),
        floatingPointUnitUncorrectableErrors(3),
        mpmgmntControllerCorrectableErrors(4),
        mpmgmntControllerUncorrectableErrors(5),
        parameterBlockCorrectableErrors(6),
        parameterBlockUncorrectableErrors(7)
    }

CucsProcessorPCIBusStatsThresholded ::= TEXTUAL-CONVENTION
    STATUS        current
    DESCRIPTION
        ""
    SYNTAX        BITS
    {
        fchuncorrectableErrors(0),
        fchcorrectableErrors(1),
        northBridgeIOCorrectableErrors(2),
        northBridgeIOUncorrectableErrors(3)
    }

CucsProcessorPMUStatsThresholded ::= TEXTUAL-CONVENTION
    STATUS        current
    DESCRIPTION
        ""
    SYNTAX        BITS
    {
        systemManagementUnitCorrectableErrors(0),
        systemManagementUnitUncorrectableErrors(1)
    }

CucsProcessorQualArch ::= TEXTUAL-CONVENTION
    STATUS        current
    DESCRIPTION
        ""
    SYNTAX        INTEGER
    {
        any(0),
        intelP4C(1),
        zen(107),
        opteron(132),
        turion64(134),
        dualCoreOpteron(135),
        pentium4(178),
        xeon(179),
        xeonMP(181)
    }

CucsProcessorRuntimeThresholded ::= TEXTUAL-CONVENTION
    STATUS        current
    DESCRIPTION
        ""
    SYNTAX        BITS
    {
        load(0),
        loadAvg(1),
        loadMax(2),
        loadMin(3)
    }

CucsProcessorRuntimeHistThresholded ::= TEXTUAL-CONVENTION
    STATUS        current
    DESCRIPTION
        ""
    SYNTAX        BITS
    {
        load(0),
        loadAvg(1),
        loadMax(2),
        loadMin(3)
    }

CucsProcessorSecurityStatsThresholded ::= TEXTUAL-CONVENTION
    STATUS        current
    DESCRIPTION
        ""
    SYNTAX        BITS
    {
        pspcorrectableErrors(0),
        pspuncorrectableErrors(1)
    }

CucsProcessorUnitArch ::= TEXTUAL-CONVENTION
    STATUS        current
    DESCRIPTION
        ""
    SYNTAX        INTEGER
    {
        any(0),
        intelP4C(1),
        zen(107),
        opteron(132),
        turion64(134),
        dualCoreOpteron(135),
        pentium4(178),
        xeon(179),
        xeonMP(181)
    }

CucsQosAdminState ::= TEXTUAL-CONVENTION
    STATUS        current
    DESCRIPTION
        ""
    SYNTAX        INTEGER
    {
        disabled(0),
        enabled(1)
    }

CucsQosBackplaneSlowDrainTimer ::= TEXTUAL-CONVENTION
    STATUS        current
    DESCRIPTION
        ""
    SYNTAX        INTEGER
    {
        n200(200),
        n300(300),
        n400(400),
        n500(500),
        n600(600),
        n700(700),
        n800(800),
        n900(900),
        n1000(1000)
    }

CucsQosECNAdminState ::= TEXTUAL-CONVENTION
    STATUS        current
    DESCRIPTION
        ""
    SYNTAX        INTEGER
    {
        disabled(0),
        enabled(1),
        unknown(2)
    }

CucsQosHostControl ::= TEXTUAL-CONVENTION
    STATUS        current
    DESCRIPTION
        ""
    SYNTAX        INTEGER
    {
        none(0),
        full(1),
        fullWithException(2)
    }

CucsQosPriority ::= TEXTUAL-CONVENTION
    STATUS        current
    DESCRIPTION
        ""
    SYNTAX        INTEGER
    {
        fc(1),
        platinum(2),
        gold(3),
        silver(4),
        bronze(5),
        bestEffort(6)
    }

CucsQosSlowDrainTimer ::= TEXTUAL-CONVENTION
    STATUS        current
    DESCRIPTION
        ""
    SYNTAX        INTEGER
    {
        n100(100),
        n200(200),
        n300(300),
        n400(400),
        n500(500),
        n600(600),
        n700(700),
        n800(800),
        n900(900),
        n1000(1000)
    }

CucsQosSlowdrainCorrectionState ::= TEXTUAL-CONVENTION
    STATUS        current
    DESCRIPTION
        ""
    SYNTAX        INTEGER
    {
        disabled(0),
        enabled(1),
        failed(2)
    }

CucsQosclassDefinitionFsmCurrentFsm ::= TEXTUAL-CONVENTION
    STATUS        current
    DESCRIPTION
        ""
    SYNTAX        INTEGER
    {
        nop(0),
        configGlobalQoS(313)
    }

CucsQosclassDefinitionFsmStageName ::= TEXTUAL-CONVENTION
    STATUS        current
    DESCRIPTION
        ""
    SYNTAX        INTEGER
    {
        nop(0),
        configGlobalQoSBegin(313),
        configGlobalQoSSetLocal(314),
        configGlobalQoSSetPeer(315),
        configGlobalQoSFail(430),
        configGlobalQoSSuccess(431),
        configGlobalQoSWaitForUserAck(2256)
    }

CucsQosclassDefinitionFsmTaskItem ::= TEXTUAL-CONVENTION
    STATUS        current
    DESCRIPTION
        ""
    SYNTAX        INTEGER
    {
        nop(0),
        configGlobalQoS(313)
    }

CucsQosclassEthBEAdminState ::= TEXTUAL-CONVENTION
    STATUS        current
    DESCRIPTION
        ""
    SYNTAX        INTEGER
    {
        disabled(0),
        enabled(1)
    }

CucsQosclassEthBEDrop ::= TEXTUAL-CONVENTION
    STATUS        current
    DESCRIPTION
        ""
    SYNTAX        INTEGER
    {
        drop(0),
        noDrop(1)
    }

CucsQosclassEthBEPriority ::= TEXTUAL-CONVENTION
    STATUS        current
    DESCRIPTION
        ""
    SYNTAX        INTEGER
    {
        fc(1),
        platinum(2),
        gold(3),
        silver(4),
        bronze(5),
        bestEffort(6)
    }

CucsQosclassEthClassifiedAdminState ::= TEXTUAL-CONVENTION
    STATUS        current
    DESCRIPTION
        ""
    SYNTAX        INTEGER
    {
        disabled(0),
        enabled(1)
    }

CucsQosclassEthClassifiedDrop ::= TEXTUAL-CONVENTION
    STATUS        current
    DESCRIPTION
        ""
    SYNTAX        INTEGER
    {
        drop(0),
        noDrop(1)
    }

CucsQosclassEthClassifiedPriority ::= TEXTUAL-CONVENTION
    STATUS        current
    DESCRIPTION
        ""
    SYNTAX        INTEGER
    {
        fc(1),
        platinum(2),
        gold(3),
        silver(4),
        bronze(5),
        bestEffort(6)
    }

CucsQosclassFcAdminState ::= TEXTUAL-CONVENTION
    STATUS        current
    DESCRIPTION
        ""
    SYNTAX        INTEGER
    {
        disabled(0),
        enabled(1)
    }

CucsQosclassFcDrop ::= TEXTUAL-CONVENTION
    STATUS        current
    DESCRIPTION
        ""
    SYNTAX        INTEGER
    {
        drop(0),
        noDrop(1)
    }

CucsQosclassFcPriority ::= TEXTUAL-CONVENTION
    STATUS        current
    DESCRIPTION
        ""
    SYNTAX        INTEGER
    {
        fc(1),
        platinum(2),
        gold(3),
        silver(4),
        bronze(5),
        bestEffort(6)
    }

CucsQosclassSlowDrainCorePortTimer ::= TEXTUAL-CONVENTION
    STATUS        current
    DESCRIPTION
        ""
    SYNTAX        INTEGER
    {
        n100(100),
        n200(200),
        n300(300),
        n400(400),
        n500(500),
        n600(600),
        n700(700),
        n800(800),
        n900(900),
        n1000(1000)
    }

CucsQosclassSlowDrainEthAdminState ::= TEXTUAL-CONVENTION
    STATUS        current
    DESCRIPTION
        ""
    SYNTAX        INTEGER
    {
        disabled(0),
        enabled(1)
    }

CucsQosclassSlowDrainFcAdminState ::= TEXTUAL-CONVENTION
    STATUS        current
    DESCRIPTION
        ""
    SYNTAX        INTEGER
    {
        disabled(0),
        enabled(1)
    }

CucsQosclassSlowDrainFsmCurrentFsm ::= TEXTUAL-CONVENTION
    STATUS        current
    DESCRIPTION
        ""
    SYNTAX        INTEGER
    {
        nop(0),
        configQoSSlowDrain(2317),
        configQoSSlowDrainFex(2320)
    }

CucsQosclassSlowDrainFsmStageName ::= TEXTUAL-CONVENTION
    STATUS        current
    DESCRIPTION
        ""
    SYNTAX        INTEGER
    {
        nop(0),
        configQoSSlowDrainBegin(2317),
        configQoSSlowDrainSetPeer(2318),
        configQoSSlowDrainSetLocal(2319),
        configQoSSlowDrainFexBegin(2320),
        configQoSSlowDrainFexSetPeer(2321),
        configQoSSlowDrainFexSetLocal(2322),
        configQoSSlowDrainFail(2330),
        configQoSSlowDrainSuccess(2331),
        configQoSSlowDrainFexFail(2332),
        configQoSSlowDrainFexSuccess(2333)
    }

CucsQosclassSlowDrainFsmTaskItem ::= TEXTUAL-CONVENTION
    STATUS        current
    DESCRIPTION
        ""
    SYNTAX        INTEGER
    {
        nop(0),
        configQoSSlowDrain(2317),
        configQoSSlowDrainFex(2320)
    }

CucsQueryActivity ::= TEXTUAL-CONVENTION
    STATUS        current
    DESCRIPTION
        ""
    SYNTAX        INTEGER
    {
        restart(0),
        idle(1)
    }

CucsQueryOperation ::= TEXTUAL-CONVENTION
    STATUS        current
    DESCRIPTION
        ""
    SYNTAX        INTEGER
    {
        estimate(1),
        import(2)
    }

CucsQueryStatus ::= TEXTUAL-CONVENTION
    STATUS        current
    DESCRIPTION
        ""
    SYNTAX        INTEGER
    {
        pending(0),
        success(1),
        timeout(2),
        failed(3)
    }

CucsQueryresultOrgCategory ::= TEXTUAL-CONVENTION
    STATUS        current
    DESCRIPTION
        ""
    SYNTAX        INTEGER
    {
        unspecified(0),
        orgOrg(1),
        domainOrg(2)
    }

CucsSecurityEncryptionEpFsmCurrentFsm ::= TEXTUAL-CONVENTION
    STATUS        current
    DESCRIPTION
        ""
    SYNTAX        INTEGER
    {
        nop(0),
        updateEncryptionEp(2499)
    }

CucsSecurityEncryptionEpFsmStageName ::= TEXTUAL-CONVENTION
    STATUS        current
    DESCRIPTION
        ""
    SYNTAX        INTEGER
    {
        nop(0),
        updateEncryptionEpBegin(2499),
        updateEncryptionEpConfigureLocal(2500),
        updateEncryptionEpDeleteAfterConfigLocal(2501),
        updateEncryptionEpConfigurePeer(2502),
        updateEncryptionEpDeleteAfterConfigPeer(2503),
        updateEncryptionEpFail(2505),
        updateEncryptionEpSuccess(2506)
    }

CucsSecurityEncryptionEpFsmTaskItem ::= TEXTUAL-CONVENTION
    STATUS        current
    DESCRIPTION
        ""
    SYNTAX        INTEGER
    {
        nop(0),
        updateEncryptionEp(2499)
    }

CucsSecurityUnitId ::= TEXTUAL-CONVENTION
    STATUS        current
    DESCRIPTION
        ""
    SYNTAX        Gauge32 (1..255)

CucsServerConfigIssues ::= TEXTUAL-CONVENTION
    STATUS        current
    DESCRIPTION
        ""
    SYNTAX        BITS
    {
        insufficientResources(0),
        boardControllerUpdateUnsupported(1),
        bootConfigurationInvalid(2),
        bootOrderIscsi(3),
        bootOrderPxe(4),
        bootOrderSanImagePath(5),
        computeUnavailable(6),
        computeUndiscovered(7),
        incompatBiosForSriovVnics(8),
        incompatibleBiosImage(9),
        insufficientPowerBudget(10),
        macAddressAssignment(11),
        memoryRequirement(12),
        migration(13),
        missingFirmwareImage(14),
        nonInterruptFsmRunning(15),
        physicalRequirement(16),
        powerGroupRequirement(17),
        processorRequirement(18),
        remotePolicy(19),
        serverPositionRequirement(20),
        remoteServiceProfile(21),
        systemUuidAssignment(22),
        wwnnDerivationFromVhba(23),
        resourceOwnershipConflict(24),
        bootipPolicyInvalid(25),
        hostimgPolicyInvalid(26),
        imgsecPolicyInvalid(27),
        provsrvPolicyInvalid(28),
        qosPolicyInvalid(29),
        bootConfigurationUnsupported(30),
        serverFeatureCapabilityMismatch(31),
        domainRequirement(32),
        duplicateAddressConflict(33),
        vmediaPolicyUnsupported(34),
        bootPolicyVmediaInvalid(35),
        vmediaMountConfigInvalid(36),
        softPinningVlanMismatch(37),
        cimcDowngradeRestriction(38),
        processorTypeCimcDowngradeRestriction(39),
        processorTypeBiosDowngradeRestriction(40),
        bootOrderJbodImagePath(41),
        unsupportedBiosForVnicCdn(42),
        onNextBootUnsupported(44),
        unsupportedBiosForTpm(45),
        serverTypeCimcDowngradeRestriction(46),
        embeddedControllerNotSupported(47),
        unsupportedVicSlot(48),
        unsupportedCimcVersionForPowerCapping(50),
        bootDevNoSupport(51),
        bootOrderBadBlockSize(52),
        hardwareInventoryMismatchBlade(53),
        hardwareInventoryMismatchRack(54),
        secondControllerServerFwDowngradeRestriction(55),
        serverFeatureCapabilityMismatchNonFatal(56),
        powerStateChange(57),
        nonPreEmptiveFsmRunning(58),
        graphicsCardModeChangeUnsupported(59),
        templateUnavailable(60),
        graphicsCardNotPresent(61),
        dualSiocServerFwRestriction(62)
    }

CucsServerExtdConfigIssues ::= TEXTUAL-CONVENTION
    STATUS        current
    DESCRIPTION
        ""
    SYNTAX        BITS
    {
        persistentMemoryPolicyNotFound(0),
        persistentMemoryDimmsNotPresent(1),
        persistentMemoryNoDimmOnGivenSlot(2),
        persistentMemoryConfiguredForSocketGt2(3),
        persistentMemoryDestructiveGoalConfigAndDataLoss(4),
        persistentMemoryDestructiveNamespaceConfigAndDataLoss(5),
        persistentMemoryForceGoalConfigAndDataLoss(6),
        persistentMemoryForceNamespaceConfigAndDataLoss(7),
        persistentMemoryOperationInProgess(8),
        persistentMemoryNotEnoughSpaceOnTheGivenRegion(9),
        persistentMemoryNotEnoughSpaceOnAnyRegion(10),
        persistentMemoryOperationNotPermitted(11),
        persistentMemoryEndPointMoNotFound(12),
        persistentMemoryNamespaceMoNotFound(13),
        persistentMemoryRegionNotFoundOnGivenSocket(14),
        persistentMemoryRegionNotFoundOnGivenDimmNumber(15),
        hfpBackupVersionSet(16),
        persistentMemorySecurityKeyNotMatching(17),
        persistentMemoryBothGoalAndSecurityConfigModifyNotAllowed(18),
        persistentMemoryDetectionServer(19),
        fwUpdateCouldFail(20),
        legacyBootModeUnsupported(21),
        processorTypeConstraintNotDefined(22),
        pcieNodeCimcDowngradeRestriction(23),
        pcieNodeBiosDowngradeRestriction(24),
        sriovDisabledVnicsPolicyEnabled(25),
        configuredPplValueDrop(26),
        dualMiamiBeachCimcDowngradeRestriction(27)
    }

CucsSesScsiDriveStatus ::= TEXTUAL-CONVENTION
    STATUS        current
    DESCRIPTION
        ""
    SYNTAX        INTEGER
    {
        unknown(0),
        good(1),
        bad(2)
    }

CucsSmartcallhomeAlertGroup ::= TEXTUAL-CONVENTION
    STATUS        current
    DESCRIPTION
        ""
    SYNTAX        BITS
    {
        diagnostic(0),
        environmental(1),
        inventory(2)
    }

CucsSmartcallhomeFormat ::= TEXTUAL-CONVENTION
    STATUS        current
    DESCRIPTION
        ""
    SYNTAX        INTEGER
    {
        xml(1),
        fullTxt(2),
        shortTxt(4)
    }

CucsSmartlicenseAdminState ::= TEXTUAL-CONVENTION
    STATUS        current
    DESCRIPTION
        ""
    SYNTAX        INTEGER
    {
        disable(0),
        enable(1)
    }

CucsSmartlicenseAgentDebugLevel ::= TEXTUAL-CONVENTION
    STATUS        current
    DESCRIPTION
        ""
    SYNTAX        INTEGER
    {
        error(0),
        trace(1),
        debug(2),
        all(3)
    }

CucsSmartlicenseAgentEnforceMode ::= TEXTUAL-CONVENTION
    STATUS        current
    DESCRIPTION
        ""
    SYNTAX        INTEGER
    {
        invalid(0),
        init(1),
        waiting(2),
        compliance(3),
        outOfCompliance(4),
        overage(5),
        eval(6),
        expired(7),
        gracePeriod(8),
        authorizationExpired(9),
        gracePeriodExpired(10),
        disabled(11),
        invalidTag(12),
        max(13)
    }

CucsSmartlicenseAgentFsmCurrentFsm ::= TEXTUAL-CONVENTION
    STATUS        current
    DESCRIPTION
        ""
    SYNTAX        INTEGER
    {
        nop(0),
        configure(480)
    }

CucsSmartlicenseAgentFsmStageName ::= TEXTUAL-CONVENTION
    STATUS        current
    DESCRIPTION
        ""
    SYNTAX        INTEGER
    {
        nop(0),
        configureBegin(480),
        configureConfig(481),
        configureFail(516),
        configureSuccess(517)
    }

CucsSmartlicenseAgentFsmTaskItem ::= TEXTUAL-CONVENTION
    STATUS        current
    DESCRIPTION
        ""
    SYNTAX        INTEGER
    {
        nop(0),
        configure(480)
    }

CucsSmartlicenseAgentRegistrationStatus ::= TEXTUAL-CONVENTION
    STATUS        current
    DESCRIPTION
        ""
    SYNTAX        INTEGER
    {
        notRegistered(0),
        registrationInProgress(1),
        registrationFailed(2),
        registrationRetryInProgress(3),
        registrationCompleted(4)
    }

CucsSmartlicenseAgentState ::= TEXTUAL-CONVENTION
    STATUS        current
    DESCRIPTION
        ""
    SYNTAX        INTEGER
    {
        unconfigured(0),
        unidentified(1),
        registered(2),
        authorized(3),
        outofcompliance(4),
        expired(5)
    }

CucsSmartlicenseConfigState ::= TEXTUAL-CONVENTION
    STATUS        current
    DESCRIPTION
        ""
    SYNTAX        INTEGER
    {
        disabled(0),
        enabled(1),
        registering(2),
        registered(3),
        registerfailed(4)
    }

CucsSmartlicenseEntitlementEpFsmCurrentFsm ::= TEXTUAL-CONVENTION
    STATUS        current
    DESCRIPTION
        ""
    SYNTAX        INTEGER
    {
        nop(0),
        configure(484)
    }

CucsSmartlicenseEntitlementEpFsmStageName ::= TEXTUAL-CONVENTION
    STATUS        current
    DESCRIPTION
        ""
    SYNTAX        INTEGER
    {
        nop(0),
        configureBegin(484),
        configureReport(485),
        configureRetryReport(486),
        configureFail(518),
        configureSuccess(519)
    }

CucsSmartlicenseEntitlementEpFsmTaskItem ::= TEXTUAL-CONVENTION
    STATUS        current
    DESCRIPTION
        ""
    SYNTAX        INTEGER
    {
        nop(0),
        configure(484)
    }

CucsSmartlicenseHolderFsmCurrentFsm ::= TEXTUAL-CONVENTION
    STATUS        current
    DESCRIPTION
        ""
    SYNTAX        INTEGER
    {
        nop(0),
        configure(487),
        updateState(530)
    }

CucsSmartlicenseHolderFsmStageName ::= TEXTUAL-CONVENTION
    STATUS        current
    DESCRIPTION
        ""
    SYNTAX        INTEGER
    {
        nop(0),
        configureBegin(487),
        configureEnableSmartLicense(488),
        configureDisableSmartLicense(489),
        configureRegisterDevice(490),
        configureRetryRegisterDevice(491),
        configureUnregisterDevice(492),
        configureRetryUnregisterDevice(493),
        configureFail(520),
        configureSuccess(521),
        updateStateBegin(530),
        updateStateRefreshState(531),
        updateStateFail(534),
        updateStateSuccess(535)
    }

CucsSmartlicenseHolderFsmTaskFlags ::= TEXTUAL-CONVENTION
    STATUS        current
    DESCRIPTION
        ""
    SYNTAX        BITS
    {
        samDmeSmartlicenseHolderConfigureEnable(10),
        samDmeSmartlicenseHolderConfigureDisable(11),
        samDmeSmartlicenseHolderConfigureReportEntitlement(12),
        samDmeSmartlicenseHolderConfigureRegisterDevice(13),
        samDmeSmartlicenseHolderConfigureUnregisterDevice(14)
    }

CucsSmartlicenseHolderFsmTaskItem ::= TEXTUAL-CONVENTION
    STATUS        current
    DESCRIPTION
        ""
    SYNTAX        INTEGER
    {
        nop(0),
        configure(487),
        updateState(530)
    }

CucsSmartlicenseTestDevCertEnableType ::= TEXTUAL-CONVENTION
    STATUS        current
    DESCRIPTION
        ""
    SYNTAX        INTEGER
    {
        none(0),
        enable(1),
        disable(2)
    }

CucsSmartlicenseTestFsmCurrentFsm ::= TEXTUAL-CONVENTION
    STATUS        current
    DESCRIPTION
        ""
    SYNTAX        INTEGER
    {
        nop(0),
        configure(482)
    }

CucsSmartlicenseTestFsmStageName ::= TEXTUAL-CONVENTION
    STATUS        current
    DESCRIPTION
        ""
    SYNTAX        INTEGER
    {
        nop(0),
        configureBegin(482),
        configureExecuteTestCli(483),
        configureFail(522),
        configureSuccess(523)
    }

CucsSmartlicenseTestFsmTaskItem ::= TEXTUAL-CONVENTION
    STATUS        current
    DESCRIPTION
        ""
    SYNTAX        INTEGER
    {
        nop(0),
        configure(482)
    }

CucsSmartlicenseTestTimerType ::= TEXTUAL-CONVENTION
    STATUS        current
    DESCRIPTION
        ""
    SYNTAX        INTEGER
    {
        none(0),
        eval(1),
        authExpire(2),
        authRenew(3),
        idcertExpire(4),
        idcertRenew(5),
        daily(6),
        ackExpire(7),
        evalWarning(8),
        registration(9),
        grace(10)
    }

CucsSmartlicenseTestTransportMode ::= TEXTUAL-CONVENTION
    STATUS        current
    DESCRIPTION
        ""
    SYNTAX        INTEGER
    {
        none(0),
        callhome(1),
        http(2)
    }

CucsSolAdminState ::= TEXTUAL-CONVENTION
    STATUS        current
    DESCRIPTION
        ""
    SYNTAX        INTEGER
    {
        disable(0),
        enable(1)
    }

CucsSolSpeed ::= TEXTUAL-CONVENTION
    STATUS        current
    DESCRIPTION
        ""
    SYNTAX        INTEGER
    {
        n9600(6),
        n19200(7),
        n38400(8),
        n57600(9),
        n115200(10),
        defaultValue(9600)
    }

CucsStatsChartDomain ::= TEXTUAL-CONVENTION
    STATUS        current
    DESCRIPTION
        ""
    SYNTAX        INTEGER
    {
        network(0),
        temp(1),
        power(2),
        cooling(3)
    }

CucsStatsChartType ::= TEXTUAL-CONVENTION
    STATUS        current
    DESCRIPTION
        ""
    SYNTAX        INTEGER
    {
        static(0),
        dynamic(1)
    }

CucsStatsCollectionDomain ::= TEXTUAL-CONVENTION
    STATUS        current
    DESCRIPTION
        ""
    SYNTAX        INTEGER
    {
        unknown(0),
        chassis(2),
        port(4),
        host(5),
        adapter(6),
        server(7),
        fex(8)
    }

CucsStatsCollectionInterval ::= TEXTUAL-CONVENTION
    STATUS        current
    DESCRIPTION
        ""
    SYNTAX        INTEGER
    {
        n30seconds(30),
        n1minute(60),
        n2minutes(120),
        n5minutes(300)
    }

CucsStatsCollectionPolicyFsmCurrentFsm ::= TEXTUAL-CONVENTION
    STATUS        current
    DESCRIPTION
        ""
    SYNTAX        INTEGER
    {
        nop(0),
        updateEp(310)
    }

CucsStatsCollectionPolicyFsmStageName ::= TEXTUAL-CONVENTION
    STATUS        current
    DESCRIPTION
        ""
    SYNTAX        INTEGER
    {
        nop(0),
        updateEpBegin(310),
        updateEpSetEpA(311),
        updateEpSetEpB(312),
        updateEpFail(432),
        updateEpSuccess(433)
    }

CucsStatsCollectionPolicyFsmTaskItem ::= TEXTUAL-CONVENTION
    STATUS        current
    DESCRIPTION
        ""
    SYNTAX        INTEGER
    {
        nop(0),
        updateEp(310)
    }

CucsStatsContextClass ::= TEXTUAL-CONVENTION
    STATUS        current
    DESCRIPTION
        ""
    SYNTAX        INTEGER
    {
        computeSystem(0),
        equipmentChassis(1),
        computeBlade(2)
    }

CucsStatsCoolingEndpoint ::= TEXTUAL-CONVENTION
    STATUS        current
    DESCRIPTION
        ""
    SYNTAX        INTEGER
    {
        chassisFans(0),
        fiFans(1),
        rackUnitFans(2)
    }

CucsStatsDailyRecords ::= TEXTUAL-CONVENTION
    STATUS        current
    DESCRIPTION
        ""
    SYNTAX        INTEGER
    {
        none(0),
        n2weeks(14),
        n3months(90),
        n6months(180),
        n1year(365),
        unlimited(-1)
    }

CucsStatsDefaultView ::= TEXTUAL-CONVENTION
    STATUS        current
    DESCRIPTION
        ""
    SYNTAX        INTEGER
    {
        chart(0),
        table(1)
    }

CucsStatsEtherType ::= TEXTUAL-CONVENTION
    STATUS        current
    DESCRIPTION
        ""
    SYNTAX        BITS
    {
        total(0),
        unicast(1),
        multicast(2),
        broadcast(3),
        jumbo(4)
    }

CucsStatsHourlyRecords ::= TEXTUAL-CONVENTION
    STATUS        current
    DESCRIPTION
        ""
    SYNTAX        INTEGER
    {
        none(0),
        n1week(168),
        n2weeks(336),
        n4weeks(672),
        n8weeks(1344),
        unlimited(-1)
    }

CucsStatsMigrateStatus ::= TEXTUAL-CONVENTION
    STATUS        current
    DESCRIPTION
        ""
    SYNTAX        INTEGER
    {
        fail(0),
        success(1),
        skip(2),
        pending(3),
        inProgress(4)
    }

CucsStatsNetworkEndpoint ::= TEXTUAL-CONVENTION
    STATUS        current
    DESCRIPTION
        ""
    SYNTAX        INTEGER
    {
        ethPorts(0),
        fcPorts(1),
        nics(2),
        hbas(3)
    }

CucsStatsPasadenaCollectionPolicyCollectionInterval ::= TEXTUAL-CONVENTION
    STATUS        current
    DESCRIPTION
        ""
    SYNTAX        INTEGER
    {
        never(0),
        n1min(1),
        n2min(2),
        n5min(5),
        n10min(10),
        n15min(15),
        n30min(30)
    }

CucsStatsPowerEndpoint ::= TEXTUAL-CONVENTION
    STATUS        current
    DESCRIPTION
        ""
    SYNTAX        INTEGER
    {
        blades(0),
        racks(1),
        chassis(2)
    }

CucsStatsRealtimeRecords ::= TEXTUAL-CONVENTION
    STATUS        current
    DESCRIPTION
        ""
    SYNTAX        INTEGER
    {
        none(0),
        n1week(672),
        n2weeks(1344),
        n4weeks(2688),
        n8weeks(5376),
        unlimited(-1)
    }

CucsStatsReportingInterval ::= TEXTUAL-CONVENTION
    STATUS        current
    DESCRIPTION
        ""
    SYNTAX        INTEGER
    {
        n2minutes(120),
        n15minutes(900),
        n30minutes(1800),
        n60minutes(3600),
        n2hours(7200),
        n4hours(14400),
        n8hours(28800)
    }

CucsStatsSubscribeStatus ::= TEXTUAL-CONVENTION
    STATUS        current
    DESCRIPTION
        ""
    SYNTAX        INTEGER
    {
        ok(0),
        pending(1)
    }

CucsStatsThermalEndpoint ::= TEXTUAL-CONVENTION
    STATUS        current
    DESCRIPTION
        ""
    SYNTAX        INTEGER
    {
        servers(0)
    }

CucsStatsThr32DefinitionPropType ::= TEXTUAL-CONVENTION
    STATUS        current
    DESCRIPTION
        ""
    SYNTAX        INTEGER
    {
        uint32(1),
        uint64(2),
        float(3)
    }

CucsStatsThr32ValuePropType ::= TEXTUAL-CONVENTION
    STATUS        current
    DESCRIPTION
        ""
    SYNTAX        INTEGER
    {
        uint32(1),
        uint64(2),
        float(3)
    }

CucsStatsThr64DefinitionPropType ::= TEXTUAL-CONVENTION
    STATUS        current
    DESCRIPTION
        ""
    SYNTAX        INTEGER
    {
        uint32(1),
        uint64(2),
        float(3)
    }

CucsStatsThr64ValuePropType ::= TEXTUAL-CONVENTION
    STATUS        current
    DESCRIPTION
        ""
    SYNTAX        INTEGER
    {
        uint32(1),
        uint64(2),
        float(3)
    }

CucsStatsThrFloatDefinitionPropType ::= TEXTUAL-CONVENTION
    STATUS        current
    DESCRIPTION
        ""
    SYNTAX        INTEGER
    {
        uint32(1),
        uint64(2),
        float(3)
    }

CucsStatsThrFloatValuePropType ::= TEXTUAL-CONVENTION
    STATUS        current
    DESCRIPTION
        ""
    SYNTAX        INTEGER
    {
        uint32(1),
        uint64(2),
        float(3)
    }

CucsStatsThresholdDefinitionAutoRecovery ::= TEXTUAL-CONVENTION
    STATUS        current
    DESCRIPTION
        ""
    SYNTAX        INTEGER
    {
        disabled(0),
        enabled(1)
    }

CucsStatsThresholdDirection ::= TEXTUAL-CONVENTION
    STATUS        current
    DESCRIPTION
        ""
    SYNTAX        INTEGER
    {
        aboveNormal(1),
        belowNormal(2)
    }

CucsStatsTopBottom ::= TEXTUAL-CONVENTION
    STATUS        current
    DESCRIPTION
        ""
    SYNTAX        BITS
    {
        top(0),
        bottom(1)
    }

CucsStatsUcsDomain ::= TEXTUAL-CONVENTION
    STATUS        current
    DESCRIPTION
        ""
    SYNTAX        INTEGER
    {
        unknown(0)
    }

CucsStatsWeeklyRecords ::= TEXTUAL-CONVENTION
    STATUS        current
    DESCRIPTION
        ""
    SYNTAX        INTEGER
    {
        none(0),
        n2weeks(2),
        n6months(26),
        n1year(53),
        unlimited(-1)
    }

CucsStatsXType ::= TEXTUAL-CONVENTION
    STATUS        current
    DESCRIPTION
        ""
    SYNTAX        BITS
    {
        tx(0),
        rx(1),
        avp(2),
        agp(3),
        pt(4),
        pfs(5)
    }

CucsStorageAccessType ::= TEXTUAL-CONVENTION
    STATUS        current
    DESCRIPTION
        ""
    SYNTAX        INTEGER
    {
        unknown(0),
        readWrite(1),
        readOnly(2),
        blocked(3),
        transportReady(4),
        hidden(5)
    }

CucsStorageActualWriteType ::= TEXTUAL-CONVENTION
    STATUS        current
    DESCRIPTION
        ""
    SYNTAX        INTEGER
    {
        unknown(0),
        writeThrough(1),
        writeBack(2)
    }

CucsStorageAdminActionTrigger ::= TEXTUAL-CONVENTION
    STATUS        current
    DESCRIPTION
        ""
    SYNTAX        INTEGER
    {
        idle(0),
        triggered(1),
        canceled(2)
    }

CucsStorageAdminActionType ::= TEXTUAL-CONVENTION
    STATUS        current
    DESCRIPTION
        ""
    SYNTAX        INTEGER
    {
        unspecified(0),
        jbod(1),
        unconfiguredGood(2),
        clearForeignConfiguration(3),
        prepareForRemoval(4),
        undoPrepareForRemoval(5),
        globalHotSpare(6),
        dedicatedHotSpare(7),
        removeHotSpare(8),
        ledOn(9),
        ledOff(10),
        enableSecurity(11),
        clearSecureDrive(12),
        clearSecureForeignConfigDrive(13),
        unlockForeignDrive(14)
    }

CucsStorageAdminCtrlActionType ::= TEXTUAL-CONVENTION
    STATUS        current
    DESCRIPTION
        ""
    SYNTAX        INTEGER
    {
        unspecified(0),
        importForeignConfiguration(1),
        unpinCacheAll(2),
        skipInitialConfig(4),
        clearBootConfiguration(5),
        unlockDisk(6),
        disableSecurity(7),
        modifyKey(8),
        enableSecurity(9),
        testKmipConnectivity(10),
        cleanHxState(11),
        secureHxDrives(12),
        rescanHxInventory(13),
        resendHxKey(14)
    }

CucsStorageAdminState ::= TEXTUAL-CONVENTION
    STATUS        current
    DESCRIPTION
        ""
    SYNTAX        INTEGER
    {
        undefined(0),
        online(1),
        offline(2),
        delete(3),
        restore(4),
        degraded(5),
        transportReady(6),
        clearTransportReady(7),
        hide(8),
        unhide(9),
        secureDriveGroup(10)
    }

CucsStorageAlarmType ::= TEXTUAL-CONVENTION
    STATUS        current
    DESCRIPTION
        ""
    SYNTAX        INTEGER
    {
        minor(0),
        major(1)
    }

CucsStorageAllocState ::= TEXTUAL-CONVENTION
    STATUS        current
    DESCRIPTION
        ""
    SYNTAX        INTEGER
    {
        none(0),
        allocating(1),
        allocated(2),
        failed(3)
    }

CucsStorageArrayId ::= TEXTUAL-CONVENTION
    STATUS        current
    DESCRIPTION
        ""
    SYNTAX        Gauge32 (0..254)

CucsStorageAutoConfigMode ::= TEXTUAL-CONVENTION
    STATUS        current
    DESCRIPTION
        ""
    SYNTAX        INTEGER
    {
        unspecified(0),
        unconfiguredGood(1),
        jbod(2),
        raid0(3),
        notSupported(4)
    }

CucsStorageBatteryType ::= TEXTUAL-CONVENTION
    STATUS        current
    DESCRIPTION
        ""
    SYNTAX        INTEGER
    {
        unknown(0),
        battery(1),
        supercap(2)
    }

CucsStorageBbuStatus ::= TEXTUAL-CONVENTION
    STATUS        current
    DESCRIPTION
        ""
    SYNTAX        INTEGER
    {
        unknown(0),
        optimal(1),
        learnCycleActive(2),
        learnCycleNeeded(3),
        failurePredicted(4),
        premiumFeatureReqd(5),
        microcodeUpdateReqd(6),
        replacementNeeded(7),
        noFlashSpace(8),
        notSupported(9),
        notPresent(10)
    }

CucsStorageBladeSlotId ::= TEXTUAL-CONVENTION
    STATUS        current
    DESCRIPTION
        ""
    SYNTAX        Gauge32 (1..8)

CucsStorageBootableType ::= TEXTUAL-CONVENTION
    STATUS        current
    DESCRIPTION
        ""
    SYNTAX        INTEGER
    {
        unknown(0),
        true(1),
        false(2)
    }

CucsStorageCacheType ::= TEXTUAL-CONVENTION
    STATUS        current
    DESCRIPTION
        ""
    SYNTAX        INTEGER
    {
        unknown(0),
        noChange(1),
        enable(2),
        disable(3)
    }

CucsStorageConfigCheckPoint ::= TEXTUAL-CONVENTION
    STATUS        current
    DESCRIPTION
        ""
    SYNTAX        BITS
    {
        firmwareInventoryReported(0)
    }

CucsStorageConfigIssues ::= TEXTUAL-CONVENTION
    STATUS        current
    DESCRIPTION
        ""
    SYNTAX        BITS
    {
        destructiveLocalDiskConfig(0),
        incompatibleDiskTypes(1),
        incompatibleNumberOfLocalDisks(2),
        incompatibleRaidLevel(3),
        missingRaidKey(4),
        storagePathConfigurationError(5),
        wwnnAssignment(6),
        zoneCapacity(7),
        flexflashController(8),
        flexflashCard(9),
        flexflashMetadata(10),
        storageFeatureCapabilityMismatch(11),
        virtualDriveHiddenOrTransportReady(12),
        invalidZoningDiskBootable(13),
        unsupportedLunSizeModification(14),
        bmcCertsAbsent(15),
        cimcMgmtNotConfigured(16),
        multipleSecurityPolicies(17),
        sedUnsupportedServer(18),
        replicaNameSuffixChange(19),
        insufficientDisks(20),
        unsupportedRaidLevel(21),
        insufficientStorageSpace(22),
        diskRoleMismatch(23),
        diskTypeMismatch(24),
        unsupportedOrphanLunModification(25),
        duplicatedLunName(26),
        unsupportedController(27),
        unsupportedDestructiveChange(28),
        unsupportedDiskControllerConfig(29),
        conflictingLunConfig(30),
        virtualDriveAccessDenied(31),
        virtualDriveDeletionInProgress(32),
        unsupportedWriteCachePolicy(33),
        unsupportedVdModification(34),
        unsupportedLunMapModification(35),
        unsupportedHotspareChange(36),
        invalidStorageProfileBinding(37),
        invalidLocalLunDiskPolicyReference(38),
        unsupportedExpandToAvailable(40),
        unsupportedGlobalHotspares(41),
        unsupportedOrder(42),
        unsupportedVdPolicy(46),
        setProperOrder(49),
        unsupportedUseRemainingDisks(50),
        driveCacheNotSupported(51),
        embeddedControllerNotSupported(52),
        invalidDzpReference(53),
        unsupportedDiskSlotZoning(54),
        unsupportedPartialDiskGroupZoning(55),
        unsupportedIoPolicy(56),
        invalidDiskSlotOwnership(57),
        diskSharingNotSupported(58),
        unsupportedChassisSpareController(59),
        unsupportedStripSizeChange(60),
        unsupportedChassisDiskZoning(61),
        unsupportedSecurityOperation(62)
    }

CucsStorageConfigState ::= TEXTUAL-CONVENTION
    STATUS        current
    DESCRIPTION
        ""
    SYNTAX        INTEGER
    {
        notApplied(0),
        applying(1),
        applied(2),
        applyFailed(3),
        orphaned(4),
        notInUse(5),
        nA(6),
        unknown(7)
    }

CucsStorageConfiguration ::= TEXTUAL-CONVENTION
    STATUS        current
    DESCRIPTION
        ""
    SYNTAX        INTEGER
    {
        unknown(0),
        supported(1),
        notSupported(2)
    }

CucsStorageConfiguredWriteType ::= TEXTUAL-CONVENTION
    STATUS        current
    DESCRIPTION
        ""
    SYNTAX        INTEGER
    {
        unknown(0),
        writeThrough(1),
        writeBackGoodBbu(2),
        alwaysWriteBack(3)
    }

CucsStorageConnectionProtocol ::= TEXTUAL-CONVENTION
    STATUS        current
    DESCRIPTION
        ""
    SYNTAX        INTEGER
    {
        unspecified(0),
        sas(1),
        sata(2),
        nvme(3)
    }

CucsStorageControllerControllerFlags ::= TEXTUAL-CONVENTION
    STATUS        current
    DESCRIPTION
        ""
    SYNTAX        BITS
    {
        driveSecurityCapable(0),
        driveSecurityEnable(1)
    }

CucsStorageControllerFaultMonitoring ::= TEXTUAL-CONVENTION
    STATUS        current
    DESCRIPTION
        ""
    SYNTAX        INTEGER
    {
        supported(1),
        notSupported(2)
    }

CucsStorageControllerId ::= TEXTUAL-CONVENTION
    STATUS        current
    DESCRIPTION
        ""
    SYNTAX        Gauge32 (1..64)

CucsStorageControllerPinnedCacheStatus ::= TEXTUAL-CONVENTION
    STATUS        current
    DESCRIPTION
        ""
    SYNTAX        INTEGER
    {
        unknown(0),
        enabled(1),
        disabled(2)
    }

CucsStorageControllerAdminActionTrigger ::= TEXTUAL-CONVENTION
    STATUS        current
    DESCRIPTION
        ""
    SYNTAX        INTEGER
    {
        remoteTrigger(0),
        importForeignConfiguration(1),
        clearForeignConfiguration(2),
        unpinCacheAll(3),
        skipInitialConfig(4),
        clearBootConfiguration(5),
        unlockDisk(6),
        disableSecurity(7),
        modifyKey(8),
        enableSecurity(9)
    }

CucsStorageControllerFlags ::= TEXTUAL-CONVENTION
    STATUS        current
    DESCRIPTION
        ""
    SYNTAX        BITS
    {
        driveSecurityCapable(0),
        driveSecurityEnable(1)
    }

CucsStorageControllerForm ::= TEXTUAL-CONVENTION
    STATUS        current
    DESCRIPTION
        ""
    SYNTAX        INTEGER
    {
        none(0),
        onBoard(1),
        mezzanine(2),
        pci(3),
        embedded(4)
    }

CucsStorageControllerId ::= TEXTUAL-CONVENTION
    STATUS        current
    DESCRIPTION
        ""
    SYNTAX        INTEGER
    {
        all(0)
    }

CucsStorageControllerJBODMode ::= TEXTUAL-CONVENTION
    STATUS        current
    DESCRIPTION
        ""
    SYNTAX        INTEGER
    {
        unknown(0),
        disabled(1),
        enabled(2)
    }

CucsStorageControllerMode ::= TEXTUAL-CONVENTION
    STATUS        current
    DESCRIPTION
        ""
    SYNTAX        INTEGER
    {
        unknown(0),
        raid(1),
        hba(2),
        ahci(3),
        swraid(4),
        nvme(5),
        phba(6),
        praid(7),
        xsds(8),
        m2hwraid(9),
        sas4(10)
    }

CucsStorageControllerRefControllerId ::= TEXTUAL-CONVENTION
    STATUS        current
    DESCRIPTION
        ""
    SYNTAX        Gauge32 (1..2)

CucsStorageControllerRefControllerType ::= TEXTUAL-CONVENTION
    STATUS        current
    DESCRIPTION
        ""
    SYNTAX        INTEGER
    {
        unknown(0),
        sas(1),
        sata(2),
        flash(3),
        sd(4),
        pt(5),
        pch(6),
        external(7),
        nvme(8),
        hba(9),
        m2(10),
        fch(11)
    }

CucsStorageControllerRefServerId ::= TEXTUAL-CONVENTION
    STATUS        current
    DESCRIPTION
        ""
    SYNTAX        Gauge32 (1..2)

CucsStorageControllerStatus ::= TEXTUAL-CONVENTION
    STATUS        current
    DESCRIPTION
        ""
    SYNTAX        INTEGER
    {
        unknown(0),
        optimal(1),
        failed(2),
        unresponsive(3),
        degraded(4),
        unsupportedFwForOob(5),
        moderateFault(6),
        severeFault(7),
        flashFailed(8),
        unsupportedDrive(9)
    }

CucsStorageControllerSubType ::= TEXTUAL-CONVENTION
    STATUS        current
    DESCRIPTION
        ""
    SYNTAX        INTEGER
    {
        na(0),
        nvmeFront(1),
        nvmeRear(2),
        nvmeHhhl(3),
        nvmeMezz(4),
        nvmeM2(5),
        rde(6)
    }

CucsStorageControllerType ::= TEXTUAL-CONVENTION
    STATUS        current
    DESCRIPTION
        ""
    SYNTAX        INTEGER
    {
        unknown(0),
        sas(1),
        sata(2),
        flash(3),
        sd(4),
        pt(5),
        pch(6),
        external(7),
        nvme(8),
        hba(9),
        m2(10),
        fch(11)
    }

CucsStorageCtrlAdminState ::= TEXTUAL-CONVENTION
    STATUS        current
    DESCRIPTION
        ""
    SYNTAX        INTEGER
    {
        inService(1),
        inMaintenance(3),
        fullMaintenance(4)
    }

CucsStorageCtrlClusterState ::= TEXTUAL-CONVENTION
    STATUS        current
    DESCRIPTION
        ""
    SYNTAX        INTEGER
    {
        unknown(0),
        ok(1),
        degraded(2)
    }

CucsStorageCtrlConfigState ::= TEXTUAL-CONVENTION
    STATUS        current
    DESCRIPTION
        ""
    SYNTAX        INTEGER
    {
        unknown(0),
        ok(1),
        disruptive(2)
    }

CucsStorageCtrlHaState ::= TEXTUAL-CONVENTION
    STATUS        current
    DESCRIPTION
        ""
    SYNTAX        INTEGER
    {
        unknown(0),
        ready(1),
        notReady(2),
        degraded(3),
        failoverInProgress(4),
        electionFailed(5),
        offline(6)
    }

CucsStorageCtrlLeadership ::= TEXTUAL-CONVENTION
    STATUS        current
    DESCRIPTION
        ""
    SYNTAX        INTEGER
    {
        unknown(0),
        active(1),
        passive(2)
    }

CucsStorageCtrlStorageStatsThresholded ::= TEXTUAL-CONVENTION
    STATUS        current
    DESCRIPTION
        ""
    SYNTAX        BITS
    {
        cpuLoad(0),
        cpuLoadAvg(1),
        cpuLoadMax(2),
        cpuLoadMin(3),
        memoryUsage(4),
        memoryUsageAvg(5),
        memoryUsageMax(6),
        memoryUsageMin(7)
    }

CucsStorageCtrlStorageStatsHistThresholded ::= TEXTUAL-CONVENTION
    STATUS        current
    DESCRIPTION
        ""
    SYNTAX        BITS
    {
        cpuLoad(0),
        cpuLoadAvg(1),
        cpuLoadMax(2),
        cpuLoadMin(3),
        memoryUsage(4),
        memoryUsageAvg(5),
        memoryUsageMax(6),
        memoryUsageMin(7)
    }

CucsStorageDeployAction ::= TEXTUAL-CONVENTION
    STATUS        current
    DESCRIPTION
        ""
    SYNTAX        INTEGER
    {
        noAction(0),
        create(1),
        delete(2),
        modify(3),
        restore(4),
        replace(5),
        setOnline(6),
        setOffline(7),
        abortReplication(8)
    }

CucsStorageDeviceBridgeType ::= TEXTUAL-CONVENTION
    STATUS        current
    DESCRIPTION
        ""
    SYNTAX        INTEGER
    {
        unknown(0),
        stsb(1)
    }

CucsStorageDiskEnvStatsThresholded ::= TEXTUAL-CONVENTION
    STATUS        current
    DESCRIPTION
        ""
    SYNTAX        BITS
    {
        temperature(0),
        temperatureAvg(1),
        temperatureMax(2),
        temperatureMin(3),
        wearPercentage(4),
        wearPercentageAvg(5),
        wearPercentageMax(6),
        wearPercentageMin(7)
    }

CucsStorageDiskEnvStatsHistThresholded ::= TEXTUAL-CONVENTION
    STATUS        current
    DESCRIPTION
        ""
    SYNTAX        BITS
    {
        temperature(0),
        temperatureAvg(1),
        temperatureMax(2),
        temperatureMin(3),
        wearPercentage(4),
        wearPercentageAvg(5),
        wearPercentageMax(6),
        wearPercentageMin(7)
    }

CucsStorageDiskRole ::= TEXTUAL-CONVENTION
    STATUS        current
    DESCRIPTION
        ""
    SYNTAX        INTEGER
    {
        normal(0),
        dedHotSpare(1),
        globHotSpare(2),
        unknown(3)
    }

CucsStorageDisklessAction ::= TEXTUAL-CONVENTION
    STATUS        current
    DESCRIPTION
        ""
    SYNTAX        INTEGER
    {
        unspecified(0),
        yes(1),
        no(2)
    }

CucsStorageDrawerOpenState ::= TEXTUAL-CONVENTION
    STATUS        current
    DESCRIPTION
        ""
    SYNTAX        INTEGER
    {
        notApplicable(0),
        open(1),
        closed(2)
    }

CucsStorageDriveFlags ::= TEXTUAL-CONVENTION
    STATUS        current
    DESCRIPTION
        ""
    SYNTAX        BITS
    {
        securityCapable(0),
        securityEnabled(1),
        secured(2),
        locked(3)
    }

CucsStorageEnclosureId ::= TEXTUAL-CONVENTION
    STATUS        current
    DESCRIPTION
        ""
    SYNTAX        Gauge32 (1..2)

CucsStorageEnclosureAdminState ::= TEXTUAL-CONVENTION
    STATUS        current
    DESCRIPTION
        ""
    SYNTAX        INTEGER
    {
        acknowledged(0),
        remove(1),
        removing(2),
        removeFailed(3)
    }

CucsStorageEnclosureAssociation ::= TEXTUAL-CONVENTION
    STATUS        current
    DESCRIPTION
        ""
    SYNTAX        INTEGER
    {
        unknown(0),
        directAttached(1),
        expanderAttached(2),
        na(3)
    }

CucsStorageEnclosureDiskSlotEpAutoZoneCause ::= TEXTUAL-CONVENTION
    STATUS        current
    DESCRIPTION
        ""
    SYNTAX        INTEGER
    {
        none(0),
        sharingUnsupported(1),
        hddslotUnassigned(2),
        hotspareUnsupported(3),
        hddTrayInLieuOfServer2(4),
        mezzControllerInIoexpander(5),
        secondControllerAbsent(6)
    }

CucsStorageEnclosureDiskSlotEpDrivePath ::= TEXTUAL-CONVENTION
    STATUS        current
    DESCRIPTION
        ""
    SYNTAX        INTEGER
    {
        unknown(0),
        pathBoth(1),
        path0(2),
        path1(3),
        none(4)
    }

CucsStorageEnclosureDiskSlotEpOwnership ::= TEXTUAL-CONVENTION
    STATUS        current
    DESCRIPTION
        ""
    SYNTAX        INTEGER
    {
        unknown(0),
        unassigned(1),
        dedicated(2),
        shared(3),
        chassisSpare(4),
        chassisDedicatedSpare(5)
    }

CucsStorageEnclosureFsmCurrentFsm ::= TEXTUAL-CONVENTION
    STATUS        current
    DESCRIPTION
        ""
    SYNTAX        INTEGER
    {
        nop(0),
        removeEnclosure(2019)
    }

CucsStorageEnclosureFsmStageName ::= TEXTUAL-CONVENTION
    STATUS        current
    DESCRIPTION
        ""
    SYNTAX        INTEGER
    {
        nop(0),
        removeEnclosureBegin(2019),
        removeEnclosureValidateRemoval(2020),
        removeEnclosureUpdateStorageInvCMC(2021),
        removeEnclosureUpdateStorageInvCIMC(2022),
        removeEnclosurePollUpdateStorageInvCIMC(2023),
        removeEnclosureFail(2191),
        removeEnclosureSuccess(2192)
    }

CucsStorageEnclosureFsmTaskItem ::= TEXTUAL-CONVENTION
    STATUS        current
    DESCRIPTION
        ""
    SYNTAX        INTEGER
    {
        nop(0),
        removeEnclosure(2019)
    }

CucsStorageEpAccess ::= TEXTUAL-CONVENTION
    STATUS        current
    DESCRIPTION
        ""
    SYNTAX        INTEGER
    {
        readonly(1),
        admin(2)
    }

CucsStorageEpLinkState ::= TEXTUAL-CONVENTION
    STATUS        current
    DESCRIPTION
        ""
    SYNTAX        INTEGER
    {
        unknown(0),
        optimal(1),
        subOptimal(2),
        misconnect(3)
    }

CucsStorageEthLifSwitchId ::= TEXTUAL-CONVENTION
    STATUS        current
    DESCRIPTION
        ""
    SYNTAX        INTEGER
    {
        none(0),
        a(1),
        b(2),
        mgmt(3),
        aB(5),
        bA(6)
    }

CucsStorageEtherIfVlanType ::= TEXTUAL-CONVENTION
    STATUS        current
    DESCRIPTION
        ""
    SYNTAX        INTEGER
    {
        regular(0),
        default(1),
        native(2)
    }

CucsStorageExpanderState ::= TEXTUAL-CONVENTION
    STATUS        current
    DESCRIPTION
        ""
    SYNTAX        INTEGER
    {
        unknown(0),
        operable(1),
        inoperable(2),
        unreachable(3),
        degraded(4),
        notReady(5),
        resourceUnavailable(6),
        discovery(7),
        rebootPending(8)
    }

CucsStorageExtdConfigIssues ::= TEXTUAL-CONVENTION
    STATUS        current
    DESCRIPTION
        ""
    SYNTAX        BITS
    {
        multipleHybridslotConfig(0),
        incompleteHybridslotDiskConfig(1),
        unsupportedHybridSlotConfigChange(2),
        unsupportedSecurityKeyMigration(3),
        invalidLocalSecurityKey(4),
        controllerInArrayTransformation(5),
        driveSecurityPolicyMissing(6)
    }

CucsStorageFFCardHealth ::= TEXTUAL-CONVENTION
    STATUS        current
    DESCRIPTION
        ""
    SYNTAX        INTEGER
    {
        ffPhyHealthNa(0),
        ffPhyHealthOk(1),
        ffPhyUnhealthyRaid(2),
        ffPhyUnhealthyOther(3),
        ffPhyRaidSyncInProgress(4),
        ffPhyRaidOutOfSync(5)
    }

CucsStorageFFCardMode ::= TEXTUAL-CONVENTION
    STATUS        current
    DESCRIPTION
        ""
    SYNTAX        INTEGER
    {
        ffPhyDriveUnpairedPrimary(0),
        ffPhyDrivePrimary(1),
        ffPhyDriveSecondaryAct(2),
        ffPhyDriveSecondaryUnhealthy(3)
    }

CucsStorageFFCardSizeMismatch ::= TEXTUAL-CONVENTION
    STATUS        current
    DESCRIPTION
        ""
    SYNTAX        INTEGER
    {
        na(0),
        mismatch(1),
        match(2)
    }

CucsStorageFFCardState ::= TEXTUAL-CONVENTION
    STATUS        current
    DESCRIPTION
        ""
    SYNTAX        INTEGER
    {
        undefined(0),
        configured(1),
        initializing(2),
        active(3),
        ignored(4),
        failed(5),
        unknown(6)
    }

CucsStorageFFCardSync ::= TEXTUAL-CONVENTION
    STATUS        current
    DESCRIPTION
        ""
    SYNTAX        INTEGER
    {
        na(0),
        manual(1),
        auto(2),
        unknown(3)
    }

CucsStorageFFCardWriteEnable ::= TEXTUAL-CONVENTION
    STATUS        current
    DESCRIPTION
        ""
    SYNTAX        INTEGER
    {
        no(0),
        yes(1)
    }

CucsStorageFFControllerHealth ::= TEXTUAL-CONVENTION
    STATUS        current
    DESCRIPTION
        ""
    SYNTAX        INTEGER
    {
        ffchOk(0),
        ffchMetadataFailure(1),
        ffchErrorCardsAccessError(2),
        ffchErrorOldFirmwareRunning(3),
        ffchErrorMediaWriteProtected(4),
        ffchErrorInvalidSize(5),
        ffchErrorCardSizeMismatch(6),
        ffchInconsistentMetadata(7),
        ffchErrorSecondaryUnhealthyCard(8),
        ffchErrorSdCardNotConfigured(9),
        ffchErrorInconsistantMetadataIgnored(10),
        ffchErrorSd253WithUnOrSd247(11),
        ffchErrorRebootedDuringRebuild(12),
        ffchErrorSd247CardDetected(13),
        ffchFlexdErrorSdCardOpModeMismatch(14),
        ffchFlexdErrorSdOpModeMismatchWithUn(15),
        ffchFlexdErrorImSdUnhealthySdUnIgnored(16),
        ffchFlexdErrorImSdHealthySdUnIgnored(17),
        ffchFlexdErrorImSdCardsOpModeMismatch(18),
        ffchFlexdErrorSdCard0UnhealthyOpModeMismatch(19),
        ffchFlexdErrorSdCard0HealthyOpModeMismatch(20),
        ffchFlexdErrorSdCard1UnhealthyOpModeMismatch(21),
        ffchFlexdErrorSdCard1HealthyOpModeMismatch(22),
        ffchFlexdErrorImSd0IgnoredSd1(23),
        ffchFlexdErrorImSd0Sd1Ignored(24)
    }

CucsStorageFFControllerState ::= TEXTUAL-CONVENTION
    STATUS        current
    DESCRIPTION
        ""
    SYNTAX        INTEGER
    {
        ffcUninitalized(0),
        ffcSoftwareErr(1),
        ffcInit(2),
        ffcConfig(3),
        ffcWaitUser(4),
        ffcUsbDisconnecting(5),
        ffcUsbDisconnected(6),
        ffcUsbConnecting(7),
        ffcUsbConnected(8),
        ffcRebuilding(9),
        ffcFailed(10)
    }

CucsStorageFFDriveRemovable ::= TEXTUAL-CONVENTION
    STATUS        current
    DESCRIPTION
        ""
    SYNTAX        INTEGER
    {
        na(0),
        yes(1),
        no(2),
        noChange(3)
    }

CucsStorageFFDriveState ::= TEXTUAL-CONVENTION
    STATUS        current
    DESCRIPTION
        ""
    SYNTAX        INTEGER
    {
        nonraid(0),
        raid(1)
    }

CucsStorageFFDriveType ::= TEXTUAL-CONVENTION
    STATUS        current
    DESCRIPTION
        ""
    SYNTAX        INTEGER
    {
        unknown(0),
        scu(1),
        huu(2),
        hv(3),
        drivers(4)
    }

CucsStorageFFDriveVisible ::= TEXTUAL-CONVENTION
    STATUS        current
    DESCRIPTION
        ""
    SYNTAX        INTEGER
    {
        no(0),
        yes(1)
    }

CucsStorageFFFormatRunning ::= TEXTUAL-CONVENTION
    STATUS        current
    DESCRIPTION
        ""
    SYNTAX        INTEGER
    {
        na(0),
        yes(1),
        no(2)
    }

CucsStorageFFHasError ::= TEXTUAL-CONVENTION
    STATUS        current
    DESCRIPTION
        ""
    SYNTAX        INTEGER
    {
        error(0),
        noError(1)
    }

CucsStorageFFRAIDHealth ::= TEXTUAL-CONVENTION
    STATUS        current
    DESCRIPTION
        ""
    SYNTAX        INTEGER
    {
        ffrHealthNa(0),
        ffrHealthOk(1),
        ffrHealthDegraded(2),
        ffrHealthNotReporting(3)
    }

CucsStorageFFRAIDState ::= TEXTUAL-CONVENTION
    STATUS        current
    DESCRIPTION
        ""
    SYNTAX        INTEGER
    {
        ffrStateDisabled(0),
        ffrStateEnabledNotPaired(1),
        ffrStateEnabledPairedInvalidSecondary(2),
        ffrStateEnabledPairedInvalidPrimary(3),
        ffrStateEnabledPairedInvalidBoth(4),
        ffrStateEnabledPaired(5),
        ffrStateRaidMirroringDisabled(6)
    }

CucsStorageFFRWType ::= TEXTUAL-CONVENTION
    STATUS        current
    DESCRIPTION
        ""
    SYNTAX        INTEGER
    {
        readWrite(0),
        readOnly(1)
    }

CucsStorageFFRaidSyncSupport ::= TEXTUAL-CONVENTION
    STATUS        current
    DESCRIPTION
        ""
    SYNTAX        INTEGER
    {
        no(0),
        yes(1)
    }

CucsStorageFFSlotENUM ::= TEXTUAL-CONVENTION
    STATUS        current
    DESCRIPTION
        ""
    SYNTAX        INTEGER
    {
        na(0),
        n1(1),
        n2(2)
    }

CucsStorageFFType ::= TEXTUAL-CONVENTION
    STATUS        current
    DESCRIPTION
        ""
    SYNTAX        INTEGER
    {
        unknown(0),
        astoria(1),
        fx3s(2)
    }

CucsStorageFcZoningType ::= TEXTUAL-CONVENTION
    STATUS        current
    DESCRIPTION
        ""
    SYNTAX        INTEGER
    {
        none(0),
        sist(1),
        simt(2)
    }

CucsStorageFileSystemStatus ::= TEXTUAL-CONVENTION
    STATUS        current
    DESCRIPTION
        ""
    SYNTAX        INTEGER
    {
        unknown(0),
        clean(1),
        notClean(2),
        mounted(3),
        unmounted(4),
        cleanWithErrors(5)
    }

CucsStorageFlexFlashControllerId ::= TEXTUAL-CONVENTION
    STATUS        current
    DESCRIPTION
        ""
    SYNTAX        Gauge32 (1..64)

CucsStorageFlexFlashControllerFsmCurrentFsm ::= TEXTUAL-CONVENTION
    STATUS        current
    DESCRIPTION
        ""
    SYNTAX        INTEGER
    {
        nop(0),
        mopsReset(1605),
        mopsFormat(1607),
        mopsPair(1609)
    }

CucsStorageFlexFlashControllerFsmStageName ::= TEXTUAL-CONVENTION
    STATUS        current
    DESCRIPTION
        ""
    SYNTAX        INTEGER
    {
        nop(0),
        mopsResetBegin(1605),
        mopsResetReset(1606),
        mopsFormatBegin(1607),
        mopsFormatFormat(1608),
        mopsPairBegin(1609),
        mopsPairPair(1610),
        mopsFormatFail(1624),
        mopsFormatSuccess(1625),
        mopsPairFail(1626),
        mopsPairSuccess(1627),
        mopsResetFail(1628),
        mopsResetSuccess(1629)
    }

CucsStorageFlexFlashControllerFsmTaskItem ::= TEXTUAL-CONVENTION
    STATUS        current
    DESCRIPTION
        ""
    SYNTAX        INTEGER
    {
        nop(0),
        mopsReset(1605),
        mopsFormat(1607),
        mopsPair(1609)
    }

CucsStorageGlobalConfigIssues ::= TEXTUAL-CONVENTION
    STATUS        current
    DESCRIPTION
        ""
    SYNTAX        BITS
    {
        globalArrayStorageArrayNotOpted(0),
        domainGroupMissing(1),
        missingArrayAutoConfigRef(2),
        missingArrayAutoConfigPolicy(3),
        missingQualifier(4),
        matchingQualifierError(5),
        storageBladeAlreadyInUse(6),
        storageBladeNotInDiscoveryMode(7)
    }

CucsStorageHddMotherBoardTempStatsThresholded ::= TEXTUAL-CONVENTION
    STATUS        current
    DESCRIPTION
        ""
    SYNTAX        BITS
    {
        leftInletTemp(0),
        leftInletTempAvg(1),
        leftInletTempMax(2),
        leftInletTempMin(3),
        leftOutletTemp(4),
        leftOutletTempAvg(5),
        leftOutletTempMax(6),
        leftOutletTempMin(7),
        rightInletTemp(8),
        rightInletTempAvg(9),
        rightInletTempMax(10),
        rightInletTempMin(11),
        rightOutletTemp(12),
        rightOutletTempAvg(13),
        rightOutletTempMax(14),
        rightOutletTempMin(15)
    }

CucsStorageHddMotherBoardTempStatsHistThresholded ::= TEXTUAL-CONVENTION
    STATUS        current
    DESCRIPTION
        ""
    SYNTAX        BITS
    {
        leftInletTemp(0),
        leftInletTempAvg(1),
        leftInletTempMax(2),
        leftInletTempMin(3),
        leftOutletTemp(4),
        leftOutletTempAvg(5),
        leftOutletTempMax(6),
        leftOutletTempMin(7),
        rightInletTemp(8),
        rightInletTempAvg(9),
        rightInletTempMax(10),
        rightInletTempMin(11),
        rightOutletTemp(12),
        rightOutletTempAvg(13),
        rightOutletTempMax(14),
        rightOutletTempMin(15)
    }

CucsStorageHybridSlotDriveType ::= TEXTUAL-CONVENTION
    STATUS        current
    DESCRIPTION
        ""
    SYNTAX        INTEGER
    {
        bayEmpty(0),
        sas(1),
        sata(2),
        u2Nvme(3),
        u3Nvme(4)
    }

CucsStorageHybridSlotMode ::= TEXTUAL-CONVENTION
    STATUS        current
    DESCRIPTION
        ""
    SYNTAX        INTEGER
    {
        unknown(0),
        cpuDirectAttached(1),
        controllerAttached(2)
    }

CucsStorageIOType ::= TEXTUAL-CONVENTION
    STATUS        current
    DESCRIPTION
        ""
    SYNTAX        INTEGER
    {
        unknown(0),
        direct(1),
        cached(2)
    }

CucsStorageIScsiInitiatorEpProt ::= TEXTUAL-CONVENTION
    STATUS        current
    DESCRIPTION
        ""
    SYNTAX        INTEGER
    {
        derived(0),
        fc(1),
        iscsi(2)
    }

CucsStorageIniGroupOperProtocol ::= TEXTUAL-CONVENTION
    STATUS        current
    DESCRIPTION
        ""
    SYNTAX        INTEGER
    {
        derived(0),
        fc(1),
        iscsi(2)
    }

CucsStorageIniGroupOwner ::= TEXTUAL-CONVENTION
    STATUS        current
    DESCRIPTION
        ""
    SYNTAX        INTEGER
    {
        unknown(0),
        physical(1),
        policy(2),
        logical(4),
        initiatorPolicy(7),
        connPolicy(8)
    }

CucsStorageIniGroupProtocol ::= TEXTUAL-CONVENTION
    STATUS        current
    DESCRIPTION
        ""
    SYNTAX        INTEGER
    {
        derived(0),
        fc(1),
        iscsi(2)
    }

CucsStorageKeyType ::= TEXTUAL-CONVENTION
    STATUS        current
    DESCRIPTION
        ""
    SYNTAX        INTEGER
    {
        initiator(1),
        target(2)
    }

CucsStorageLearnCycleRequested ::= TEXTUAL-CONVENTION
    STATUS        current
    DESCRIPTION
        ""
    SYNTAX        INTEGER
    {
        unknown(0),
        true(1),
        false(2)
    }

CucsStorageLearnMode ::= TEXTUAL-CONVENTION
    STATUS        current
    DESCRIPTION
        ""
    SYNTAX        INTEGER
    {
        unknown(0),
        auto(1),
        disabled(2),
        warn(3)
    }

CucsStorageLinkSpeed ::= TEXTUAL-CONVENTION
    STATUS        current
    DESCRIPTION
        ""
    SYNTAX        INTEGER
    {
        unknown(0),
        n15Gbps(1),
        n3Gbps(2),
        n6Gbps(3),
        n12Gbps(4),
        n24Gbps(5),
        n25Gtps(6),
        unsupportedDevice(7),
        n8Gtps(8),
        na(9)
    }

CucsStorageLocalDiskDiscoveredPath ::= TEXTUAL-CONVENTION
    STATUS        current
    DESCRIPTION
        ""
    SYNTAX        INTEGER
    {
        default(0),
        oob(1),
        ib(2)
    }

CucsStorageLocalDiskConfigFlexFlashRAIDReportingState ::= TEXTUAL-CONVENTION
    STATUS        current
    DESCRIPTION
        ""
    SYNTAX        INTEGER
    {
        disable(0),
        enable(1)
    }

CucsStorageLocalDiskConfigFlexFlashRemovableState ::= TEXTUAL-CONVENTION
    STATUS        current
    DESCRIPTION
        ""
    SYNTAX        INTEGER
    {
        na(0),
        yes(1),
        no(2),
        noChange(3)
    }

CucsStorageLocalDiskConfigFlexFlashState ::= TEXTUAL-CONVENTION
    STATUS        current
    DESCRIPTION
        ""
    SYNTAX        INTEGER
    {
        disable(0),
        enable(1)
    }

CucsStorageLocalDiskFsmCurrentFsm ::= TEXTUAL-CONVENTION
    STATUS        current
    DESCRIPTION
        ""
    SYNTAX        INTEGER
    {
        nop(0),
        updateLocalDisk(2156)
    }

CucsStorageLocalDiskFsmStageName ::= TEXTUAL-CONVENTION
    STATUS        current
    DESCRIPTION
        ""
    SYNTAX        INTEGER
    {
        nop(0),
        updateLocalDiskBegin(2156),
        updateLocalDiskPowerOffServers(2157),
        updateLocalDiskServersPowerOffCompletion(2158),
        updateLocalDiskUpdate(2159),
        updateLocalDiskPollUpdateStatus(2160),
        updateLocalDiskFail(2193),
        updateLocalDiskSuccess(2194)
    }

CucsStorageLocalDiskFsmTaskFlags ::= TEXTUAL-CONVENTION
    STATUS        current
    DESCRIPTION
        ""
    SYNTAX        BITS
    {
        samDmeStorageLocalDiskUpdateLocalDiskActivate(5)
    }

CucsStorageLocalDiskFsmTaskItem ::= TEXTUAL-CONVENTION
    STATUS        current
    DESCRIPTION
        ""
    SYNTAX        INTEGER
    {
        nop(0),
        updateLocalDisk(2156)
    }

CucsStorageLocalDiskMode ::= TEXTUAL-CONVENTION
    STATUS        current
    DESCRIPTION
        ""
    SYNTAX        INTEGER
    {
        noLocalStorage(1),
        singleDisk(2),
        dualDisk(3),
        raidStriped(4),
        raidMirrored(5),
        bestEffortMirrored(6),
        bestEffortStriped(7),
        anyConfiguration(8),
        noRaid(9),
        raidStripedParity(10),
        raidStripedDualParity(11),
        raidMirroredStriped(12),
        bestEffortStripedParity(13),
        bestEffortStripedDualParity(14),
        bestEffortMirroredStriped(15),
        raidStripedParityStriped(16),
        raidStripedDualParityStriped(17)
    }

CucsStorageLocalDiskPartitionType ::= TEXTUAL-CONVENTION
    STATUS        current
    DESCRIPTION
        ""
    SYNTAX        INTEGER
    {
        none(1),
        swap(2),
        ext2(3),
        ext3(4),
        ntfs(5),
        fat32(6)
    }

CucsStorageLunObjType ::= TEXTUAL-CONVENTION
    STATUS        current
    DESCRIPTION
        ""
    SYNTAX        INTEGER
    {
        regular(0),
        snapshot(1),
        replica(2)
    }

CucsStorageLunSetLunType ::= TEXTUAL-CONVENTION
    STATUS        current
    DESCRIPTION
        ""
    SYNTAX        INTEGER
    {
        unspecified(0),
        simple(1),
        jbod(2),
        stripe(3)
    }

CucsStorageLunStatusType ::= TEXTUAL-CONVENTION
    STATUS        current
    DESCRIPTION
        ""
    SYNTAX        INTEGER
    {
        undefined(0),
        online(1),
        offline(2)
    }

CucsStorageLunType ::= TEXTUAL-CONVENTION
    STATUS        current
    DESCRIPTION
        ""
    SYNTAX        INTEGER
    {
        unspecified(0),
        simple(1),
        mirror(2),
        stripe(3),
        raid(4),
        stripeParity(5),
        stripeDualParity(6),
        mirrorStripe(7),
        stripeParityStripe(8),
        stripeDualParityStripe(9)
    }

CucsStorageMembershipStatus ::= TEXTUAL-CONVENTION
    STATUS        current
    DESCRIPTION
        ""
    SYNTAX        INTEGER
    {
        unknown(0),
        down(1),
        up(2),
        hotStandby(3)
    }

CucsStorageMiniStorageId ::= TEXTUAL-CONVENTION
    STATUS        current
    DESCRIPTION
        ""
    SYNTAX        Gauge32 (1..64)

CucsStorageNvmeStatsThresholded ::= TEXTUAL-CONVENTION
    STATUS        current
    DESCRIPTION
        ""
    SYNTAX        BITS
    {
        driveLifeUsedPercentage(0),
        driveLifeUsedPercentageAvg(1),
        driveLifeUsedPercentageMax(2),
        driveLifeUsedPercentageMin(3),
        temperature(4),
        temperatureAvg(5),
        temperatureMax(6),
        temperatureMin(7)
    }

CucsStorageNvmeStatsHistThresholded ::= TEXTUAL-CONVENTION
    STATUS        current
    DESCRIPTION
        ""
    SYNTAX        BITS
    {
        driveLifeUsedPercentage(0),
        driveLifeUsedPercentageAvg(1),
        driveLifeUsedPercentageMax(2),
        driveLifeUsedPercentageMin(3),
        temperature(4),
        temperatureAvg(5),
        temperatureMax(6),
        temperatureMin(7)
    }

CucsStorageNvmeSwitchType ::= TEXTUAL-CONVENTION
    STATUS        current
    DESCRIPTION
        ""
    SYNTAX        INTEGER
    {
        unknown(0),
        directAttached(1),
        hhhl(2),
        mswitch(3)
    }

CucsStorageOnBoardMemoryPresent ::= TEXTUAL-CONVENTION
    STATUS        current
    DESCRIPTION
        ""
    SYNTAX        INTEGER
    {
        unknown(0),
        yes(1),
        no(2)
    }

CucsStorageOnboardDeviceType ::= TEXTUAL-CONVENTION
    STATUS        current
    DESCRIPTION
        ""
    SYNTAX        INTEGER
    {
        unknown(0),
        sbr(1),
        cpld(2),
        sasExpRegFwDev(3),
        psoc(4)
    }

CucsStorageOperIssues ::= TEXTUAL-CONVENTION
    STATUS        current
    DESCRIPTION
        ""
    SYNTAX        BITS
    {
        invalidConfig(0),
        invictaUptimeOutOfSync(1)
    }

CucsStorageOperState ::= TEXTUAL-CONVENTION
    STATUS        current
    DESCRIPTION
        ""
    SYNTAX        INTEGER
    {
        ok(0),
        misconfigured(1)
    }

CucsStorageOperatingModeType ::= TEXTUAL-CONVENTION
    STATUS        current
    DESCRIPTION
        ""
    SYNTAX        INTEGER
    {
        unknown(0),
        mirror(1),
        util(2)
    }

CucsStorageOperationRequestType ::= TEXTUAL-CONVENTION
    STATUS        current
    DESCRIPTION
        ""
    SYNTAX        INTEGER
    {
        unknown(0),
        format(1),
        reset(2),
        pair(3),
        unpair(4)
    }

CucsStorageOperationState ::= TEXTUAL-CONVENTION
    STATUS        current
    DESCRIPTION
        ""
    SYNTAX        INTEGER
    {
        unknown(0),
        inProgress(1),
        completed(2),
        failed(3),
        triggered(4),
        ready(5),
        notPerformed(6),
        updating(7)
    }

CucsStorageOperationStateType ::= TEXTUAL-CONVENTION
    STATUS        current
    DESCRIPTION
        ""
    SYNTAX        INTEGER
    {
        partitionNonMirrored(0),
        partitionMirrored(1),
        partitionMirroredSyncing(2),
        partitionMirroredErasing(3),
        partitionMirroredUpdating(4),
        partitionNonMirroredUpdating(5),
        partitionNonMirroredErasing(6),
        partitionMirroredSyncingFail(7),
        partitionMirroredErasingFail(8),
        partitionMirroredUpdatingFail(9),
        partitionNonMirroredUpdatingFail(10),
        partitionNonMirroredErasingFail(11),
        partitionMirroredSyncingSuccess(12),
        partitionMirroredErasingSuccess(13),
        partitionMirroredUpdatingSuccess(14),
        partitionNonMirroredUpdatingSuccess(15),
        partitionNonMirroredErasingSuccess(16),
        unknown(17)
    }

CucsStorageOperationType ::= TEXTUAL-CONVENTION
    STATUS        current
    DESCRIPTION
        ""
    SYNTAX        INTEGER
    {
        reconstruction(0),
        relearning(1),
        patrolRead(2),
        consistencyCheck(3),
        rebuild(4),
        initialization(5),
        copyback(6)
    }

CucsStorageOptionRomBootStatus ::= TEXTUAL-CONVENTION
    STATUS        current
    DESCRIPTION
        ""
    SYNTAX        INTEGER
    {
        unknown(0),
        enabled(1),
        disabled(2)
    }

CucsStoragePDriveConfig ::= TEXTUAL-CONVENTION
    STATUS        current
    DESCRIPTION
        ""
    SYNTAX        INTEGER
    {
        yes(1),
        no(2)
    }

CucsStoragePDriveStatus ::= TEXTUAL-CONVENTION
    STATUS        current
    DESCRIPTION
        ""
    SYNTAX        INTEGER
    {
        unknown(0),
        online(1),
        unconfiguredGood(2),
        globalHotSpare(3),
        dedicatedHotSpare(4),
        jbod(5),
        offline(6),
        rebuilding(7),
        copyback(8),
        failed(9),
        unconfiguredBad(10),
        predictiveFailure(11),
        disabledForRemoval(12),
        foreignConfiguration(13),
        zeroing(14),
        good(15),
        bad(16),
        lockedForeignConfiguration(17),
        selfTestFailed(18)
    }

CucsStoragePartitionFsmCurrentFsm ::= TEXTUAL-CONVENTION
    STATUS        current
    DESCRIPTION
        ""
    SYNTAX        INTEGER
    {
        nop(0),
        deployStorage(1630),
        scrubRAIDGroup(1677)
    }

CucsStoragePartitionFsmStageName ::= TEXTUAL-CONVENTION
    STATUS        current
    DESCRIPTION
        ""
    SYNTAX        INTEGER
    {
        nop(0),
        deployStorageBegin(1630),
        deployStorageConfigDisk(1631),
        deployStorageConfigLun(1632),
        deployStorageVerifyConfig(1633),
        deployStorageVerifySnapshotConfig(1634),
        deployStorageVerifyReplicationConfig(1635),
        scrubRAIDGroupBegin(1677),
        scrubRAIDGroupPerformErase(1678),
        scrubRAIDGroupWaitForEraseCompletion(1679),
        deployStorageFail(1829),
        deployStorageSuccess(1830),
        scrubRAIDGroupFail(1831),
        scrubRAIDGroupSuccess(1832)
    }

CucsStoragePartitionFsmTaskFlags ::= TEXTUAL-CONVENTION
    STATUS        current
    DESCRIPTION
        ""
    SYNTAX        BITS
    {
        samDmeStoragePartitionDeployStorageLunConfig(14),
        samDmeStoragePartitionDeployStorageDiskConfig(15)
    }

CucsStoragePartitionFsmTaskItem ::= TEXTUAL-CONVENTION
    STATUS        current
    DESCRIPTION
        ""
    SYNTAX        INTEGER
    {
        nop(0),
        deployStorage(1630),
        scrubRAIDGroup(1677)
    }

CucsStoragePathHA ::= TEXTUAL-CONVENTION
    STATUS        current
    DESCRIPTION
        ""
    SYNTAX        BITS
    {
        initiator(0),
        target(1),
        fabric(2)
    }

CucsStoragePhysicalHolder ::= TEXTUAL-CONVENTION
    STATUS        current
    DESCRIPTION
        ""
    SYNTAX        INTEGER
    {
        unknown(0),
        hddMotherBoard(1),
        hddExpansionTray(2),
        dedicatedRearSsdEnclosure(3),
        sbNvmeEnclosure(4),
        ioeNvmeEnclosure(5),
        serverFrontLoad(6),
        serverPch(7),
        serverNvme(8),
        serverRear(9),
        siocNvmeEnclosure(10),
        serverMid(11)
    }

CucsStoragePowerState ::= TEXTUAL-CONVENTION
    STATUS        current
    DESCRIPTION
        ""
    SYNTAX        INTEGER
    {
        unknown(0),
        active(1),
        powersave(2),
        transitioning(3),
        off(4),
        na(5)
    }

CucsStorageProcessorOperState ::= TEXTUAL-CONVENTION
    STATUS        current
    DESCRIPTION
        ""
    SYNTAX        INTEGER
    {
        undefined(0),
        online(1),
        offline(2),
        inMaintenance(3),
        fullMaintenance(4),
        computeDegraded(5),
        clusterDegraded(6)
    }

CucsStorageProcessorFsmCurrentFsm ::= TEXTUAL-CONVENTION
    STATUS        current
    DESCRIPTION
        ""
    SYNTAX        INTEGER
    {
        nop(0),
        discoverSystem(1636),
        enterMaintenance(1644),
        exitMaintenance(1649),
        deploySystem(1654),
        undeploySystem(1663),
        haTakeOver(1675)
    }

CucsStorageProcessorFsmStageName ::= TEXTUAL-CONVENTION
    STATUS        current
    DESCRIPTION
        ""
    SYNTAX        INTEGER
    {
        nop(0),
        discoverSystemBegin(1636),
        discoverSystemInitiatePollBMCLocal(1637),
        discoverSystemInitiatePollBMCRemote(1638),
        discoverSystemWaitForOSStatus(1639),
        discoverSystemConnectSMELocal(1640),
        discoverSystemConnectSMERemote(1641),
        discoverSystemWaitForSMEConnection(1642),
        discoverSystemWaitForInventory(1643),
        enterMaintenanceBegin(1644),
        enterMaintenanceDisableStorageTarget(1645),
        enterMaintenanceWaitForServerShutdown(1646),
        enterMaintenancePowerOff(1647),
        enterMaintenanceSlotPowerCycle(1648),
        exitMaintenanceBegin(1649),
        exitMaintenanceWaitForHAQuorum(1650),
        exitMaintenanceWaitForServerPowerUp(1651),
        exitMaintenanceWaitForSMEConnection(1652),
        exitMaintenanceEnableStorageTarget(1653),
        deploySystemBegin(1654),
        deploySystemPowerOn(1655),
        deploySystemConnectSMELocal(1656),
        deploySystemConnectSMERemote(1657),
        deploySystemConfigHAState(1658),
        deploySystemConfigNetwork(1659),
        deploySystemConfigPlatform(1660),
        deploySystemConfigStorageTargetIdentity(1661),
        deploySystemConfigStorageReplicationService(1662),
        undeploySystemBegin(1663),
        undeploySystemDisableStorageTarget(1664),
        undeploySystemWaitForServerShutdown(1665),
        undeploySystemPowerOff(1666),
        undeploySystemSlotPowerCycle(1667),
        undeploySystemUndeployStorage(1668),
        undeploySystemWaitForUndeployStorage(1669),
        undeploySystemUndeployTargetIdentity(1670),
        undeploySystemUndeployPlatform(1671),
        undeploySystemUndeployNetwork(1672),
        undeploySystemDisassocStorageController(1673),
        undeploySystemWaitForDisassocCompletion(1674),
        haTakeOverBegin(1675),
        haTakeOverPerformHaTakeOver(1676),
        deploySystemFail(1833),
        deploySystemSuccess(1834),
        discoverSystemFail(1835),
        discoverSystemSuccess(1836),
        enterMaintenanceFail(1837),
        enterMaintenanceSuccess(1838),
        exitMaintenanceFail(1839),
        exitMaintenanceSuccess(1840),
        haTakeOverFail(1841),
        haTakeOverSuccess(1842),
        undeploySystemFail(1843),
        undeploySystemSuccess(1844)
    }

CucsStorageProcessorFsmTaskFlags ::= TEXTUAL-CONVENTION
    STATUS        current
    DESCRIPTION
        ""
    SYNTAX        BITS
    {
        samDmeStorageProcessorDeploySystemHostConfig(16),
        samDmeStorageProcessorDeploySystemSupInstall(17),
        samDmeStorageProcessorDeploySystemSupConfig(18),
        samDmeStorageProcessorDeploySystemSaInstall(19),
        samDmeStorageProcessorDeploySystemSaConfig(20),
        samDmeStorageProcessorUndeploySystemSaUnconfig(21)
    }

CucsStorageProcessorFsmTaskItem ::= TEXTUAL-CONVENTION
    STATUS        current
    DESCRIPTION
        ""
    SYNTAX        INTEGER
    {
        nop(0),
        discoverSystem(1636),
        enterMaintenance(1644),
        exitMaintenance(1649),
        deploySystem(1654),
        undeploySystem(1663),
        haTakeOver(1675)
    }

CucsStorageProtocol ::= TEXTUAL-CONVENTION
    STATUS        current
    DESCRIPTION
        ""
    SYNTAX        INTEGER
    {
        derived(0),
        fc(1),
        iscsi(2)
    }

CucsStorageRaidBatteryOperabilityQualifier ::= TEXTUAL-CONVENTION
    STATUS        current
    DESCRIPTION
        ""
    SYNTAX        INTEGER
    {
        unknown(0)
    }

CucsStorageRaidType ::= TEXTUAL-CONVENTION
    STATUS        current
    DESCRIPTION
        ""
    SYNTAX        BITS
    {
        raid0(0),
        raid1(1),
        raid5(2),
        raid6(3),
        raid00(4),
        raid10(5),
        raid50(6),
        raid60(7)
    }

CucsStorageReadType ::= TEXTUAL-CONVENTION
    STATUS        current
    DESCRIPTION
        ""
    SYNTAX        INTEGER
    {
        unknown(0),
        readAhead(1),
        normal(2)
    }

CucsStorageRemoteDiskAdminActionTrigger ::= TEXTUAL-CONVENTION
    STATUS        current
    DESCRIPTION
        ""
    SYNTAX        INTEGER
    {
        remoteTrigger(0),
        jbod(1),
        unconfiguredGood(2),
        prepareForRemoval(4),
        undoPrepareForRemoval(5),
        globalHotSpare(6),
        dedicatedHotSpare(7),
        removeHotSpare(8),
        ledOn(9),
        ledOff(10),
        enableSecurity(11),
        clearSecureDrive(12),
        clearSecureForeignConfigDrive(13),
        unlockForeignDrive(14)
    }

CucsStorageRemoteStorageAdminTrigger ::= TEXTUAL-CONVENTION
    STATUS        current
    DESCRIPTION
        ""
    SYNTAX        INTEGER
    {
        remoteTrigger(0),
        rediscover(1),
        resetToFactory(2),
        discovered(3),
        remove(4),
        migrate(5),
        decommission(6)
    }

CucsStorageRemoteVirtualDriveAdminActionTrigger ::= TEXTUAL-CONVENTION
    STATUS        current
    DESCRIPTION
        ""
    SYNTAX        INTEGER
    {
        remoteTrigger(0),
        online(1),
        offline(2),
        delete(3),
        restore(4),
        degraded(5),
        transportReady(6),
        clearTransportReady(7),
        hide(8),
        unhide(9),
        secureDriveGroup(10)
    }

CucsStorageRemoteVirtualDriveRefAdminActionTrigger ::= TEXTUAL-CONVENTION
    STATUS        current
    DESCRIPTION
        ""
    SYNTAX        INTEGER
    {
        remoteTrigger(0),
        online(1),
        undeployed(4)
    }

CucsStorageReplicationActionType ::= TEXTUAL-CONVENTION
    STATUS        current
    DESCRIPTION
        ""
    SYNTAX        INTEGER
    {
        policy(1),
        manual(2)
    }

CucsStorageReplicationCtxLunCfgAction ::= TEXTUAL-CONVENTION
    STATUS        current
    DESCRIPTION
        ""
    SYNTAX        INTEGER
    {
        triggered(0),
        delete(1),
        online(2),
        offline(3),
        restore(10)
    }

CucsStorageReplicationPairErrorCode ::= TEXTUAL-CONVENTION
    STATUS        current
    DESCRIPTION
        ""
    SYNTAX        INTEGER
    {
        none(0),
        success(1),
        tcpConnectionFailed(101),
        unsupportedAsyncrepProtocolVer(102),
        incorrectSharedSecretKey(103),
        notOnAllowList(104),
        failedToCreateTarget(105),
        failedToIncreaseSize(106),
        failedToReplicateMetadata(107),
        lostConnection(108),
        canceledByUser(109),
        internalError(110)
    }

CucsStorageReplicationPairState ::= TEXTUAL-CONVENTION
    STATUS        current
    DESCRIPTION
        ""
    SYNTAX        INTEGER
    {
        online(0),
        offline(1)
    }

CucsStorageReplicationPeerStatus ::= TEXTUAL-CONVENTION
    STATUS        current
    DESCRIPTION
        ""
    SYNTAX        INTEGER
    {
        idle(0),
        replicationInProgress(1),
        restoreInProgress(2)
    }

CucsStorageSasExpanderConnectionManagement ::= TEXTUAL-CONVENTION
    STATUS        current
    DESCRIPTION
        ""
    SYNTAX        INTEGER
    {
        disabled(0),
        enabled(1),
        unknown(2),
        default(3)
    }

CucsStorageSasLinkDescriptorControllerId ::= TEXTUAL-CONVENTION
    STATUS        current
    DESCRIPTION
        ""
    SYNTAX        Gauge32 (1..2)

CucsStorageSasLinkDescriptorControllerType ::= TEXTUAL-CONVENTION
    STATUS        current
    DESCRIPTION
        ""
    SYNTAX        INTEGER
    {
        unknown(0),
        sas(1),
        sata(2),
        flash(3),
        sd(4),
        pt(5),
        pch(6),
        external(7),
        nvme(8),
        hba(9),
        m2(10),
        fch(11)
    }

CucsStorageSasLinkDescriptorServerId ::= TEXTUAL-CONVENTION
    STATUS        current
    DESCRIPTION
        ""
    SYNTAX        Gauge32 (1..2)

CucsStorageSasUpLinkControllerId ::= TEXTUAL-CONVENTION
    STATUS        current
    DESCRIPTION
        ""
    SYNTAX        Gauge32 (1..2)

CucsStorageSasUpLinkControllerType ::= TEXTUAL-CONVENTION
    STATUS        current
    DESCRIPTION
        ""
    SYNTAX        INTEGER
    {
        unknown(0),
        sas(1),
        sata(2),
        flash(3),
        sd(4),
        pt(5),
        pch(6),
        external(7),
        nvme(8),
        hba(9),
        m2(10),
        fch(11)
    }

CucsStorageSasUpLinkServerId ::= TEXTUAL-CONVENTION
    STATUS        current
    DESCRIPTION
        ""
    SYNTAX        Gauge32 (1..2)

CucsStorageScsiDesignatorType ::= TEXTUAL-CONVENTION
    STATUS        current
    DESCRIPTION
        ""
    SYNTAX        INTEGER
    {
        t10(1),
        eui64(2),
        naa(3),
        md5(7),
        scsiName(8)
    }

CucsStorageScsiLunCtxLunCfgAction ::= TEXTUAL-CONVENTION
    STATUS        current
    DESCRIPTION
        ""
    SYNTAX        INTEGER
    {
        triggered(0),
        delete(1),
        online(2),
        offline(3),
        createSnapshot(4),
        createReplication(5),
        abortReplication(6),
        enableReplication(7),
        disableReplication(8),
        restore(10)
    }

CucsStorageSelectionDecisionType ::= TEXTUAL-CONVENTION
    STATUS        current
    DESCRIPTION
        ""
    SYNTAX        INTEGER
    {
        unspecified(0),
        selectLun(1),
        normalDisk(2),
        dedicatedHotSpare(3),
        globalHotSpare(4),
        useRemainingSpace(5),
        shareDiskGroup(6),
        useRemainingDisk(7),
        affinity(8),
        verifyResources(9),
        verifyVirtualDriveConfig(10),
        verifyDiskgroupConfig(11),
        verifyControllerConfig(12),
        verifyLunConfig(13),
        verifyDiskConfig(14),
        verifyRaidConfig(15),
        verifyStripSizeConfig(16)
    }

CucsStorageSelectionResultType ::= TEXTUAL-CONVENTION
    STATUS        current
    DESCRIPTION
        ""
    SYNTAX        INTEGER
    {
        unspecified(0),
        succeeded(1),
        failed(2),
        dataLoss(3)
    }

CucsStorageSnapshotAdminState ::= TEXTUAL-CONVENTION
    STATUS        current
    DESCRIPTION
        ""
    SYNTAX        INTEGER
    {
        undefined(0),
        create(1),
        createLunReplica(2),
        setReplicationOnline(3),
        setReplicationOffline(4),
        replicationRestore(5),
        abortReplication(6)
    }

CucsStorageSnapshotCtxLunCfgAction ::= TEXTUAL-CONVENTION
    STATUS        current
    DESCRIPTION
        ""
    SYNTAX        INTEGER
    {
        triggered(0),
        delete(1),
        online(2),
        offline(3),
        restoreSnapshot(9)
    }

CucsStorageSsdHealthStatsThresholded ::= TEXTUAL-CONVENTION
    STATUS        current
    DESCRIPTION
        ""
    SYNTAX        BITS
    {
        percentageLifeLeft(0),
        percentageLifeLeftAvg(1),
        percentageLifeLeftMax(2),
        percentageLifeLeftMin(3),
        powerCycleCount(4),
        powerCycleCountAvg(5),
        powerCycleCountMax(6),
        powerCycleCountMin(7),
        powerOnHours(8),
        powerOnHoursAvg(9),
        powerOnHoursMax(10),
        powerOnHoursMin(11),
        wearStatusInDays(12),
        wearStatusInDaysAvg(13),
        wearStatusInDaysMax(14),
        wearStatusInDaysMin(15)
    }

CucsStorageSsdHealthStatsHistThresholded ::= TEXTUAL-CONVENTION
    STATUS        current
    DESCRIPTION
        ""
    SYNTAX        BITS
    {
        percentageLifeLeft(0),
        percentageLifeLeftAvg(1),
        percentageLifeLeftMax(2),
        percentageLifeLeftMin(3),
        powerCycleCount(4),
        powerCycleCountAvg(5),
        powerCycleCountMax(6),
        powerCycleCountMin(7),
        powerOnHours(8),
        powerOnHoursAvg(9),
        powerOnHoursMax(10),
        powerOnHoursMin(11),
        wearStatusInDays(12),
        wearStatusInDaysAvg(13),
        wearStatusInDaysMax(14),
        wearStatusInDaysMin(15)
    }

CucsStorageStorageStatsThresholded ::= TEXTUAL-CONVENTION
    STATUS        current
    DESCRIPTION
        ""
    SYNTAX        BITS
    {
        iops(0),
        iopsAvg(1),
        iopsMax(2),
        iopsMin(3),
        latency(4),
        latencyAvg(5),
        latencyMax(6),
        latencyMin(7),
        mbps(8),
        mbpsAvg(9),
        mbpsMax(10),
        mbpsMin(11),
        readIops(12),
        readIopsAvg(13),
        readIopsMax(14),
        readIopsMin(15),
        readMbps(16),
        readMbpsAvg(17),
        readMbpsMax(18),
        readMbpsMin(19),
        writeIops(20),
        writeIopsAvg(21),
        writeIopsMax(22),
        writeIopsMin(23),
        writeMbps(24),
        writeMbpsAvg(25),
        writeMbpsMax(26),
        writeMbpsMin(27)
    }

CucsStorageStorageStatsHistThresholded ::= TEXTUAL-CONVENTION
    STATUS        current
    DESCRIPTION
        ""
    SYNTAX        BITS
    {
        iops(0),
        iopsAvg(1),
        iopsMax(2),
        iopsMin(3),
        latency(4),
        latencyAvg(5),
        latencyMax(6),
        latencyMin(7),
        mbps(8),
        mbpsAvg(9),
        mbpsMax(10),
        mbpsMin(11),
        readIops(12),
        readIopsAvg(13),
        readIopsMax(14),
        readIopsMin(15),
        readMbps(16),
        readMbpsAvg(17),
        readMbpsMax(18),
        readMbpsMin(19),
        writeIops(20),
        writeIopsAvg(21),
        writeIopsMax(22),
        writeIopsMin(23),
        writeMbps(24),
        writeMbpsAvg(25),
        writeMbpsMax(26),
        writeMbpsMin(27)
    }

CucsStorageStorageTargetIfRole ::= TEXTUAL-CONVENTION
    STATUS        current
    DESCRIPTION
        ""
    SYNTAX        BITS
    {
        nodeMgmt(0),
        nodeHaState(1),
        dataProtection(2),
        iscsi(3),
        nfs(4),
        cifs(5)
    }

CucsStorageSupportedCmcFeatures ::= TEXTUAL-CONVENTION
    STATUS        current
    DESCRIPTION
        ""
    SYNTAX        BITS
    {
        featureConnectionManagement(1),
        featureSinglePath(2)
    }

CucsStorageSupportedCmcOperations ::= TEXTUAL-CONVENTION
    STATUS        current
    DESCRIPTION
        ""
    SYNTAX        BITS
    {
        operationConnectionManagement(1),
        operationSinglePath(2)
    }

CucsStorageSupportedControllerOp ::= TEXTUAL-CONVENTION
    STATUS        current
    DESCRIPTION
        ""
    SYNTAX        BITS
    {
        noOpsSupported(0),
        modify(1),
        clearBootDrive(2),
        getTtyLog(3),
        getForeignConfiguration(4),
        clearForeignConfiguration(5),
        importForeignConfiguration(6),
        getSuboem(7),
        setSuboem(8),
        setFactoryDefaults(9),
        getTimeSecs(10),
        setTimeSecs(11),
        ctlrShutdown(12),
        getPinnedList(13),
        unpinCache(14),
        ctlrLockOperation(15),
        getPhyErrors(16),
        clearAllConfig(17),
        updateBootDrive(18),
        unlockDisk(20),
        disableSecurity(21)
    }

CucsStorageSupportedLocalDiskOp ::= TEXTUAL-CONVENTION
    STATUS        current
    DESCRIPTION
        ""
    SYNTAX        BITS
    {
        noOpsSupported(0),
        remove(1),
        locateStart(2),
        locateStop(3),
        makeGhsp(4),
        makeDhsp(5),
        removeHsp(6),
        makeOnline(7),
        makeOffline(8),
        prepareToRemove(9),
        undoPrepareToRemove(10),
        startRebuild(11),
        cancelRebuild(12),
        getPdProgress(13),
        getForeignConfiguration(14),
        importForeignConfiguration(15),
        clearForeignConfiguration(16),
        setState(17),
        setBootDrive(18),
        updateLropStatus(19),
        setRebuildStatus(20),
        setCopybackStatus(21),
        enableSecurityOnJbod(22),
        clearSecureDrive(23),
        clearSecureForeignConfigDrive(24),
        getPhyErrors(25),
        smartSsdSupport(26),
        disableSecurityOnJbod(27)
    }

CucsStorageSupportedRaidBatteryOp ::= TEXTUAL-CONVENTION
    STATUS        current
    DESCRIPTION
        ""
    SYNTAX        BITS
    {
        noOpsSupported(0),
        disableLearn(1),
        enableLearn(2),
        startLearnCycle(3)
    }

CucsStorageSupportedStripSizeBitmask ::= TEXTUAL-CONVENTION
    STATUS        current
    DESCRIPTION
        ""
    SYNTAX        BITS
    {
        notApplicable(0),
        n8KB(1),
        n16KB(2),
        n32KB(3),
        n64KB(4),
        n128KB(5),
        n256KB(6),
        n512KB(7),
        n1MB(8),
        n2MB(9),
        n4MB(10),
        n8MB(11),
        n16MB(12),
        n32MB(13),
        n64MB(14),
        n128MB(15),
        n256MB(16),
        n512MB(17)
    }

CucsStorageSupportedVirtualDriveOp ::= TEXTUAL-CONVENTION
    STATUS        current
    DESCRIPTION
        ""
    SYNTAX        BITS
    {
        noOpsSupported(0),
        deleted(1),
        createOperation(2),
        carveOperation(3),
        deleteOperation(4),
        modifyOperation(5),
        setBootDriveOperation(6),
        startInitialization(7),
        cancelInitialization(8),
        startCheckConsistency(9),
        cancelCheckConsistency(10),
        startReconstruction(11),
        getReconstructionInfo(12),
        getLdProgress(13),
        startPatrolRead(14),
        stopPatrolRead(15),
        getMaxsize(16),
        updateLropStatus(17),
        setHiddenOp(18),
        clearHiddenOp(19),
        setCcStatus(20),
        unpinCacheOp(21),
        secureDriveGroup(22),
        setTransportReady(23),
        clearTransportReady(24),
        getDiskGroup(25),
        setReconstructionStatus(26),
        setInitializationStatus(27),
        setChanged(28)
    }

CucsStorageSystemFsmCurrentFsm ::= TEXTUAL-CONVENTION
    STATUS        current
    DESCRIPTION
        ""
    SYNTAX        INTEGER
    {
        nop(0),
        sync(1383)
    }

CucsStorageSystemFsmStageName ::= TEXTUAL-CONVENTION
    STATUS        current
    DESCRIPTION
        ""
    SYNTAX        INTEGER
    {
        nop(0),
        syncBegin(1383),
        syncExecute(1384),
        syncFail(1463),
        syncSuccess(1464)
    }

CucsStorageSystemFsmTaskItem ::= TEXTUAL-CONVENTION
    STATUS        current
    DESCRIPTION
        ""
    SYNTAX        INTEGER
    {
        nop(0),
        sync(1383)
    }

CucsStorageTargetPath ::= TEXTUAL-CONVENTION
    STATUS        current
    DESCRIPTION
        ""
    SYNTAX        INTEGER
    {
        none(0),
        a(1),
        b(2),
        mgmt(3)
    }

CucsStorageTargetIdentityType ::= TEXTUAL-CONVENTION
    STATUS        current
    DESCRIPTION
        ""
    SYNTAX        BITS
    {
        iqnTarget(0),
        euiTarget(1),
        naaTarget(2)
    }

CucsStorageTargetType ::= TEXTUAL-CONVENTION
    STATUS        current
    DESCRIPTION
        ""
    SYNTAX        INTEGER
    {
        unspecified(0),
        unmanaged(1),
        managed(2)
    }

CucsStorageTechnology ::= TEXTUAL-CONVENTION
    STATUS        current
    DESCRIPTION
        ""
    SYNTAX        INTEGER
    {
        unspecified(0),
        hdd(1),
        ssd(2),
        nvme(3)
    }

CucsStorageTechnologyConfig ::= TEXTUAL-CONVENTION
    STATUS        current
    DESCRIPTION
        ""
    SYNTAX        INTEGER
    {
        unspecified(0),
        hdd(1),
        ssd(2),
        nvmeSsd(3)
    }

CucsStorageUnitOperState ::= TEXTUAL-CONVENTION
    STATUS        current
    DESCRIPTION
        ""
    SYNTAX        INTEGER
    {
        undefined(0),
        online(1),
        offline(2),
        computeInoperable(4),
        computeDegraded(5),
        clusterDegraded(6)
    }

CucsStorageVDriveState ::= TEXTUAL-CONVENTION
    STATUS        current
    DESCRIPTION
        ""
    SYNTAX        INTEGER
    {
        unknown(0),
        optimal(1),
        cacheDegraded(2),
        partiallyDegraded(3),
        degraded(4),
        offline(5),
        rebuilding(6)
    }

CucsStorageVdChangeQualifierType ::= TEXTUAL-CONVENTION
    STATUS        current
    DESCRIPTION
        ""
    SYNTAX        BITS
    {
        policyChange(0),
        globalHotspareChange(1),
        dedHotspareChange(2),
        nameChange(3),
        sizeChange(4),
        bootDriveChange(5),
        scrubChange(6)
    }

CucsStorageVdMemberConfigQualifierType ::= TEXTUAL-CONVENTION
    STATUS        current
    DESCRIPTION
        ""
    SYNTAX        INTEGER
    {
        noAction(0),
        add(1),
        remove(2)
    }

CucsStorageVirtualDriveRefAdminState ::= TEXTUAL-CONVENTION
    STATUS        current
    DESCRIPTION
        ""
    SYNTAX        INTEGER
    {
        online(1),
        offline(2),
        undeployed(4)
    }

CucsStorageVsanRefSwitchId ::= TEXTUAL-CONVENTION
    STATUS        current
    DESCRIPTION
        ""
    SYNTAX        INTEGER
    {
        none(0),
        a(1),
        b(2),
        mgmt(3)
    }

CucsSwAccessDomainLocale ::= TEXTUAL-CONVENTION
    STATUS        current
    DESCRIPTION
        ""
    SYNTAX        BITS
    {
        server(0),
        chassis(1),
        internal(2),
        external(3)
    }

CucsSwAccessDomainType ::= TEXTUAL-CONVENTION
    STATUS        current
    DESCRIPTION
        ""
    SYNTAX        BITS
    {
        lan(0),
        san(1),
        ipc(2)
    }

CucsSwAccessDomainFsmCurrentFsm ::= TEXTUAL-CONVENTION
    STATUS        current
    DESCRIPTION
        ""
    SYNTAX        INTEGER
    {
        nop(0),
        deploy(222)
    }

CucsSwAccessDomainFsmStageName ::= TEXTUAL-CONVENTION
    STATUS        current
    DESCRIPTION
        ""
    SYNTAX        INTEGER
    {
        nop(0),
        deployBegin(222),
        deployUpdateConnectivity(223),
        deployFail(434),
        deploySuccess(435)
    }

CucsSwAccessDomainFsmTaskItem ::= TEXTUAL-CONVENTION
    STATUS        current
    DESCRIPTION
        ""
    SYNTAX        INTEGER
    {
        nop(0),
        deploy(222)
    }

CucsSwAccessEpLocale ::= TEXTUAL-CONVENTION
    STATUS        current
    DESCRIPTION
        ""
    SYNTAX        BITS
    {
        server(0),
        chassis(1),
        internal(2),
        external(3)
    }

CucsSwAccessEpTransport ::= TEXTUAL-CONVENTION
    STATUS        current
    DESCRIPTION
        ""
    SYNTAX        BITS
    {
        ether(0),
        dce(1),
        fc(2)
    }

CucsSwBorderDomainLocale ::= TEXTUAL-CONVENTION
    STATUS        current
    DESCRIPTION
        ""
    SYNTAX        BITS
    {
        server(0),
        chassis(1),
        internal(2),
        external(3)
    }

CucsSwBorderEpLocale ::= TEXTUAL-CONVENTION
    STATUS        current
    DESCRIPTION
        ""
    SYNTAX        BITS
    {
        server(0),
        chassis(1),
        internal(2),
        external(3)
    }

CucsSwBorderPcLocale ::= TEXTUAL-CONVENTION
    STATUS        current
    DESCRIPTION
        ""
    SYNTAX        BITS
    {
        server(0),
        chassis(1),
        internal(2),
        external(3)
    }

CucsSwBreakoutType ::= TEXTUAL-CONVENTION
    STATUS        current
    DESCRIPTION
        ""
    SYNTAX        INTEGER
    {
        unknown(0),
        n10g4x(1),
        n25g4x(2)
    }

CucsSwCIoEpIfType ::= TEXTUAL-CONVENTION
    STATUS        current
    DESCRIPTION
        ""
    SYNTAX        INTEGER
    {
        unknown(0),
        physical(1),
        aggregation(2),
        virtual(3)
    }

CucsSwCardEnvStatsThresholded ::= TEXTUAL-CONVENTION
    STATUS        current
    DESCRIPTION
        ""
    SYNTAX        BITS
    {
        slotOutlet1(0),
        slotOutlet1Avg(1),
        slotOutlet1Max(2),
        slotOutlet1Min(3),
        slotOutlet2(4),
        slotOutlet2Avg(5),
        slotOutlet2Max(6),
        slotOutlet2Min(7),
        slotOutlet3(8),
        slotOutlet3Avg(9),
        slotOutlet3Max(10),
        slotOutlet3Min(11)
    }

CucsSwCardEnvStatsHistThresholded ::= TEXTUAL-CONVENTION
    STATUS        current
    DESCRIPTION
        ""
    SYNTAX        BITS
    {
        slotOutlet1(0),
        slotOutlet1Avg(1),
        slotOutlet1Max(2),
        slotOutlet1Min(3),
        slotOutlet2(4),
        slotOutlet2Avg(5),
        slotOutlet2Max(6),
        slotOutlet2Min(7),
        slotOutlet3(8),
        slotOutlet3Avg(9),
        slotOutlet3Max(10),
        slotOutlet3Min(11)
    }

CucsSwCimcId ::= TEXTUAL-CONVENTION
    STATUS        current
    DESCRIPTION
        ""
    SYNTAX        BITS
    {
        unused(1)
    }

CucsSwConfMode ::= TEXTUAL-CONVENTION
    STATUS        current
    DESCRIPTION
        ""
    SYNTAX        INTEGER
    {
        none(0),
        inProgress(1),
        verifying(2),
        failed(3)
    }

CucsSwConfigStatus ::= TEXTUAL-CONVENTION
    STATUS        current
    DESCRIPTION
        ""
    SYNTAX        INTEGER
    {
        none(1),
        noVlanComp(2)
    }

CucsSwEnvStatsThresholded ::= TEXTUAL-CONVENTION
    STATUS        current
    DESCRIPTION
        ""
    SYNTAX        BITS
    {
        fanCtrlrInlet1(0),
        fanCtrlrInlet1Avg(1),
        fanCtrlrInlet1Max(2),
        fanCtrlrInlet1Min(3),
        fanCtrlrInlet2(4),
        fanCtrlrInlet2Avg(5),
        fanCtrlrInlet2Max(6),
        fanCtrlrInlet2Min(7),
        fanCtrlrInlet3(8),
        fanCtrlrInlet3Avg(9),
        fanCtrlrInlet3Max(10),
        fanCtrlrInlet3Min(11),
        fanCtrlrInlet4(12),
        fanCtrlrInlet4Avg(13),
        fanCtrlrInlet4Max(14),
        fanCtrlrInlet4Min(15),
        mainBoardOutlet1(16),
        mainBoardOutlet1Avg(17),
        mainBoardOutlet1Max(18),
        mainBoardOutlet1Min(19),
        mainBoardOutlet2(20),
        mainBoardOutlet2Avg(21),
        mainBoardOutlet2Max(22),
        mainBoardOutlet2Min(23),
        psuCtrlrInlet1(24),
        psuCtrlrInlet1Avg(25),
        psuCtrlrInlet1Max(26),
        psuCtrlrInlet1Min(27),
        psuCtrlrInlet2(28),
        psuCtrlrInlet2Avg(29),
        psuCtrlrInlet2Max(30),
        psuCtrlrInlet2Min(31),
        td2(36),
        td2Avg(37),
        td2Max(38),
        td2Min(39),
        tiburon(40),
        tiburonAvg(41),
        tiburonMax(42),
        tiburonMin(43)
    }

CucsSwEnvStatsHistThresholded ::= TEXTUAL-CONVENTION
    STATUS        current
    DESCRIPTION
        ""
    SYNTAX        BITS
    {
        fanCtrlrInlet1(0),
        fanCtrlrInlet1Avg(1),
        fanCtrlrInlet1Max(2),
        fanCtrlrInlet1Min(3),
        fanCtrlrInlet2(4),
        fanCtrlrInlet2Avg(5),
        fanCtrlrInlet2Max(6),
        fanCtrlrInlet2Min(7),
        fanCtrlrInlet3(8),
        fanCtrlrInlet3Avg(9),
        fanCtrlrInlet3Max(10),
        fanCtrlrInlet3Min(11),
        fanCtrlrInlet4(12),
        fanCtrlrInlet4Avg(13),
        fanCtrlrInlet4Max(14),
        fanCtrlrInlet4Min(15),
        mainBoardOutlet1(16),
        mainBoardOutlet1Avg(17),
        mainBoardOutlet1Max(18),
        mainBoardOutlet1Min(19),
        mainBoardOutlet2(20),
        mainBoardOutlet2Avg(21),
        mainBoardOutlet2Max(22),
        mainBoardOutlet2Min(23),
        psuCtrlrInlet1(24),
        psuCtrlrInlet1Avg(25),
        psuCtrlrInlet1Max(26),
        psuCtrlrInlet1Min(27),
        psuCtrlrInlet2(28),
        psuCtrlrInlet2Avg(29),
        psuCtrlrInlet2Max(30),
        psuCtrlrInlet2Min(31),
        td2(36),
        td2Avg(37),
        td2Max(38),
        td2Min(39),
        tiburon(40),
        tiburonAvg(41),
        tiburonMax(42),
        tiburonMin(43)
    }

CucsSwEstcEpLocale ::= TEXTUAL-CONVENTION
    STATUS        current
    DESCRIPTION
        ""
    SYNTAX        BITS
    {
        server(0),
        chassis(1),
        internal(2),
        external(3)
    }

CucsSwEthEstcEpLldp ::= TEXTUAL-CONVENTION
    STATUS        current
    DESCRIPTION
        ""
    SYNTAX        BITS
    {
        transmit(0),
        receive(1)
    }

CucsSwEthEstcEpTransport ::= TEXTUAL-CONVENTION
    STATUS        current
    DESCRIPTION
        ""
    SYNTAX        BITS
    {
        ether(0),
        dce(1),
        fc(2)
    }

CucsSwEthEstcPcLldp ::= TEXTUAL-CONVENTION
    STATUS        current
    DESCRIPTION
        ""
    SYNTAX        BITS
    {
        transmit(0),
        receive(1)
    }

CucsSwEthEstcPcTransport ::= TEXTUAL-CONVENTION
    STATUS        current
    DESCRIPTION
        ""
    SYNTAX        BITS
    {
        ether(0),
        dce(1),
        fc(2)
    }

CucsSwEthFlowMonSessionTransport ::= TEXTUAL-CONVENTION
    STATUS        current
    DESCRIPTION
        ""
    SYNTAX        BITS
    {
        ether(0),
        dce(1),
        fc(2)
    }

CucsSwEthFlowMonSessionType ::= TEXTUAL-CONVENTION
    STATUS        current
    DESCRIPTION
        ""
    SYNTAX        BITS
    {
        lan(0),
        san(1),
        ipc(2)
    }

CucsSwEthLanBorderTransport ::= TEXTUAL-CONVENTION
    STATUS        current
    DESCRIPTION
        ""
    SYNTAX        BITS
    {
        ether(0),
        dce(1),
        fc(2)
    }

CucsSwEthLanBorderFsmCurrentFsm ::= TEXTUAL-CONVENTION
    STATUS        current
    DESCRIPTION
        ""
    SYNTAX        INTEGER
    {
        nop(0),
        deploy(224)
    }

CucsSwEthLanBorderFsmStageName ::= TEXTUAL-CONVENTION
    STATUS        current
    DESCRIPTION
        ""
    SYNTAX        INTEGER
    {
        nop(0),
        deployBegin(224),
        deployUpdateConnectivity(225),
        deployFail(436),
        deploySuccess(437),
        deployUpdateVlanGroups(1184),
        deployWaitOnSwConfigHost(2316),
        deployUpdateMacsec(2485),
        deployWaitForUpdateEncryptionFsm(2504)
    }

CucsSwEthLanBorderFsmTaskFlags ::= TEXTUAL-CONVENTION
    STATUS        current
    DESCRIPTION
        ""
    SYNTAX        BITS
    {
        samDmeSwEthLanBorderDeployVlanRemoveConfig(25),
        samDmeSwEthLanBorderDeployBootstrap(27),
        samDmeSwEthLanBorderDeployVlanGroupConfig(59),
        samDmeSwEthLanBorderDeployVlanGroupRetry(60),
        samDmeSwEthLanBorderDeployPortConfig(61)
    }

CucsSwEthLanBorderFsmTaskItem ::= TEXTUAL-CONVENTION
    STATUS        current
    DESCRIPTION
        ""
    SYNTAX        INTEGER
    {
        nop(0),
        deploy(224)
    }

CucsSwEthLanEpTransport ::= TEXTUAL-CONVENTION
    STATUS        current
    DESCRIPTION
        ""
    SYNTAX        BITS
    {
        ether(0),
        dce(1),
        fc(2)
    }

CucsSwEthLanEpUdldAdminState ::= TEXTUAL-CONVENTION
    STATUS        current
    DESCRIPTION
        ""
    SYNTAX        INTEGER
    {
        enabled(1),
        disabled(2)
    }

CucsSwEthLanEpUdldMode ::= TEXTUAL-CONVENTION
    STATUS        current
    DESCRIPTION
        ""
    SYNTAX        INTEGER
    {
        normal(0),
        aggressive(1)
    }

CucsSwEthLanEpVlanStatus ::= TEXTUAL-CONVENTION
    STATUS        current
    DESCRIPTION
        ""
    SYNTAX        INTEGER
    {
        ok(0),
        missingPrimary(1)
    }

CucsSwEthLanFlowMonTransport ::= TEXTUAL-CONVENTION
    STATUS        current
    DESCRIPTION
        ""
    SYNTAX        BITS
    {
        ether(0),
        dce(1),
        fc(2)
    }

CucsSwEthLanFlowMonExporterTransport ::= TEXTUAL-CONVENTION
    STATUS        current
    DESCRIPTION
        ""
    SYNTAX        BITS
    {
        ether(0),
        dce(1),
        fc(2)
    }

CucsSwEthLanFlowMonExporterType ::= TEXTUAL-CONVENTION
    STATUS        current
    DESCRIPTION
        ""
    SYNTAX        BITS
    {
        lan(0),
        san(1),
        ipc(2)
    }

CucsSwEthLanFlowMonFsmCurrentFsm ::= TEXTUAL-CONVENTION
    STATUS        current
    DESCRIPTION
        ""
    SYNTAX        INTEGER
    {
        nop(0),
        deploy(1537)
    }

CucsSwEthLanFlowMonFsmStageName ::= TEXTUAL-CONVENTION
    STATUS        current
    DESCRIPTION
        ""
    SYNTAX        INTEGER
    {
        nop(0),
        deployBegin(1537),
        deployUpdateEthFlowMon(1538),
        deployFail(1560),
        deploySuccess(1561)
    }

CucsSwEthLanFlowMonFsmTaskItem ::= TEXTUAL-CONVENTION
    STATUS        current
    DESCRIPTION
        ""
    SYNTAX        INTEGER
    {
        nop(0),
        deploy(1537)
    }

CucsSwEthLanFlowMonitorTransport ::= TEXTUAL-CONVENTION
    STATUS        current
    DESCRIPTION
        ""
    SYNTAX        BITS
    {
        ether(0),
        dce(1),
        fc(2)
    }

CucsSwEthLanFlowMonitorType ::= TEXTUAL-CONVENTION
    STATUS        current
    DESCRIPTION
        ""
    SYNTAX        BITS
    {
        lan(0),
        san(1),
        ipc(2)
    }

CucsSwEthLanFlowRecordDefTransport ::= TEXTUAL-CONVENTION
    STATUS        current
    DESCRIPTION
        ""
    SYNTAX        BITS
    {
        ether(0),
        dce(1),
        fc(2)
    }

CucsSwEthLanFlowRecordDefType ::= TEXTUAL-CONVENTION
    STATUS        current
    DESCRIPTION
        ""
    SYNTAX        BITS
    {
        lan(0),
        san(1),
        ipc(2)
    }

CucsSwEthLanMonTransport ::= TEXTUAL-CONVENTION
    STATUS        current
    DESCRIPTION
        ""
    SYNTAX        BITS
    {
        ether(0),
        dce(1),
        fc(2)
    }

CucsSwEthLanPcTransport ::= TEXTUAL-CONVENTION
    STATUS        current
    DESCRIPTION
        ""
    SYNTAX        BITS
    {
        ether(0),
        dce(1),
        fc(2)
    }

CucsSwEthLanPcVlanStatus ::= TEXTUAL-CONVENTION
    STATUS        current
    DESCRIPTION
        ""
    SYNTAX        INTEGER
    {
        ok(0),
        missingPrimary(1)
    }

CucsSwEthMonTransport ::= TEXTUAL-CONVENTION
    STATUS        current
    DESCRIPTION
        ""
    SYNTAX        BITS
    {
        ether(0),
        dce(1),
        fc(2)
    }

CucsSwEthMonType ::= TEXTUAL-CONVENTION
    STATUS        current
    DESCRIPTION
        ""
    SYNTAX        BITS
    {
        lan(0),
        san(1),
        ipc(2)
    }

CucsSwEthMonDestEpTransport ::= TEXTUAL-CONVENTION
    STATUS        current
    DESCRIPTION
        ""
    SYNTAX        BITS
    {
        ether(0),
        dce(1),
        fc(2)
    }

CucsSwEthMonFsmCurrentFsm ::= TEXTUAL-CONVENTION
    STATUS        current
    DESCRIPTION
        ""
    SYNTAX        INTEGER
    {
        nop(0),
        deploy(867)
    }

CucsSwEthMonFsmStageName ::= TEXTUAL-CONVENTION
    STATUS        current
    DESCRIPTION
        ""
    SYNTAX        INTEGER
    {
        nop(0),
        deployBegin(867),
        deployUpdateEthMon(868),
        deployFail(1004),
        deploySuccess(1005)
    }

CucsSwEthMonFsmTaskItem ::= TEXTUAL-CONVENTION
    STATUS        current
    DESCRIPTION
        ""
    SYNTAX        INTEGER
    {
        nop(0),
        deploy(953)
    }

CucsSwEthMonSrcEpTransport ::= TEXTUAL-CONVENTION
    STATUS        current
    DESCRIPTION
        ""
    SYNTAX        BITS
    {
        ether(0),
        dce(1),
        fc(2)
    }

CucsSwEthTargetEpAdminState ::= TEXTUAL-CONVENTION
    STATUS        current
    DESCRIPTION
        ""
    SYNTAX        INTEGER
    {
        enabled(1),
        disabled(2)
    }

CucsSwEthTargetEpTransport ::= TEXTUAL-CONVENTION
    STATUS        current
    DESCRIPTION
        ""
    SYNTAX        BITS
    {
        ether(0),
        dce(1),
        fc(2)
    }

CucsSwEtherPortAggrPortId ::= TEXTUAL-CONVENTION
    STATUS        current
    DESCRIPTION
        ""
    SYNTAX        Gauge32 (1..64)

CucsSwEtherPortPortId ::= TEXTUAL-CONVENTION
    STATUS        current
    DESCRIPTION
        ""
    SYNTAX        Gauge32 (1..64)

CucsSwEtherPortSlotId ::= TEXTUAL-CONVENTION
    STATUS        current
    DESCRIPTION
        ""
    SYNTAX        Gauge32 (1..7)

CucsSwExtUtilityFsmCurrentFsm ::= TEXTUAL-CONVENTION
    STATUS        current
    DESCRIPTION
        ""
    SYNTAX        INTEGER
    {
        nop(0),
        confPortBreakout(1985)
    }

CucsSwExtUtilityFsmStageName ::= TEXTUAL-CONVENTION
    STATUS        current
    DESCRIPTION
        ""
    SYNTAX        INTEGER
    {
        nop(0),
        confPortBreakoutBegin(1985),
        confPortBreakoutPortInventorySwA(1986),
        confPortBreakoutPortInventorySwB(1987),
        confPortBreakoutConfigSwA(1988),
        confPortBreakoutConfigSwB(1989),
        confPortBreakoutVerifyBreakoutConfig(1990),
        confPortBreakoutSuccess(1991),
        confPortBreakoutFail(1992)
    }

CucsSwExtUtilityFsmTaskItem ::= TEXTUAL-CONVENTION
    STATUS        current
    DESCRIPTION
        ""
    SYNTAX        INTEGER
    {
        nop(0),
        confPortBreakout(1985)
    }

CucsSwFabricZoneNsAllocStatus ::= TEXTUAL-CONVENTION
    STATUS        current
    DESCRIPTION
        ""
    SYNTAX        INTEGER
    {
        available(0),
        full(1)
    }

CucsSwFabricZoneNsUserZoneAllocStatus ::= TEXTUAL-CONVENTION
    STATUS        current
    DESCRIPTION
        ""
    SYNTAX        INTEGER
    {
        available(0),
        full(1)
    }

CucsSwFcEstcEpTransport ::= TEXTUAL-CONVENTION
    STATUS        current
    DESCRIPTION
        ""
    SYNTAX        BITS
    {
        ether(0),
        dce(1),
        fc(2)
    }

CucsSwFcMonTransport ::= TEXTUAL-CONVENTION
    STATUS        current
    DESCRIPTION
        ""
    SYNTAX        BITS
    {
        ether(0),
        dce(1),
        fc(2)
    }

CucsSwFcMonType ::= TEXTUAL-CONVENTION
    STATUS        current
    DESCRIPTION
        ""
    SYNTAX        BITS
    {
        lan(0),
        san(1),
        ipc(2)
    }

CucsSwFcMonDestEpTransport ::= TEXTUAL-CONVENTION
    STATUS        current
    DESCRIPTION
        ""
    SYNTAX        BITS
    {
        ether(0),
        dce(1),
        fc(2)
    }

CucsSwFcMonFsmCurrentFsm ::= TEXTUAL-CONVENTION
    STATUS        current
    DESCRIPTION
        ""
    SYNTAX        INTEGER
    {
        nop(0),
        deploy(869)
    }

CucsSwFcMonFsmStageName ::= TEXTUAL-CONVENTION
    STATUS        current
    DESCRIPTION
        ""
    SYNTAX        INTEGER
    {
        nop(0),
        deployBegin(869),
        deployUpdateFcMon(870),
        deployFail(1006),
        deploySuccess(1007)
    }

CucsSwFcMonFsmTaskItem ::= TEXTUAL-CONVENTION
    STATUS        current
    DESCRIPTION
        ""
    SYNTAX        INTEGER
    {
        nop(0),
        deploy(955)
    }

CucsSwFcMonSrcEpTransport ::= TEXTUAL-CONVENTION
    STATUS        current
    DESCRIPTION
        ""
    SYNTAX        BITS
    {
        ether(0),
        dce(1),
        fc(2)
    }

CucsSwFcSanBorderTransport ::= TEXTUAL-CONVENTION
    STATUS        current
    DESCRIPTION
        ""
    SYNTAX        BITS
    {
        ether(0),
        dce(1),
        fc(2)
    }

CucsSwFcSanBorderUplinkTrunking ::= TEXTUAL-CONVENTION
    STATUS        current
    DESCRIPTION
        ""
    SYNTAX        INTEGER
    {
        disabled(0),
        enabled(1)
    }

CucsSwFcSanBorderFsmCurrentFsm ::= TEXTUAL-CONVENTION
    STATUS        current
    DESCRIPTION
        ""
    SYNTAX        INTEGER
    {
        nop(0),
        deploy(226),
        activateZoneSet(1185)
    }

CucsSwFcSanBorderFsmStageName ::= TEXTUAL-CONVENTION
    STATUS        current
    DESCRIPTION
        ""
    SYNTAX        INTEGER
    {
        nop(0),
        deployBegin(226),
        deployUpdateConnectivity(227),
        deployFail(438),
        deploySuccess(439),
        activateZoneSetBegin(1185),
        activateZoneSetUpdateZones(1186),
        activateZoneSetFail(1465),
        activateZoneSetSuccess(1466),
        activateZoneSetVerifyUserZoneConfig(2100)
    }

CucsSwFcSanBorderFsmTaskFlags ::= TEXTUAL-CONVENTION
    STATUS        current
    DESCRIPTION
        ""
    SYNTAX        BITS
    {
        samDmeSwFcSanBorderActivateZoneSetUserZoneConfig(60),
        samDmeSwFcSanBorderActivateZoneSetInternalZoneConfig(61)
    }

CucsSwFcSanBorderFsmTaskItem ::= TEXTUAL-CONVENTION
    STATUS        current
    DESCRIPTION
        ""
    SYNTAX        INTEGER
    {
        nop(0),
        deploy(226),
        activateZoneSet(1185)
    }

CucsSwFcSanEpTransport ::= TEXTUAL-CONVENTION
    STATUS        current
    DESCRIPTION
        ""
    SYNTAX        BITS
    {
        ether(0),
        dce(1),
        fc(2)
    }

CucsSwFcSanMonTransport ::= TEXTUAL-CONVENTION
    STATUS        current
    DESCRIPTION
        ""
    SYNTAX        BITS
    {
        ether(0),
        dce(1),
        fc(2)
    }

CucsSwFcSanPcTransport ::= TEXTUAL-CONVENTION
    STATUS        current
    DESCRIPTION
        ""
    SYNTAX        BITS
    {
        ether(0),
        dce(1),
        fc(2)
    }

CucsSwFcServerZoneGroupLc ::= TEXTUAL-CONVENTION
    STATUS        current
    DESCRIPTION
        ""
    SYNTAX        INTEGER
    {
        available(0),
        allocated(1),
        deallocated(2),
        repurposed(3)
    }

CucsSwFcUserZoneLc ::= TEXTUAL-CONVENTION
    STATUS        current
    DESCRIPTION
        ""
    SYNTAX        INTEGER
    {
        available(0),
        allocated(1),
        deallocated(2),
        repurposed(3)
    }

CucsSwFcUserZoneGroupLc ::= TEXTUAL-CONVENTION
    STATUS        current
    DESCRIPTION
        ""
    SYNTAX        INTEGER
    {
        available(0),
        allocated(1),
        deallocated(2),
        repurposed(3)
    }

CucsSwFcZoneLc ::= TEXTUAL-CONVENTION
    STATUS        current
    DESCRIPTION
        ""
    SYNTAX        INTEGER
    {
        available(0),
        allocated(1),
        deallocated(2),
        repurposed(3)
    }

CucsSwFcZoneMemberLc ::= TEXTUAL-CONVENTION
    STATUS        current
    DESCRIPTION
        ""
    SYNTAX        INTEGER
    {
        available(0),
        allocated(1),
        deallocated(2),
        repurposed(3)
    }

CucsSwFcZoneSetLc ::= TEXTUAL-CONVENTION
    STATUS        current
    DESCRIPTION
        ""
    SYNTAX        INTEGER
    {
        available(0),
        allocated(1),
        deallocated(2),
        repurposed(3)
    }

CucsSwFcoeEstcEpTransport ::= TEXTUAL-CONVENTION
    STATUS        current
    DESCRIPTION
        ""
    SYNTAX        BITS
    {
        ether(0),
        dce(1),
        fc(2)
    }

CucsSwFcoeSanEpTransport ::= TEXTUAL-CONVENTION
    STATUS        current
    DESCRIPTION
        ""
    SYNTAX        BITS
    {
        ether(0),
        dce(1),
        fc(2)
    }

CucsSwFcoeSanEpUdldAdminState ::= TEXTUAL-CONVENTION
    STATUS        current
    DESCRIPTION
        ""
    SYNTAX        INTEGER
    {
        enabled(1),
        disabled(2)
    }

CucsSwFcoeSanEpUdldMode ::= TEXTUAL-CONVENTION
    STATUS        current
    DESCRIPTION
        ""
    SYNTAX        INTEGER
    {
        normal(0),
        aggressive(1)
    }

CucsSwFcoeSanPcTransport ::= TEXTUAL-CONVENTION
    STATUS        current
    DESCRIPTION
        ""
    SYNTAX        BITS
    {
        ether(0),
        dce(1),
        fc(2)
    }

CucsSwFlowMonitorAdminState ::= TEXTUAL-CONVENTION
    STATUS        current
    DESCRIPTION
        ""
    SYNTAX        INTEGER
    {
        enabled(1),
        disabled(2)
    }

CucsSwLanBorderType ::= TEXTUAL-CONVENTION
    STATUS        current
    DESCRIPTION
        ""
    SYNTAX        BITS
    {
        lan(0),
        san(1),
        ipc(2)
    }

CucsSwLanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsSwLanEpType ::= TEXTUAL-CONVENTION
    STATUS        current
    DESCRIPTION
        ""
    SYNTAX        BITS
    {
        lan(0),
        san(1),
        ipc(2)
    }

CucsSwLanMonType ::= TEXTUAL-CONVENTION
    STATUS        current
    DESCRIPTION
        ""
    SYNTAX        BITS
    {
        lan(0),
        san(1),
        ipc(2)
    }

CucsSwLanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsSwLanPcType ::= TEXTUAL-CONVENTION
    STATUS        current
    DESCRIPTION
        ""
    SYNTAX        BITS
    {
        lan(0),
        san(1),
        ipc(2)
    }

CucsSwMonAdminState ::= TEXTUAL-CONVENTION
    STATUS        current
    DESCRIPTION
        ""
    SYNTAX        INTEGER
    {
        enabled(1),
        disabled(2)
    }

CucsSwMonSpanCtrlPkts ::= TEXTUAL-CONVENTION
    STATUS        current
    DESCRIPTION
        ""
    SYNTAX        INTEGER
    {
        enabled(1),
        disabled(2)
    }

CucsSwMonDomainLocale ::= TEXTUAL-CONVENTION
    STATUS        current
    DESCRIPTION
        ""
    SYNTAX        BITS
    {
        server(0),
        chassis(1),
        internal(2),
        external(3)
    }

CucsSwMonLifeCycle ::= TEXTUAL-CONVENTION
    STATUS        current
    DESCRIPTION
        ""
    SYNTAX        INTEGER
    {
        normal(1),
        new(2),
        deleted(3)
    }

CucsSwMonSrcEpLocale ::= TEXTUAL-CONVENTION
    STATUS        current
    DESCRIPTION
        ""
    SYNTAX        BITS
    {
        server(0),
        chassis(1),
        internal(2),
        external(3)
    }

CucsSwNFConfigStatus ::= TEXTUAL-CONVENTION
    STATUS        current
    DESCRIPTION
        ""
    SYNTAX        INTEGER
    {
        ok(1),
        incomplete(2)
    }

CucsSwNetflowExporterProtocol ::= TEXTUAL-CONVENTION
    STATUS        current
    DESCRIPTION
        ""
    SYNTAX        INTEGER
    {
        netflow(1)
    }

CucsSwNetflowMonSessionProtocol ::= TEXTUAL-CONVENTION
    STATUS        current
    DESCRIPTION
        ""
    SYNTAX        INTEGER
    {
        netflow(1)
    }

CucsSwNetflowMonitorProtocol ::= TEXTUAL-CONVENTION
    STATUS        current
    DESCRIPTION
        ""
    SYNTAX        INTEGER
    {
        netflow(1)
    }

CucsSwNetflowRecordDefProtocol ::= TEXTUAL-CONVENTION
    STATUS        current
    DESCRIPTION
        ""
    SYNTAX        INTEGER
    {
        netflow(1)
    }

CucsSwPIoEpIfType ::= TEXTUAL-CONVENTION
    STATUS        current
    DESCRIPTION
        ""
    SYNTAX        INTEGER
    {
        unknown(0),
        physical(1),
        aggregation(2),
        virtual(3)
    }

CucsSwPIoEpLc ::= TEXTUAL-CONVENTION
    STATUS        current
    DESCRIPTION
        ""
    SYNTAX        INTEGER
    {
        available(0),
        allocated(1),
        deallocated(2),
        repurposed(3),
        pending(4)
    }

CucsSwPeerStatus ::= TEXTUAL-CONVENTION
    STATUS        current
    DESCRIPTION
        ""
    SYNTAX        INTEGER
    {
        existing(1),
        nonexisting(2)
    }

CucsSwPhysFsmCurrentFsm ::= TEXTUAL-CONVENTION
    STATUS        current
    DESCRIPTION
        ""
    SYNTAX        INTEGER
    {
        nop(0),
        confPhysical(1121)
    }

CucsSwPhysFsmStageName ::= TEXTUAL-CONVENTION
    STATUS        current
    DESCRIPTION
        ""
    SYNTAX        INTEGER
    {
        nop(0),
        confPhysicalBegin(1121),
        confPhysicalPortInventorySwA(1122),
        confPhysicalPortInventorySwB(1123),
        confPhysicalConfigSwA(1124),
        confPhysicalConfigSwB(1125),
        confPhysicalVerifyPhysConfig(1126),
        confPhysicalSuccess(1127),
        confPhysicalFail(1128)
    }

CucsSwPhysFsmTaskItem ::= TEXTUAL-CONVENTION
    STATUS        current
    DESCRIPTION
        ""
    SYNTAX        INTEGER
    {
        nop(0),
        confPhysical(1082)
    }

CucsSwPortBreakoutPortId ::= TEXTUAL-CONVENTION
    STATUS        current
    DESCRIPTION
        ""
    SYNTAX        Gauge32 (1..48)

CucsSwPortBreakoutSlotId ::= TEXTUAL-CONVENTION
    STATUS        current
    DESCRIPTION
        ""
    SYNTAX        Gauge32 (1..2)

CucsSwPortDiscoverFsmCurrentFsm ::= TEXTUAL-CONVENTION
    STATUS        current
    DESCRIPTION
        ""
    SYNTAX        INTEGER
    {
        nop(0),
        deploy(2249)
    }

CucsSwPortDiscoverFsmStageName ::= TEXTUAL-CONVENTION
    STATUS        current
    DESCRIPTION
        ""
    SYNTAX        INTEGER
    {
        nop(0),
        deployBegin(2249),
        deployEnablePort(2250),
        deployFail(2267),
        deploySuccess(2268)
    }

CucsSwPortDiscoverFsmTaskItem ::= TEXTUAL-CONVENTION
    STATUS        current
    DESCRIPTION
        ""
    SYNTAX        INTEGER
    {
        nop(0),
        deploy(2249)
    }

CucsSwRMonEpFsmCurrentFsm ::= TEXTUAL-CONVENTION
    STATUS        current
    DESCRIPTION
        ""
    SYNTAX        INTEGER
    {
        nop(0),
        deployRMonEp(2486)
    }

CucsSwRMonEpFsmStageName ::= TEXTUAL-CONVENTION
    STATUS        current
    DESCRIPTION
        ""
    SYNTAX        INTEGER
    {
        nop(0),
        deployRMonEpBegin(2486),
        deployRMonEpUpdateSVI(2487),
        deployRMonEpFail(2490),
        deployRMonEpSuccess(2491)
    }

CucsSwRMonEpFsmTaskItem ::= TEXTUAL-CONVENTION
    STATUS        current
    DESCRIPTION
        ""
    SYNTAX        INTEGER
    {
        nop(0),
        deployRMonEp(2486)
    }

CucsSwSanBorderType ::= TEXTUAL-CONVENTION
    STATUS        current
    DESCRIPTION
        ""
    SYNTAX        BITS
    {
        lan(0),
        san(1),
        ipc(2)
    }

CucsSwSanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsSwSanEpType ::= TEXTUAL-CONVENTION
    STATUS        current
    DESCRIPTION
        ""
    SYNTAX        BITS
    {
        lan(0),
        san(1),
        ipc(2)
    }

CucsSwSanMonType ::= TEXTUAL-CONVENTION
    STATUS        current
    DESCRIPTION
        ""
    SYNTAX        BITS
    {
        lan(0),
        san(1),
        ipc(2)
    }

CucsSwSanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CucsSwSanPcType ::= TEXTUAL-CONVENTION
    STATUS        current
    DESCRIPTION
        ""
    SYNTAX        BITS
    {
        lan(0),
        san(1),
        ipc(2)
    }

CucsSwSubGroupAggrPortId ::= TEXTUAL-CONVENTION
    STATUS        current
    DESCRIPTION
        ""
    SYNTAX        Gauge32 (1..48)

CucsSwSubGroupSlotId ::= TEXTUAL-CONVENTION
    STATUS        current
    DESCRIPTION
        ""
    SYNTAX        Gauge32 (1..4)

CucsSwSystemStatsThresholded ::= TEXTUAL-CONVENTION
    STATUS        current
    DESCRIPTION
        ""
    SYNTAX        BITS
    {
        load(0),
        loadAvg(1),
        loadMax(2),
        loadMin(3),
        memAvailable(4),
        memAvailableAvg(5),
        memAvailableMax(6),
        memAvailableMin(7),
        memCached(8),
        memCachedAvg(9),
        memCachedMax(10),
        memCachedMin(11)
    }

CucsSwSystemStatsHistThresholded ::= TEXTUAL-CONVENTION
    STATUS        current
    DESCRIPTION
        ""
    SYNTAX        BITS
    {
        load(0),
        loadAvg(1),
        loadMax(2),
        loadMin(3),
        memAvailable(4),
        memAvailableAvg(5),
        memAvailableMax(6),
        memAvailableMin(7),
        memCached(8),
        memCachedAvg(9),
        memCachedMax(10),
        memCachedMin(11)
    }

CucsSwTargetEpType ::= TEXTUAL-CONVENTION
    STATUS        current
    DESCRIPTION
        ""
    SYNTAX        BITS
    {
        lan(0),
        san(1),
        ipc(2)
    }

CucsSwUlanPurpose ::= TEXTUAL-CONVENTION
    STATUS        current
    DESCRIPTION
        ""
    SYNTAX        INTEGER
    {
        management(1),
        boot(2),
        reserved1(3),
        reserved2(4),
        applianceManagement(5)
    }

CucsSwUtilityDomainLocale ::= TEXTUAL-CONVENTION
    STATUS        current
    DESCRIPTION
        ""
    SYNTAX        BITS
    {
        server(0),
        chassis(1),
        internal(2),
        external(3)
    }

CucsSwUtilityDomainType ::= TEXTUAL-CONVENTION
    STATUS        current
    DESCRIPTION
        ""
    SYNTAX        BITS
    {
        lan(0),
        san(1),
        ipc(2)
    }

CucsSwUtilityDomainFsmCurrentFsm ::= TEXTUAL-CONVENTION
    STATUS        current
    DESCRIPTION
        ""
    SYNTAX        INTEGER
    {
        nop(0),
        deploy(228)
    }

CucsSwUtilityDomainFsmStageName ::= TEXTUAL-CONVENTION
    STATUS        current
    DESCRIPTION
        ""
    SYNTAX        INTEGER
    {
        nop(0),
        deployBegin(228),
        deployUpdateConnectivity(229),
        deployFail(440),
        deploySuccess(441)
    }

CucsSwUtilityDomainFsmTaskItem ::= TEXTUAL-CONVENTION
    STATUS        current
    DESCRIPTION
        ""
    SYNTAX        INTEGER
    {
        nop(0),
        deploy(228)
    }

CucsSwVlanLc ::= TEXTUAL-CONVENTION
    STATUS        current
    DESCRIPTION
        ""
    SYNTAX        INTEGER
    {
        available(0),
        allocated(1),
        deallocated(2),
        repurposed(3),
        pending(4),
        provisioned(5)
    }

CucsSwVlanCompType ::= TEXTUAL-CONVENTION
    STATUS        current
    DESCRIPTION
        ""
    SYNTAX        INTEGER
    {
        included(1),
        excluded(2)
    }

CucsSwVlanConfigStatusType ::= TEXTUAL-CONVENTION
    STATUS        current
    DESCRIPTION
        ""
    SYNTAX        INTEGER
    {
        applied(1),
        unApplied(2)
    }

CucsSwVlanGroupType ::= TEXTUAL-CONVENTION
    STATUS        current
    DESCRIPTION
        ""
    SYNTAX        INTEGER
    {
        compressed(1),
        uncompressed(2),
        vpCompressed(3)
    }

CucsSwVlanLimitStatus ::= TEXTUAL-CONVENTION
    STATUS        current
    DESCRIPTION
        ""
    SYNTAX        INTEGER
    {
        ok(1),
        exceeded(2)
    }

CucsSwVlanPortNsAllocStatus ::= TEXTUAL-CONVENTION
    STATUS        current
    DESCRIPTION
        ""
    SYNTAX        INTEGER
    {
        available(0),
        exceeded(1)
    }

CucsSwAutoNegMode ::= TEXTUAL-CONVENTION
    STATUS        current
    DESCRIPTION
        ""
    SYNTAX        INTEGER
    {
        none(0),
        auto(1),
        unset(2)
    }

CucsSysdebugAutoCoreFileExportTargetProto ::= TEXTUAL-CONVENTION
    STATUS        current
    DESCRIPTION
        ""
    SYNTAX        INTEGER
    {
        none(0),
        ftp(1),
        tftp(2),
        scp(3),
        http(4),
        sftp(5),
        nfsCopy(6)
    }

CucsSysdebugAutoCoreFileExportTargetFsmCurrentFsm ::= TEXTUAL-CONVENTION
    STATUS        current
    DESCRIPTION
        ""
    SYNTAX        INTEGER
    {
        nop(0),
        configure(216)
    }

CucsSysdebugAutoCoreFileExportTargetFsmStageName ::= TEXTUAL-CONVENTION
    STATUS        current
    DESCRIPTION
        ""
    SYNTAX        INTEGER
    {
        nop(0),
        configureBegin(216),
        configureLocal(217),
        configurePeer(218),
        configureFail(444),
        configureSuccess(445)
    }

CucsSysdebugAutoCoreFileExportTargetFsmTaskItem ::= TEXTUAL-CONVENTION
    STATUS        current
    DESCRIPTION
        ""
    SYNTAX        INTEGER
    {
        nop(0),
        configure(216)
    }

CucsSysdebugBackupBehaviorInterval ::= TEXTUAL-CONVENTION
    STATUS        current
    DESCRIPTION
        ""
    SYNTAX        INTEGER
    {
        never(0),
        n1hour(3600),
        n2hours(7200),
        n4hours(14400),
        n8hours(28800),
        n24hours(86400),
        n1week(604800),
        n1month(2592000)
    }

CucsSysdebugBackupBehaviorProto ::= TEXTUAL-CONVENTION
    STATUS        current
    DESCRIPTION
        ""
    SYNTAX        INTEGER
    {
        none(0),
        ftp(1),
        tftp(2),
        scp(3),
        http(4),
        sftp(5),
        nfsCopy(6)
    }

CucsSysdebugBackupFormat ::= TEXTUAL-CONVENTION
    STATUS        current
    DESCRIPTION
        ""
    SYNTAX        INTEGER
    {
        ascii(1),
        binary(2)
    }

CucsSysdebugCoreExportStatus ::= TEXTUAL-CONVENTION
    STATUS        current
    DESCRIPTION
        ""
    SYNTAX        INTEGER
    {
        success(1),
        failure(2)
    }

CucsSysdebugCoreFileAdminState ::= TEXTUAL-CONVENTION
    STATUS        current
    DESCRIPTION
        ""
    SYNTAX        INTEGER
    {
        init(0),
        prepareDownload(1),
        downloaded(2)
    }

CucsSysdebugCoreFileOperState ::= TEXTUAL-CONVENTION
    STATUS        current
    DESCRIPTION
        ""
    SYNTAX        INTEGER
    {
        unavailable(0),
        available(1),
        availableOnSubordinate(2),
        inProgress(3),
        failed(4)
    }

CucsSysdebugCoreFsmCurrentFsm ::= TEXTUAL-CONVENTION
    STATUS        current
    DESCRIPTION
        ""
    SYNTAX        INTEGER
    {
        nop(0),
        download(1041)
    }

CucsSysdebugCoreFsmStageName ::= TEXTUAL-CONVENTION
    STATUS        current
    DESCRIPTION
        ""
    SYNTAX        INTEGER
    {
        nop(0),
        downloadBegin(1041),
        downloadCopySub(1042),
        downloadCopyPrimary(1043),
        downloadDeleteSub(1044),
        downloadDeletePrimary(1045),
        downloadFail(1053),
        downloadSuccess(1054)
    }

CucsSysdebugCoreFsmTaskItem ::= TEXTUAL-CONVENTION
    STATUS        current
    DESCRIPTION
        ""
    SYNTAX        INTEGER
    {
        nop(0),
        download(1041)
    }

CucsSysdebugDiagLogOperState ::= TEXTUAL-CONVENTION
    STATUS        current
    DESCRIPTION
        ""
    SYNTAX        INTEGER
    {
        unknown(0),
        allocated(1),
        created(2)
    }

CucsSysdebugEpLogAdminState ::= TEXTUAL-CONVENTION
    STATUS        current
    DESCRIPTION
        ""
    SYNTAX        INTEGER
    {
        policy(0),
        backup(1),
        clear(2)
    }

CucsSysdebugEpLogBackupAction ::= TEXTUAL-CONVENTION
    STATUS        current
    DESCRIPTION
        ""
    SYNTAX        BITS
    {
        logFull(0),
        onClear(1),
        timer(2),
        onAssocChange(3)
    }

CucsSysdebugEpLogCapacity ::= TEXTUAL-CONVENTION
    STATUS        current
    DESCRIPTION
        ""
    SYNTAX        INTEGER
    {
        unknown(0),
        available(1),
        low(2),
        veryLow(3),
        full(4)
    }

CucsSysdebugEpLogType ::= TEXTUAL-CONVENTION
    STATUS        current
    DESCRIPTION
        ""
    SYNTAX        INTEGER
    {
        sel(1),
        obfl(2),
        syslog(3)
    }

CucsSysdebugExportStatus ::= TEXTUAL-CONVENTION
    STATUS        current
    DESCRIPTION
        ""
    SYNTAX        INTEGER
    {
        success(1),
        failure(2)
    }

CucsSysdebugLogControlDomainEnum ::= TEXTUAL-CONVENTION
    STATUS        current
    DESCRIPTION
        ""
    SYNTAX        INTEGER
    {
        sysmgmt(0)
    }

CucsSysdebugLogControlEpFsmCurrentFsm ::= TEXTUAL-CONVENTION
    STATUS        current
    DESCRIPTION
        ""
    SYNTAX        INTEGER
    {
        nop(0),
        persistence(1),
        logControlPersist(219)
    }

CucsSysdebugLogControlEpFsmStageName ::= TEXTUAL-CONVENTION
    STATUS        current
    DESCRIPTION
        ""
    SYNTAX        INTEGER
    {
        nop(0),
        persistenceBegin(1),
        persistencePersist(2),
        persistenceFail(163),
        persistenceSuccess(164),
        logControlPersistBegin(219),
        logControlPersistLocal(220),
        logControlPersistPeer(221),
        logControlPersistFail(446),
        logControlPersistSuccess(447)
    }

CucsSysdebugLogControlEpFsmTaskItem ::= TEXTUAL-CONVENTION
    STATUS        current
    DESCRIPTION
        ""
    SYNTAX        INTEGER
    {
        nop(0),
        persistence(1),
        logControlPersist(219)
    }

CucsSysdebugLogControlLevel ::= TEXTUAL-CONVENTION
    STATUS        current
    DESCRIPTION
        ""
    SYNTAX        INTEGER
    {
        debug0(0),
        debug1(1),
        debug2(2),
        debug3(3),
        debug4(4),
        info(5),
        warn(6),
        minor(7),
        major(8),
        crit(9)
    }

CucsSysdebugLogExportPolicyProto ::= TEXTUAL-CONVENTION
    STATUS        current
    DESCRIPTION
        ""
    SYNTAX        INTEGER
    {
        none(0),
        ftp(1),
        tftp(2),
        scp(3),
        http(4),
        sftp(5),
        nfsCopy(6)
    }

CucsSysdebugLogExportPolicyFsmCurrentFsm ::= TEXTUAL-CONVENTION
    STATUS        current
    DESCRIPTION
        ""
    SYNTAX        INTEGER
    {
        nop(0),
        configure(1600)
    }

CucsSysdebugLogExportPolicyFsmStageName ::= TEXTUAL-CONVENTION
    STATUS        current
    DESCRIPTION
        ""
    SYNTAX        INTEGER
    {
        nop(0),
        configureBegin(1600),
        configureLocal(1601),
        configurePeer(1602),
        configureFail(1605),
        configureSuccess(1606)
    }

CucsSysdebugLogExportPolicyFsmTaskItem ::= TEXTUAL-CONVENTION
    STATUS        current
    DESCRIPTION
        ""
    SYNTAX        INTEGER
    {
        nop(0),
        configure(1600)
    }

CucsSysdebugMEpLogOperState ::= TEXTUAL-CONVENTION
    STATUS        current
    DESCRIPTION
        ""
    SYNTAX        INTEGER
    {
        ok(0),
        permissionDeniedError(1),
        remoteCommunicationError(2),
        bmcCommunicationError(3),
        internalUcsmError(4)
    }

CucsSysdebugManualCoreFileExportTargetAdminState ::= TEXTUAL-CONVENTION
    STATUS        current
    DESCRIPTION
        ""
    SYNTAX        INTEGER
    {
        enabled(1),
        disabled(2)
    }

CucsSysdebugManualCoreFileExportTargetProto ::= TEXTUAL-CONVENTION
    STATUS        current
    DESCRIPTION
        ""
    SYNTAX        INTEGER
    {
        none(0),
        ftp(1),
        tftp(2),
        scp(3),
        http(4),
        sftp(5),
        nfsCopy(6)
    }

CucsSysdebugManualCoreFileExportTargetFsmCurrentFsm ::= TEXTUAL-CONVENTION
    STATUS        current
    DESCRIPTION
        ""
    SYNTAX        INTEGER
    {
        nop(0),
        export(214)
    }

CucsSysdebugManualCoreFileExportTargetFsmStageName ::= TEXTUAL-CONVENTION
    STATUS        current
    DESCRIPTION
        ""
    SYNTAX        INTEGER
    {
        nop(0),
        exportBegin(214),
        exportExecute(215),
        exportFail(448),
        exportSuccess(449)
    }

CucsSysdebugManualCoreFileExportTargetFsmTaskItem ::= TEXTUAL-CONVENTION
    STATUS        current
    DESCRIPTION
        ""
    SYNTAX        INTEGER
    {
        nop(0),
        export(214)
    }

CucsSysdebugRemoteTechSupportAdminState ::= TEXTUAL-CONVENTION
    STATUS        current
    DESCRIPTION
        ""
    SYNTAX        INTEGER
    {
        init(0),
        start(1),
        created(2),
        prepareDownload(3),
        delete(4)
    }

CucsSysdebugTSCmdOptCmdOptions ::= TEXTUAL-CONVENTION
    STATUS        current
    DESCRIPTION
        ""
    SYNTAX        BITS
    {
        ucsmExcludeCommands(0),
        ucsmIncludeFiDetail(1)
    }

CucsSysdebugTSCmdOptMajorType ::= TEXTUAL-CONVENTION
    STATUS        current
    DESCRIPTION
        ""
    SYNTAX        INTEGER
    {
        chassis(0),
        fex(1),
        server(2),
        ucsm(3),
        ucsmMgmt(4),
        serverMemory(5)
    }

CucsSysdebugTSScope ::= TEXTUAL-CONVENTION
    STATUS        current
    DESCRIPTION
        ""
    SYNTAX        BITS
    {
        mgmtController(0),
        serviceReg(1),
        operationMgr(2),
        identifierMgr(3),
        resourceMgr(4),
        policyMgr(5),
        storageBroker(6),
        statsMgr(7),
        all(15)
    }

CucsSysdebugTechSupportAdminState ::= TEXTUAL-CONVENTION
    STATUS        current
    DESCRIPTION
        ""
    SYNTAX        INTEGER
    {
        init(0),
        start(1),
        created(2),
        prepareDownload(3),
        delete(4)
    }

CucsSysdebugTechSupportFsmCurrentFsm ::= TEXTUAL-CONVENTION
    STATUS        current
    DESCRIPTION
        ""
    SYNTAX        INTEGER
    {
        nop(0),
        initiate(881),
        deleteTechSupFile(883),
        download(886)
    }

CucsSysdebugTechSupportFsmStageName ::= TEXTUAL-CONVENTION
    STATUS        current
    DESCRIPTION
        ""
    SYNTAX        INTEGER
    {
        nop(0),
        initiateBegin(881),
        initiateLocal(882),
        deleteTechSupFileBegin(883),
        deleteTechSupFileLocal(884),
        deleteTechSupFilePeer(885),
        downloadBegin(886),
        downloadCopySub(887),
        downloadCopyPrimary(888),
        downloadDeleteSub(889),
        downloadDeletePrimary(890),
        deleteTechSupFileFail(1008),
        deleteTechSupFileSuccess(1009),
        downloadFail(1010),
        downloadSuccess(1011),
        initiateFail(1012),
        initiateSuccess(1013)
    }

CucsSysdebugTechSupportFsmTaskItem ::= TEXTUAL-CONVENTION
    STATUS        current
    DESCRIPTION
        ""
    SYNTAX        INTEGER
    {
        nop(0),
        initiate(881),
        deleteTechSupFile(883),
        download(886)
    }

CucsSysdebugTechSupportOperState ::= TEXTUAL-CONVENTION
    STATUS        current
    DESCRIPTION
        ""
    SYNTAX        INTEGER
    {
        unavailable(0),
        available(1),
        availableOnSubordinate(2),
        inProgress(3),
        failed(4)
    }

CucsSysfileExporterPostAction ::= TEXTUAL-CONVENTION
    STATUS        current
    DESCRIPTION
        ""
    SYNTAX        INTEGER
    {
        none(0),
        remove(1)
    }

CucsSysfileMutationAction ::= TEXTUAL-CONVENTION
    STATUS        current
    DESCRIPTION
        ""
    SYNTAX        INTEGER
    {
        none(0),
        remove(1)
    }

CucsSysfileMutationFsmCurrentFsm ::= TEXTUAL-CONVENTION
    STATUS        current
    DESCRIPTION
        ""
    SYNTAX        INTEGER
    {
        nop(0),
        single(209),
        global(211)
    }

CucsSysfileMutationFsmStageName ::= TEXTUAL-CONVENTION
    STATUS        current
    DESCRIPTION
        ""
    SYNTAX        INTEGER
    {
        nop(0),
        singleBegin(209),
        singleExecute(210),
        globalBegin(211),
        globalLocal(212),
        globalPeer(213),
        globalFail(450),
        globalSuccess(451),
        singleFail(452),
        singleSuccess(453)
    }

CucsSysfileMutationFsmTaskItem ::= TEXTUAL-CONVENTION
    STATUS        current
    DESCRIPTION
        ""
    SYNTAX        INTEGER
    {
        nop(0),
        single(209),
        global(211)
    }

CucsTestingServiceProfileFsmCurrentFsm ::= TEXTUAL-CONVENTION
    STATUS        current
    DESCRIPTION
        ""
    SYNTAX        INTEGER
    {
        nop(0),
        resolvePolicyFsm(46),
        resolveManyPolicyFsm(48)
    }

CucsTestingServiceProfileFsmStageName ::= TEXTUAL-CONVENTION
    STATUS        current
    DESCRIPTION
        ""
    SYNTAX        INTEGER
    {
        nop(0),
        resolvePolicyFsmBegin(46),
        resolvePolicyFsmResolve(47),
        resolveManyPolicyFsmBegin(48),
        resolveManyPolicyFsmResolveMany(49),
        resolveManyPolicyFsmFail(175),
        resolveManyPolicyFsmSuccess(176),
        resolvePolicyFsmFail(177),
        resolvePolicyFsmSuccess(178)
    }

CucsTestingServiceProfileFsmTaskItem ::= TEXTUAL-CONVENTION
    STATUS        current
    DESCRIPTION
        ""
    SYNTAX        INTEGER
    {
        nop(0),
        resolvePolicyFsm(46),
        resolveManyPolicyFsm(48)
    }

CucsTestingSnmpSupportVersion ::= TEXTUAL-CONVENTION
    STATUS        current
    DESCRIPTION
        ""
    SYNTAX        INTEGER

CucsTopAdminState ::= TEXTUAL-CONVENTION
    STATUS        current
    DESCRIPTION
        ""
    SYNTAX        INTEGER
    {
        disabled(0),
        enabled(1)
    }

CucsTopInfoPolicyState ::= TEXTUAL-CONVENTION
    STATUS        current
    DESCRIPTION
        ""
    SYNTAX        INTEGER
    {
        disabled(0),
        enabled(1)
    }

CucsTopInfoSyncPolicyState ::= TEXTUAL-CONVENTION
    STATUS        current
    DESCRIPTION
        ""
    SYNTAX        INTEGER
    {
        disabled(0),
        enabled(1)
    }

CucsTopMode ::= TEXTUAL-CONVENTION
    STATUS        current
    DESCRIPTION
        ""
    SYNTAX        INTEGER
    {
        unspecified(0),
        standAlone(1),
        cluster(2)
    }

CucsTopSystemFsmCurrentFsm ::= TEXTUAL-CONVENTION
    STATUS        current
    DESCRIPTION
        ""
    SYNTAX        INTEGER
    {
        nop(0),
        hostName(15),
        peerHostName(293)
    }

CucsTopSystemFsmStageName ::= TEXTUAL-CONVENTION
    STATUS        current
    DESCRIPTION
        ""
    SYNTAX        INTEGER
    {
        nop(0),
        hostNameBegin(15),
        hostNameConfig(16),
        hostNameFail(179),
        hostNameSuccess(180),
        peerHostNameBegin(293),
        peerHostNameConfig(294),
        peerHostNameFail(303),
        peerHostNameSuccess(304),
        hostNameConfigPeer(394)
    }

CucsTopSystemFsmTaskItem ::= TEXTUAL-CONVENTION
    STATUS        current
    DESCRIPTION
        ""
    SYNTAX        INTEGER
    {
        nop(0),
        hostName(15),
        peerHostName(293)
    }

CucsTrigAckOperState ::= TEXTUAL-CONVENTION
    STATUS        current
    DESCRIPTION
        ""
    SYNTAX        INTEGER
    {
        untriggered(0),
        evaluationPending(1),
        evaluated(2),
        waitingForUser(3),
        waitingForMaintWindow(4),
        applyPending(5),
        applied(6),
        waitingForDependency(7),
        none(8),
        expired(9),
        pending(10),
        active(11)
    }

CucsTrigAckPrevOperState ::= TEXTUAL-CONVENTION
    STATUS        current
    DESCRIPTION
        ""
    SYNTAX        INTEGER
    {
        untriggered(0),
        evaluationPending(1),
        evaluated(2),
        waitingForUser(3),
        waitingForMaintWindow(4),
        applyPending(5),
        applied(6),
        waitingForDependency(7),
        none(8),
        expired(9),
        pending(10),
        active(11)
    }

CucsTrigAckChangeDetails ::= TEXTUAL-CONVENTION
    STATUS        current
    DESCRIPTION
        ""
    SYNTAX        BITS
    {
        binding(0),
        hostVirtEthIf(1),
        hostNonvirtEthIf(2),
        hostEthIfProfile(3),
        hostEthIfQos(4),
        hostEthIfNwCtrl(5),
        hostVirtFcIf(6),
        hostNonvirtFcIf(7),
        hostVirtFcIfPersBind(8),
        hostNonvirtFcIfPersBind(9),
        hostFcIfProfile(10),
        hostFcIfQos(11),
        hostFcoeIf(12),
        vif(13),
        vlan(14),
        vsan(15),
        ip(16),
        bootOrder(17),
        bootVirtVnic(18),
        bootNonvirtVnic(19),
        bootLocalStorage(20),
        bootVirtPxe(21),
        bootNonvirtPxe(22),
        bladeIdentity(24),
        agentPolicy(25),
        biosFw(26),
        storageControllerFw(27),
        adaptorHostFw(28),
        adaptorNwFw(29),
        mgmtControllerFw(30),
        localDiskPolicy(31),
        pin(32),
        sol(33),
        epAuth(34),
        biosProfile(35),
        checkpoint(36),
        implicitReboot(37),
        implicitHostFcIfProfileRedeploy(38),
        boardControllerFw(39),
        hostEthIfQosHostControl(40),
        localDiskFw(41),
        implicitHostEthIfProfileRedeploy(42),
        storagePath(43),
        bmcUpdateBiosFw(44),
        hostIfPcie(45),
        flexflashConfig(46),
        flexflashReboot(47),
        bootmodeConfig(48),
        securebootConfig(49),
        vmediaConfig(50),
        storageApplianceSw(51),
        storageTargetId(52),
        remoteStorageConfig(53),
        storageDevBridgeFw(54),
        sasExpanderFw(55),
        fanSpeedConfig(57),
        sasExpRegFw(58),
        assetTagConfig(59),
        pciSwitchFw(60),
        localDiskDataLoss(61),
        localStorageSecurity(62),
        nvmeMswitchFw(63)
    }

CucsTrigAckChanges ::= TEXTUAL-CONVENTION
    STATUS        current
    DESCRIPTION
        ""
    SYNTAX        BITS
    {
        serverIdentity(0),
        storage(1),
        networking(2),
        vnicVhbaPlacement(3),
        bootOrder(4),
        serverAssignment(5),
        operationalPolicies(6),
        storageIdentity(7),
        chassisIdentity(22),
        chassisAssignment(25)
    }

CucsTrigAckDisr ::= TEXTUAL-CONVENTION
    STATUS        current
    DESCRIPTION
        ""
    SYNTAX        BITS
    {
        upTime(0),
        acPowerCycle(1),
        storageAccess(2),
        storageUptime(3)
    }

CucsTrigAckExtdChangeDetails ::= TEXTUAL-CONVENTION
    STATUS        current
    DESCRIPTION
        ""
    SYNTAX        BITS
    {
        persistentMemoryPolicy(0),
        persistentMemoryDimmFw(1),
        hostPackHaveBackupSet(2),
        adaptorSwmReset(3),
        ubmFw(4),
        cpldFw(5),
        retimerFw(6),
        hybridLocalSlotConfig(7),
        intelAmcFw(8)
    }

CucsTrigAckMode ::= TEXTUAL-CONVENTION
    STATUS        current
    DESCRIPTION
        ""
    SYNTAX        INTEGER
    {
        immediate(0),
        userAck(1),
        timerAutomatic(2)
    }

CucsTrigAdminState ::= TEXTUAL-CONVENTION
    STATUS        current
    DESCRIPTION
        ""
    SYNTAX        INTEGER
    {
        triggerImmediate(0),
        triggered(1),
        untriggered(2),
        userAck(4),
        userDiscard(5)
    }

CucsTrigChassisAckMode ::= TEXTUAL-CONVENTION
    STATUS        current
    DESCRIPTION
        ""
    SYNTAX        INTEGER
    {
        userAck(0),
        unspecified(3)
    }

CucsTrigDay ::= TEXTUAL-CONVENTION
    STATUS        current
    DESCRIPTION
        ""
    SYNTAX        INTEGER
    {
        monday(1),
        tuesday(2),
        wednesday(3),
        thursday(4),
        friday(5),
        saturday(6),
        sunday(7),
        oddDay(8),
        evenDay(9),
        everyDay(10)
    }

CucsTrigOperState ::= TEXTUAL-CONVENTION
    STATUS        current
    DESCRIPTION
        ""
    SYNTAX        INTEGER
    {
        pending(0),
        inProgress(1),
        failed(2),
        triggered(3),
        capReached(4),
        pendingAck(5)
    }

CucsTrigReqAdminState ::= TEXTUAL-CONVENTION
    STATUS        current
    DESCRIPTION
        ""
    SYNTAX        INTEGER
    {
        autoSched(0),
        schedAck(1),
        forceAck(2)
    }

CucsTrigSchedMode ::= TEXTUAL-CONVENTION
    STATUS        current
    DESCRIPTION
        ""
    SYNTAX        INTEGER
    {
        advanced(0),
        simple(1)
    }

CucsTrigSchedType ::= TEXTUAL-CONVENTION
    STATUS        current
    DESCRIPTION
        ""
    SYNTAX        INTEGER
    {
        default(0),
        storage(1)
    }

CucsTrigStorageAckMode ::= TEXTUAL-CONVENTION
    STATUS        current
    DESCRIPTION
        ""
    SYNTAX        INTEGER
    {
        immediate(0),
        userAck(1)
    }

CucsTrigTokenOperState ::= TEXTUAL-CONVENTION
    STATUS        current
    DESCRIPTION
        ""
    SYNTAX        INTEGER
    {
        valid(0),
        expired(1)
    }

CucsTrigTrigOperState ::= TEXTUAL-CONVENTION
    STATUS        current
    DESCRIPTION
        ""
    SYNTAX        INTEGER
    {
        untriggered(0),
        evaluationPending(1),
        evaluated(2),
        waitingForUser(3),
        waitingForMaintWindow(4),
        applyPending(5),
        applied(6),
        waitingForDependency(7),
        none(8),
        expired(9),
        pending(10),
        active(11)
    }

CucsTrigTrigState ::= TEXTUAL-CONVENTION
    STATUS        current
    DESCRIPTION
        ""
    SYNTAX        INTEGER
    {
        none(0),
        waitingForNextBoot(1)
    }

CucsTrigTrigger ::= TEXTUAL-CONVENTION
    STATUS        current
    DESCRIPTION
        ""
    SYNTAX        BITS
    {
        onNextBoot(0)
    }

CucsTrigTriggeredState ::= TEXTUAL-CONVENTION
    STATUS        current
    DESCRIPTION
        ""
    SYNTAX        INTEGER
    {
        pending(0),
        inProgress(1),
        failed(2),
        triggered(3)
    }

CucsUuidpoolPoolAssignmentOrder ::= TEXTUAL-CONVENTION
    STATUS        current
    DESCRIPTION
        ""
    SYNTAX        INTEGER
    {
        default(0),
        sequential(1)
    }

CucsVmAdaptorOwner ::= TEXTUAL-CONVENTION
    STATUS        current
    DESCRIPTION
        ""
    SYNTAX        INTEGER
    {
        unknown(0),
        physical(1),
        policy(2),
        logical(4),
        initiatorPolicy(7),
        connPolicy(8)
    }

CucsVmComputeEpClInstType ::= TEXTUAL-CONVENTION
    STATUS        current
    DESCRIPTION
        ""
    SYNTAX        INTEGER
    {
        vm(0),
        hv(1),
        computeEp(2)
    }

CucsVmHbaType ::= TEXTUAL-CONVENTION
    STATUS        current
    DESCRIPTION
        ""
    SYNTAX        INTEGER
    {
        unknown(0),
        ether(1),
        fc(4),
        scsi(8),
        ipc(16)
    }

CucsVmHvClInstType ::= TEXTUAL-CONVENTION
    STATUS        current
    DESCRIPTION
        ""
    SYNTAX        INTEGER
    {
        vm(0),
        hv(1),
        computeEp(2)
    }

CucsVmHvType ::= TEXTUAL-CONVENTION
    STATUS        current
    DESCRIPTION
        ""
    SYNTAX        INTEGER
    {
        unspecified(0),
        esx(1),
        kvm(2),
        hyperv(3),
        xen(4)
    }

CucsVmInstType ::= TEXTUAL-CONVENTION
    STATUS        current
    DESCRIPTION
        ""
    SYNTAX        INTEGER
    {
        vm(0),
        hv(1),
        computeEp(2)
    }

CucsVmLifeCyclePolicyFsmCurrentFsm ::= TEXTUAL-CONVENTION
    STATUS        current
    DESCRIPTION
        ""
    SYNTAX        INTEGER
    {
        nop(0),
        config(1132)
    }

CucsVmLifeCyclePolicyFsmStageName ::= TEXTUAL-CONVENTION
    STATUS        current
    DESCRIPTION
        ""
    SYNTAX        INTEGER
    {
        nop(0),
        configBegin(1132),
        configLocal(1133),
        configPeer(1134),
        configFail(1146),
        configSuccess(1147)
    }

CucsVmLifeCyclePolicyFsmTaskItem ::= TEXTUAL-CONVENTION
    STATUS        current
    DESCRIPTION
        ""
    SYNTAX        INTEGER
    {
        nop(0),
        config(1142)
    }

CucsVmMgmtPlane ::= TEXTUAL-CONVENTION
    STATUS        current
    DESCRIPTION
        ""
    SYNTAX        INTEGER
    {
        unmanaged(0),
        vcenter(1),
        rhevM(2),
        scvmm(3)
    }

CucsVmNicType ::= TEXTUAL-CONVENTION
    STATUS        current
    DESCRIPTION
        ""
    SYNTAX        INTEGER
    {
        unknown(0),
        ether(1),
        fc(4),
        scsi(8),
        ipc(16)
    }

CucsVmOsHvVendor ::= TEXTUAL-CONVENTION
    STATUS        current
    DESCRIPTION
        ""
    SYNTAX        INTEGER
    {
        unspecified(0),
        vmware(1),
        redhat(2),
        microsoft(3),
        novell(4),
        oracle(5),
        citrix(6)
    }

CucsVmStatus ::= TEXTUAL-CONVENTION
    STATUS        current
    DESCRIPTION
        ""
    SYNTAX        INTEGER
    {
        unknown(0),
        online(1),
        offline(2)
    }

CucsVmSwitchAdminState ::= TEXTUAL-CONVENTION
    STATUS        current
    DESCRIPTION
        ""
    SYNTAX        INTEGER
    {
        disable(0),
        enable(1)
    }

CucsVmSwitchVendor ::= TEXTUAL-CONVENTION
    STATUS        current
    DESCRIPTION
        ""
    SYNTAX        INTEGER
    {
        undetermined(0),
        vmware(1),
        microsoft(2)
    }

CucsVnicAEtherIfType ::= TEXTUAL-CONVENTION
    STATUS        current
    DESCRIPTION
        ""
    SYNTAX        INTEGER
    {
        unknown(0),
        ether(1),
        fc(4),
        scsi(8),
        ipc(16)
    }

CucsVnicAFcIfSwitchId ::= TEXTUAL-CONVENTION
    STATUS        current
    DESCRIPTION
        ""
    SYNTAX        INTEGER
    {
        none(0),
        a(1),
        b(2),
        mgmt(3),
        aB(5),
        bA(6)
    }

CucsVnicAFcIfType ::= TEXTUAL-CONVENTION
    STATUS        current
    DESCRIPTION
        ""
    SYNTAX        INTEGER
    {
        unknown(0),
        ether(1),
        fc(4),
        scsi(8),
        ipc(16)
    }

CucsVnicAIpcIfType ::= TEXTUAL-CONVENTION
    STATUS        current
    DESCRIPTION
        ""
    SYNTAX        INTEGER
    {
        unknown(0),
        ether(1),
        fc(4),
        scsi(8),
        ipc(16)
    }

CucsVnicAScsiIfType ::= TEXTUAL-CONVENTION
    STATUS        current
    DESCRIPTION
        ""
    SYNTAX        INTEGER
    {
        unknown(0),
        ether(1),
        fc(4),
        scsi(8),
        ipc(16)
    }

CucsVnicCdnSource ::= TEXTUAL-CONVENTION
    STATUS        current
    DESCRIPTION
        ""
    SYNTAX        INTEGER
    {
        vnicName(0),
        userDefined(1)
    }

CucsVnicConfigIssues ::= TEXTUAL-CONVENTION
    STATUS        current
    DESCRIPTION
        ""
    SYNTAX        BITS
    {
        pinningVlanMismatch(0),
        vnicVlanAssignmentError(1),
        missingPrimaryVlan(2),
        pinnedTargetMisconfig(3),
        unresolvedVlanName(4),
        inaccessibleVlan(5),
        unresolvedVsanName(6),
        unresolvedRemoteVlanName(7),
        unresolvedRemoteVsanName(8),
        unableToUpdateUcsm(9),
        unassociatedVlan(10),
        adaptorRequirement(11),
        connectionPlacement(12),
        dynamicVfVnic(13),
        fcoeCapacity(14),
        insufficientVhbaCapacity(15),
        insufficientVnicCapacity(16),
        invalidWwn(17),
        macDerivationVirtualizedPort(18),
        vfcVnicPvlanConflict(19),
        vifResourcesOverprovisioned(20),
        vnicNotHaReady(21),
        vnicVconProvisioningChange(22),
        wwpnAssignment(23),
        wwpnDerivationVirtualizedPort(24),
        unsupportedGeneveVmqVmmqArfsRoceAdvfilters(25),
        serviceProfileVirtualizationConflict(27),
        vnicVirtualizationConflict(28),
        virtualizationNotSupported(29),
        ungroupedDomain(30),
        missingIpv4InbandMgmtAddr(31),
        missingIpv6InbandMgmtAddr(32),
        missingIpv4Addr(33),
        vnicVirtualizationNetflowConflict(34),
        softPinningVlanMismatch(35),
        unsupportedRoceVmq(36),
        unsupportedRoceNetflow(37),
        unsupportedRoce(38),
        unsupportedVxlan(39),
        unsupportedNvgre(40),
        unsupportedNvgreDynamicVnic(41),
        unsupportedNvgreUsnic(42),
        unsupportedVxlanDynamicVnic(43),
        unsupportedVxlanUsnic(44),
        unsupportedRoceUsnic(45),
        unsupportedVxlanVmq(46),
        unsupportedVxlanNetflow(47),
        unsupportedNvgreNetflow(48),
        unsupportedRoceNvgre(49),
        unsupportedAdaptorForVnicCdn(50),
        duplicateVnicCdnName(51),
        insufficientRoceResources(52),
        unsupportedVmqResources(53),
        unsupportedRoceProperties(54),
        redundancyVnicNotInPair(56),
        redundancyVnicpairNotInSync(57),
        unsupportedAdaptorForVnicOracleRac(58),
        unresolvedNetSanGroup(59),
        misconfiguredNetSanGroup(60),
        overlappingVlans(61),
        unsupportedVmMultiQueue(62),
        unsupportedAzurestackqosGeneve(63)
    }

CucsVnicConfigIssues2 ::= TEXTUAL-CONVENTION
    STATUS        current
    DESCRIPTION
        ""
    SYNTAX        BITS
    {
        unsupportedPtp(0),
        insufficientPtpResources(1),
        unsupportedLunsPerTarget(2),
        unsupportedSriovHpnGeneve(3),
        unsupportedSriovHpnRoce(4),
        unsupportedSriovHpnAzurestackqos(5),
        unsupportedSriovHpnQinq(6),
        misconfiguredQinqVlanQinq(7),
        misconfiguredQinqVicQinqFi(8),
        unsupportedQinqCruz(9),
        unsupportedQinqGeneve(10),
        unsupportedQinqRocev2(11),
        unsupportedQinqVmmq(12),
        unsupportedAzurestackqosQinq(13),
        unsupportedSriovHpnCruz(14),
        unsupportedSriovHpnNetflow(15),
        unsupportedQinqUsnic(16),
        unsupportedVxlanSriovHpn(17),
        unsupportedArfsNetflow(18),
        unsupportedNvgreSriovHpn(19),
        unsupportedEtherChannelWorkQueue(21),
        unsupportedEtherChannelPinningVmqcount(22),
        unsupportedQinqVxlan(23),
        nativeVlanChange(24)
    }

CucsVnicConnectionLcCtrlState ::= TEXTUAL-CONVENTION
    STATUS        current
    DESCRIPTION
        ""
    SYNTAX        INTEGER
    {
        available(0),
        allocated(1),
        deallocated(2),
        repurposed(3)
    }

CucsVnicConnectionOwner ::= TEXTUAL-CONVENTION
    STATUS        current
    DESCRIPTION
        ""
    SYNTAX        INTEGER
    {
        unknown(0),
        physical(1),
        policy(2),
        logical(4),
        initiatorPolicy(7),
        connPolicy(8)
    }

CucsVnicConnectionType ::= TEXTUAL-CONVENTION
    STATUS        current
    DESCRIPTION
        ""
    SYNTAX        INTEGER
    {
        unknown(0),
        ether(1),
        fc(4),
        scsi(8),
        ipc(16)
    }

CucsVnicDefBehType ::= TEXTUAL-CONVENTION
    STATUS        current
    DESCRIPTION
        ""
    SYNTAX        INTEGER
    {
        vnic(1),
        vhba(2)
    }

CucsVnicDefaultAction ::= TEXTUAL-CONVENTION
    STATUS        current
    DESCRIPTION
        ""
    SYNTAX        INTEGER
    {
        none(0),
        hwInherit(1)
    }

CucsVnicDynamicConReqProtection ::= TEXTUAL-CONVENTION
    STATUS        current
    DESCRIPTION
        ""
    SYNTAX        INTEGER
    {
        none(0),
        protectedPrefA(1),
        protectedPrefB(2),
        protected(3)
    }

CucsVnicEtherQInQ ::= TEXTUAL-CONVENTION
    STATUS        current
    DESCRIPTION
        ""
    SYNTAX        INTEGER
    {
        disabled(0),
        enabled(1)
    }

CucsVnicEtherType ::= TEXTUAL-CONVENTION
    STATUS        current
    DESCRIPTION
        ""
    SYNTAX        INTEGER
    {
        unknown(0),
        ether(1),
        fc(4),
        scsi(8),
        ipc(16)
    }

CucsVnicEtherBaseSwitchId ::= TEXTUAL-CONVENTION
    STATUS        current
    DESCRIPTION
        ""
    SYNTAX        INTEGER
    {
        none(0),
        a(1),
        b(2),
        mgmt(3),
        aB(5),
        bA(6)
    }

CucsVnicEtherBaseIfSwitchId ::= TEXTUAL-CONVENTION
    STATUS        current
    DESCRIPTION
        ""
    SYNTAX        INTEGER
    {
        none(0),
        a(1),
        b(2),
        mgmt(3),
        aB(5),
        bA(6)
    }

CucsVnicExternalMgmtIPMode ::= TEXTUAL-CONVENTION
    STATUS        current
    DESCRIPTION
        ""
    SYNTAX        INTEGER
    {
        none(1),
        static(2),
        pooled(3)
    }

CucsVnicFcBasePersBind ::= TEXTUAL-CONVENTION
    STATUS        current
    DESCRIPTION
        ""
    SYNTAX        INTEGER
    {
        disabled(0),
        enabled(4)
    }

CucsVnicFcBaseType ::= TEXTUAL-CONVENTION
    STATUS        current
    DESCRIPTION
        ""
    SYNTAX        INTEGER
    {
        unknown(0),
        ether(1),
        fc(4),
        scsi(8),
        ipc(16)
    }

CucsVnicFcNodeOwner ::= TEXTUAL-CONVENTION
    STATUS        current
    DESCRIPTION
        ""
    SYNTAX        INTEGER
    {
        unknown(0),
        physical(1),
        policy(2),
        logical(4),
        initiatorPolicy(7),
        connPolicy(8)
    }

CucsVnicHostNwIOPerfPref ::= TEXTUAL-CONVENTION
    STATUS        current
    DESCRIPTION
        ""
    SYNTAX        INTEGER
    {
        none(0),
        highPerfReqd(1)
    }

CucsVnicIPv4DnsPref ::= TEXTUAL-CONVENTION
    STATUS        current
    DESCRIPTION
        ""
    SYNTAX        INTEGER
    {
        preferred(0),
        alternate(1)
    }

CucsVnicIScsiConfigIssues ::= TEXTUAL-CONVENTION
    STATUS        current
    DESCRIPTION
        ""
    SYNTAX        BITS
    {
        initiatorName(0),
        iqnPoolName(1),
        targetName(2),
        authProfileSame(3),
        invalidTargetName(4),
        noLuns(5),
        iscsiCardinality(6),
        autoTargetAuth(7),
        autoTargetInit(8),
        noVlanIp(9),
        staticTargetMix(10),
        ipAddrDhcp(11),
        unclassified(12),
        internalCfgError(13),
        missingVlan(14),
        vnicName(15),
        allowedVlan(16),
        iscsiConfig(17),
        iscsiInitiatorIpAddress(18),
        invalidMac(19),
        nativeVlan(20),
        initTargetPasswd(21),
        initIdentity(22),
        unresolvableManagedTarget(23),
        invalidTargetParams(24),
        targetIscsilifStaticIp(25),
        iscsiInvalidServerBootMode(26)
    }

CucsVnicIScsiIfDefType ::= TEXTUAL-CONVENTION
    STATUS        current
    DESCRIPTION
        ""
    SYNTAX        INTEGER
    {
        static(0),
        dynamicNw(1),
        option17(2),
        option43(4)
    }

CucsVnicIScsiNodeOwner ::= TEXTUAL-CONVENTION
    STATUS        current
    DESCRIPTION
        ""
    SYNTAX        INTEGER
    {
        unknown(0),
        physical(1),
        policy(2),
        logical(4),
        initiatorPolicy(7),
        connPolicy(8)
    }

CucsVnicIfOperState ::= TEXTUAL-CONVENTION
    STATUS        current
    DESCRIPTION
        ""
    SYNTAX        INTEGER
    {
        indeterminate(0),
        up(1),
        down(2),
        failed(4)
    }

CucsVnicInstantiation ::= TEXTUAL-CONVENTION
    STATUS        current
    DESCRIPTION
        ""
    SYNTAX        INTEGER
    {
        manual(0),
        default(1),
        dynamic(2),
        dynamicVf(3)
    }

CucsVnicIpcType ::= TEXTUAL-CONVENTION
    STATUS        current
    DESCRIPTION
        ""
    SYNTAX        INTEGER
    {
        unknown(0),
        ether(1),
        fc(4),
        scsi(8),
        ipc(16)
    }

CucsVnicL2IfSwitchId ::= TEXTUAL-CONVENTION
    STATUS        current
    DESCRIPTION
        ""
    SYNTAX        INTEGER
    {
        none(0),
        a(1),
        b(2),
        dual(3),
        aB(5),
        bA(6)
    }

CucsVnicLanConnTemplQInQ ::= TEXTUAL-CONVENTION
    STATUS        current
    DESCRIPTION
        ""
    SYNTAX        INTEGER
    {
        disabled(0),
        enabled(1)
    }

CucsVnicLanConnTemplSwitchId ::= TEXTUAL-CONVENTION
    STATUS        current
    DESCRIPTION
        ""
    SYNTAX        INTEGER
    {
        none(0),
        a(1),
        b(2),
        mgmt(3),
        aB(5),
        bA(6)
    }

CucsVnicLstorageIScsiSwitchId ::= TEXTUAL-CONVENTION
    STATUS        current
    DESCRIPTION
        ""
    SYNTAX        INTEGER
    {
        none(0),
        a(1),
        b(2),
        mgmt(3),
        ab(10)
    }

CucsVnicLunId ::= TEXTUAL-CONVENTION
    STATUS        current
    DESCRIPTION
        ""
    SYNTAX        Gauge32 (0..65535)

CucsVnicMezzMappingScheme ::= TEXTUAL-CONVENTION
    STATUS        current
    DESCRIPTION
        ""
    SYNTAX        INTEGER
    {
        physicalCapFirst(1),
        capLoadDistribute(2)
    }

CucsVnicOrderScheme ::= TEXTUAL-CONVENTION
    STATUS        current
    DESCRIPTION
        ""
    SYNTAX        INTEGER
    {
        zeroFuncAll(0),
        multiFuncAll(1),
        staticZeroFunc(2)
    }

CucsVnicOutbandMgmtEpFsmCurrentFsm ::= TEXTUAL-CONVENTION
    STATUS        current
    DESCRIPTION
        ""
    SYNTAX        INTEGER
    {
        nop(0),
        configureOutband(629)
    }

CucsVnicOutbandMgmtEpFsmStageName ::= TEXTUAL-CONVENTION
    STATUS        current
    DESCRIPTION
        ""
    SYNTAX        INTEGER
    {
        nop(0),
        configureOutbandBegin(629),
        configureOutbandResolveOutbandPool(630),
        configureOutbandCollectIdContexts(631),
        configureOutbandResolveIdentifiers(632),
        configureOutbandValidate(633),
        configureOutbandApplyConfig(634),
        configureOutbandFail(678),
        configureOutbandSuccess(679)
    }

CucsVnicOutbandMgmtEpFsmTaskItem ::= TEXTUAL-CONVENTION
    STATUS        current
    DESCRIPTION
        ""
    SYNTAX        INTEGER
    {
        nop(0),
        configureOutband(629)
    }

CucsVnicPlacement ::= TEXTUAL-CONVENTION
    STATUS        current
    DESCRIPTION
        ""
    SYNTAX        INTEGER
    {
        allVnic(0),
        staticAllFirst(1),
        dynamicAllLast(2)
    }

CucsVnicProfileConfigQualifier ::= TEXTUAL-CONVENTION
    STATUS        current
    DESCRIPTION
        ""
    SYNTAX        INTEGER
    {
        normal(0),
        invalidName(1)
    }

CucsVnicProfileSetFsmCurrentFsm ::= TEXTUAL-CONVENTION
    STATUS        current
    DESCRIPTION
        ""
    SYNTAX        INTEGER
    {
        nop(0),
        deploy(187),
        deployAlias(1118)
    }

CucsVnicProfileSetFsmStageName ::= TEXTUAL-CONVENTION
    STATUS        current
    DESCRIPTION
        ""
    SYNTAX        INTEGER
    {
        nop(0),
        deployBegin(187),
        deployLocal(188),
        deployPeer(189),
        deployFail(456),
        deploySuccess(457),
        deployAliasBegin(1118),
        deployAliasLocal(1119),
        deployAliasPeer(1120),
        deployAliasFail(1148),
        deployAliasSuccess(1149)
    }

CucsVnicProfileSetFsmTaskItem ::= TEXTUAL-CONVENTION
    STATUS        current
    DESCRIPTION
        ""
    SYNTAX        INTEGER
    {
        nop(0),
        deploy(187),
        deployAlias(1123)
    }

CucsVnicRedundancyPairType ::= TEXTUAL-CONVENTION
    STATUS        current
    DESCRIPTION
        ""
    SYNTAX        INTEGER
    {
        none(1),
        primary(2),
        secondary(3)
    }

CucsVnicSanConnTemplTarget ::= TEXTUAL-CONVENTION
    STATUS        current
    DESCRIPTION
        ""
    SYNTAX        BITS
    {
        vm(0),
        adaptor(1)
    }

CucsVnicScsiType ::= TEXTUAL-CONVENTION
    STATUS        current
    DESCRIPTION
        ""
    SYNTAX        INTEGER
    {
        unknown(0),
        ether(1),
        fc(4),
        scsi(8),
        ipc(16)
    }

CucsVnicSriovHpnPreferenceType ::= TEXTUAL-CONVENTION
    STATUS        current
    DESCRIPTION
        ""
    SYNTAX        INTEGER
    {
        disabled(0),
        enabled(1)
    }

CucsVnicStorageEthLifSwitchId ::= TEXTUAL-CONVENTION
    STATUS        current
    DESCRIPTION
        ""
    SYNTAX        INTEGER
    {
        none(0),
        a(1),
        b(2),
        mgmt(3),
        aB(5),
        bA(6)
    }

CucsVnicStorageEthLifType ::= TEXTUAL-CONVENTION
    STATUS        current
    DESCRIPTION
        ""
    SYNTAX        INTEGER
    {
        unknown(0),
        ether(1),
        fc(4),
        scsi(8),
        ipc(16)
    }

CucsVnicTemplateTarget ::= TEXTUAL-CONVENTION
    STATUS        current
    DESCRIPTION
        ""
    SYNTAX        BITS
    {
        vm(0),
        adaptor(1)
    }

CucsVnicTemplateType ::= TEXTUAL-CONVENTION
    STATUS        current
    DESCRIPTION
        ""
    SYNTAX        INTEGER
    {
        initialTemplate(1),
        updatingTemplate(2)
    }

CucsVnicVhbaBehPolicyType ::= TEXTUAL-CONVENTION
    STATUS        current
    DESCRIPTION
        ""
    SYNTAX        INTEGER
    {
        vnic(1),
        vhba(2)
    }

CucsVnicVirtualizationPreferenceType ::= TEXTUAL-CONVENTION
    STATUS        current
    DESCRIPTION
        ""
    SYNTAX        INTEGER
    {
        none(0),
        sriov(2),
        sriovVmfex(3),
        sriovUsnic(4),
        vmq(5),
        vmmq(6),
        sriovHpn(7)
    }

CucsVnicVlanGroupUpdate ::= TEXTUAL-CONVENTION
    STATUS        current
    DESCRIPTION
        ""
    SYNTAX        INTEGER
    {
        na(0),
        vlanGroupUpdate(1)
    }

CucsVnicVmqConPolicyMultiQueue ::= TEXTUAL-CONVENTION
    STATUS        current
    DESCRIPTION
        ""
    SYNTAX        INTEGER
    {
        disabled(0),
        enabled(1)
    }

CucsVnicVnicBootDev ::= TEXTUAL-CONVENTION
    STATUS        current
    DESCRIPTION
        ""
    SYNTAX        INTEGER
    {
        disabled(0),
        enabled(1)
    }

CucsVnicVnicOperHostPort ::= TEXTUAL-CONVENTION
    STATUS        current
    DESCRIPTION
        ""
    SYNTAX        INTEGER
    {
        any(0),
        n1(1),
        n2(2),
        none(10)
    }

CucsVnicVnicBehPolicyType ::= TEXTUAL-CONVENTION
    STATUS        current
    DESCRIPTION
        ""
    SYNTAX        INTEGER
    {
        vnic(1),
        vhba(2)
    }

CucsVnicIpPoolType ::= TEXTUAL-CONVENTION
    STATUS        current
    DESCRIPTION
        ""
    SYNTAX        INTEGER
    {
        target(0),
        specific(1)
    }

CucsVnicIpType ::= TEXTUAL-CONVENTION
    STATUS        current
    DESCRIPTION
        ""
    SYNTAX        INTEGER
    {
        ipv4(0),
        ipv6(1)
    }

CucsVnicPortProfileType ::= TEXTUAL-CONVENTION
    STATUS        current
    DESCRIPTION
        ""
    SYNTAX        INTEGER
    {
        regular(0),
        slaOnly(1)
    }

END
