--  This MIB  has been autogenerated by genTraps.py
VIPTELA-TRAPS DEFINITIONS ::= BEGIN

IMPORTS
	MODULE-IDENTITY, OBJECT-TYPE, NOTIFICATION-TYPE,
	Integer32, Unsigned32, Counter32, Counter64,
	Gauge32, IpAddress
		FROM SNMPv2-SMI
	TEXTUAL-CONVENTION, RowStatus, DateAndTime,
	TruthValue
		FROM SNMPv2-TC
    viptela
        FROM VIPTELA-GLOBAL
;

viptela-traps MODULE-IDENTITY
    LAST-UPDATED "202602280000Z"
    ORGANIZATION "Viptela, Inc."
    CONTACT-INFO "Viptela, Inc.  Email:support@viptela.com"
    DESCRIPTION "This module defines the data model for VPN operational data"
    REVISION "202602280000Z"
    DESCRIPTION "Viptela Revision 26.1"
    REVISION "202507010000Z"
    DESCRIPTION "Viptela Revision 20.18"
    REVISION "202503010000Z"
    DESCRIPTION "Viptela Revision 20.17"
    REVISION "202411010000Z"
    DESCRIPTION "Viptela Revision 20.16"
    REVISION "202407010000Z"
    DESCRIPTION "Viptela Revision 20.15"
    REVISION "202403010000Z"
    DESCRIPTION "Viptela Revision 20.14"
    REVISION "202311010000Z"
    DESCRIPTION "Viptela Revision 20.13"
    REVISION "202307010000Z"
    DESCRIPTION "Viptela Revision 20.12"
    REVISION "202303010000Z"
    DESCRIPTION "Viptela Revision 20.11"
    REVISION "202212150000Z"
    DESCRIPTION "Viptela Revision 20.10"
    REVISION "202206010000Z"
    DESCRIPTION "Viptela Revision 20.9"
    REVISION "202203010000Z"
    DESCRIPTION "Viptela Revision 20.8"
    REVISION "202111010000Z"
    DESCRIPTION "Viptela Revision 20.7"
    REVISION "202107010000Z"
    DESCRIPTION "Viptela Revision 20.6"
    REVISION "202103010000Z"
    DESCRIPTION "Viptela Revision 20.5"
    REVISION "202011010000Z"
    DESCRIPTION "Viptela Revision 20.4"
    REVISION "202007010000Z"
    DESCRIPTION "Viptela Revision 20.3"
    REVISION "202002240000Z"
    DESCRIPTION "Viptela Revision 20.1"
    REVISION "201911150000Z"
    DESCRIPTION "Viptela Revision 19.3"
    REVISION "201908150000Z"
    DESCRIPTION "Viptela Revision 19.2"
    REVISION "201811010000Z"
    DESCRIPTION "Viptela Revision 18.4"
    REVISION "201808200000Z"
    DESCRIPTION "Viptela Revision 18.3.1"
    REVISION "201806250000Z"
    DESCRIPTION "Viptela Revision 18.3"
    REVISION "201804250000Z"
    DESCRIPTION "Viptela Revision 18.2"
    REVISION "201803150000Z"
    DESCRIPTION "Viptela Revision 18.1.1"
    REVISION "201801160000Z"
    DESCRIPTION "Viptela Revision 17.2.3"
    REVISION "201711010000Z"
    DESCRIPTION "Viptela Revision 17.2.1"
    REVISION "201708010000Z"
    DESCRIPTION "Viptela Revision 17.2"
    REVISION "201705250000Z"
    DESCRIPTION "Viptela Revision 17.1.1"
    REVISION "201704060000Z"
    DESCRIPTION "Viptela Revision 17.1"
    REVISION "201702150000Z"
    DESCRIPTION "Viptela Revision 16.3.2"
    REVISION "201702060000Z"
    DESCRIPTION "Viptela Revision 16.3.1"
    REVISION "201611160000Z"
    DESCRIPTION "Viptela Revision 16.3"
    REVISION "201610250000Z"
    DESCRIPTION "Viptela Revision 16.2.10"
    REVISION "201610240000Z"
    DESCRIPTION "Viptela Revision 16.2.4"
    REVISION "201608100000Z"
    DESCRIPTION "Viptela Revision 16.2.2"
    REVISION "201608010000Z"
    DESCRIPTION "Viptela Revision 16.2.1"
    REVISION "201606090000Z"
    DESCRIPTION "Viptela Revision 16.2"
    REVISION "201604220000Z"
    DESCRIPTION "Viptela Revision 16.1.1"
    REVISION "201603150000Z"
    DESCRIPTION "Viptela Revision 16.1"
    REVISION "201601300000Z"
    DESCRIPTION "Viptela Revision 15.4.3"
    REVISION "201512280000Z"
    DESCRIPTION "Viptela Revision 15.4.1"
    REVISION "201512010000Z"
    DESCRIPTION "Viptela Revision 15.4.0"
    REVISION "201510310000Z"
    DESCRIPTION "Viptela Revision 15.3.5"
    REVISION "201509270000Z"
    DESCRIPTION "Viptela Revision 15.3.3"
    REVISION "201509010000Z"
    DESCRIPTION "Viptela Revision 15.3.1"
	REVISION "201507010000Z"
	DESCRIPTION "Viptela Revision 15.3"
	::= { viptela 100 } 

fields     OBJECT IDENTIFIER ::= { viptela-traps 1 }
traps      OBJECT IDENTIFIER ::= { viptela-traps 2 }

-- Notification type definitions
NetconfNotificationSeverity ::= TEXTUAL-CONVENTION
    STATUS      current
    DESCRIPTION "Netconf notification severity level"
    SYNTAX      INTEGER {critical(1),major(2),minor(3)}

DomainId ::= TEXTUAL-CONVENTION
    STATUS      current
    DESCRIPTION "<1..4294967295>"
    SYNTAX      Unsigned32 (0 .. 4294967295)

UnsignedByte ::= TEXTUAL-CONVENTION
    DISPLAY-HINT "d"
    STATUS      current
    DESCRIPTION "xs:unsignedByte"
    SYNTAX      Unsigned32 (0 .. 255)

ColorEnum ::= TEXTUAL-CONVENTION
    STATUS      current
    DESCRIPTION "3g  biz-internet  blue  bronze  custom1  custom2  custom3  default  gold  green  lte  metro-ethernet  mpls public-internet  red  silver private1 private2 private3 private4 private5 private6"
    SYNTAX      INTEGER {default(1),mpls(2),metro-ethernet(3),biz-internet(4),public-internet(5),lte(6),threeG(7),red(8),green(9),blue(10),gold(11),silver(12),bronze(13),custom1(14),custom2(15),custom3(16),private1(17),private2(18),private3(19),private4(20),private5(21),private6(22)}

VpnId ::= TEXTUAL-CONVENTION
    STATUS      current
    DESCRIPTION "<0..65530>"
    SYNTAX      Unsigned32 (0 .. 65530)

FailureStateEnum ::= TEXTUAL-CONVENTION
    STATUS      current
    DESCRIPTION ""
    SYNTAX      INTEGER {oK(0),failed(1)}

SensorStateEnum ::= TEXTUAL-CONVENTION
    STATUS      current
    DESCRIPTION ""
    SYNTAX      INTEGER {green(0),yellow(1),red(2)}

BoolEnum ::= TEXTUAL-CONVENTION
    STATUS      current
    DESCRIPTION ""
    SYNTAX      INTEGER {false(0),true(1)}

AddressFamilyEnum ::= TEXTUAL-CONVENTION
    STATUS      current
    DESCRIPTION ""
    SYNTAX      INTEGER {ipv4(0),ipv6(1)}

AfTypeEnum ::= TEXTUAL-CONVENTION
    STATUS      current
    DESCRIPTION ""
    SYNTAX      INTEGER {tloc-ipv4(0),tloc-ipv6(1),service(2),route-ipv4(3),route-ipv6(4),mcast-ipv4(5),mcast-ipv6(6)}

OperState ::= TEXTUAL-CONVENTION
    STATUS      current
    DESCRIPTION "Operational state"
    SYNTAX      INTEGER {up(0),down(1)}

AdminState ::= TEXTUAL-CONVENTION
    STATUS      current
    DESCRIPTION "Administrative state"
    SYNTAX      INTEGER {up(0),down(1)}

SiteId ::= TEXTUAL-CONVENTION
    STATUS      current
    DESCRIPTION "<1..4294967295>"
    SYNTAX      Unsigned32

BgpState ::= TEXTUAL-CONVENTION
    STATUS      current
    DESCRIPTION ""
    SYNTAX      INTEGER {idle(0),connect(1),active(2),opensent(3),openconfirm(4),established(5),clearing(6),deleted(7)}

HwSensorTypeEnum ::= TEXTUAL-CONVENTION
    STATUS      current
    DESCRIPTION ""
    SYNTAX      INTEGER {board(0),cPU-Junction(1),dRAM(2),pIM(3)}

TunnelEnum ::= TEXTUAL-CONVENTION
    STATUS      current
    DESCRIPTION "Tunnel status"
    SYNTAX      INTEGER {add(1),delete(2)}

PersonalityEnumOper ::= TEXTUAL-CONVENTION
    STATUS      current
    DESCRIPTION "Device type"
    SYNTAX      INTEGER {unknown(0),vedge(1),vhub(2),vsmart(3),vbond(4),vmanage(5),ztp(6),vapigw(7)}

Ipv4UcastAddrPrefix ::= TEXTUAL-CONVENTION
    DISPLAY-HINT "1t"
    STATUS      current
    DESCRIPTION "IPv4 address/prefix length"
    SYNTAX      OCTET STRING

EncapEnum ::= TEXTUAL-CONVENTION
    STATUS      current
    DESCRIPTION "TLOC's encap"
    SYNTAX      INTEGER {gre(1),ipsec(2)}

Enumeration ::= TEXTUAL-CONVENTION
    STATUS      current
    DESCRIPTION "DHCP operational state"
    SYNTAX      INTEGER {up(0),down(1)}

ViptelaIpAddress ::= TEXTUAL-CONVENTION
    DISPLAY-HINT "1t"
    STATUS       current
    DESCRIPTION  "IPv4/IPv6 address"
    SYNTAX       OCTET STRING

OspfIfStateEnum ::= TEXTUAL-CONVENTION
    STATUS      current
    DESCRIPTION ""
    SYNTAX      INTEGER {if-depend-upon(0),if-down(1),if-loopback(2),if-waiting(3),if-point-to-point(4),if-dr-other(5),if-backup(6),if-dr(7)}

OspfStateEnum ::= TEXTUAL-CONVENTION
    STATUS      current
    DESCRIPTION ""
    SYNTAX      INTEGER {full(0),deleted(1),depend-upon(2),down(3),attempt(4),init(5),two-way(6),exstart(7),exchange(8),loading(9)}

StateEnum ::= TEXTUAL-CONVENTION
    STATUS      current
    DESCRIPTION "Operational state"
    SYNTAX      INTEGER {dOWN(1),uP(2)}

PeerState ::= TEXTUAL-CONVENTION
    STATUS      current
    DESCRIPTION "OMP peer state"
    SYNTAX      INTEGER {invalid(0),init(1),handshake(2),up(3),down(4),init-in-gr(5),down-in-gr(6),handshake-in-gr(7)}

VrrpGroupStateEnum ::= TEXTUAL-CONVENTION
    STATUS      current
    DESCRIPTION "VRRP group state"
    SYNTAX      INTEGER {init(1),backup(2),master(3)}

InstallationStatus ::= TEXTUAL-CONVENTION
    STATUS      current
    DESCRIPTION "Installation phase/status"
    SYNTAX      INTEGER {download-start(2),download-complete(3),verification-complete(4),upgrade-apply-complete(5),sync-partition-start(6),sync-partition-complete(7),install-complete(8),install-fail(9),reboot(10),precheck-complete(11),precheck-fail(12)}

OmpPolicyState ::= TEXTUAL-CONVENTION
    STATUS      current
    DESCRIPTION "OMP policy state"
    SYNTAX      INTEGER {add(0),delete(1)}

AdminStateEnum ::= TEXTUAL-CONVENTION
    STATUS      current
    DESCRIPTION "Operational state"
    SYNTAX      INTEGER {disable(1),enable(2)}

BridgeId ::= TEXTUAL-CONVENTION
    STATUS      current
    DESCRIPTION "<1..63>"
    SYNTAX      Unsigned32 (1 .. 63)

NumMacs ::= TEXTUAL-CONVENTION
    STATUS      current
    DESCRIPTION "<0..65535>"
    SYNTAX      Unsigned32 (0 .. 65535)

TrafficDirectionEnum ::= TEXTUAL-CONVENTION
    STATUS      current
    DESCRIPTION "Traffic Direction"
    SYNTAX      INTEGER {downstream(0),upstream(1)}

CloudAppEnum ::= TEXTUAL-CONVENTION
    STATUS      current
    DESCRIPTION "Cloudexpress applications"
    SYNTAX      INTEGER { salesforce        (1),
                          office365         (2),
                          amazonAws         (3),
                          oracle            (4),
                          boxNet            (6),
                          dropbox           (7),
                          intuit            (9),
                          concur            (10),
                          sugarCrm          (11),
                          zohoCrm           (12),
                          zendesk           (13),
                          gotomeeting       (14),
                          googleApps        (16)
                        }

CloudExitEnum ::= TEXTUAL-CONVENTION
    STATUS      current
    DESCRIPTION "Cloudexpress applications"
    SYNTAX      INTEGER { gateway           (1),
                          local             (2),
                          uncomputed        (3),
                          none              (4)
                        }

WwanSimStatusEnum ::= TEXTUAL-CONVENTION
    STATUS      current
    DESCRIPTION "SIM status"
    SYNTAX      INTEGER {not-present(0),present(1),error(2)}

WwanDomainStatusEnum ::= TEXTUAL-CONVENTION
    STATUS      current
    DESCRIPTION "Packet-switched domain status"
    SYNTAX      INTEGER {unknown(0),attached(1),detached(2)}

WwanRegStatusEnum ::= TEXTUAL-CONVENTION
    STATUS      current
    DESCRIPTION "Network registration status"
    SYNTAX      INTEGER {not-registered(0),registered(1),searching(2),registration-denied(3),unknown(4)}

WwanBearerEnum ::= TEXTUAL-CONVENTION
    STATUS      current
    DESCRIPTION "Data bearer"
    SYNTAX      INTEGER {unknown(0),cdma-1x(1),cdma-1xevdo-rev0(2),gprs(3),umts(4),cdma-1xevdo-revA(5),
                         edge(6),hsdpa-wcdma(7),wcdma-hsupa(8),hsdpa-hsupa(9),lte(10),cdma-ehdrpd(11),
                         hsdpaplus-wcdma(12),hsdpaplus-hsupa(13),dchsdpaplus-wcdma(14),dchsdpaplus-hsupa(15),
                         hsdpaplus-64qam(16),hsdpaplus-64qam-hsupa(17),tdscdma(18),tdscdma-hsdpa(19)}

BfdFlapReasonEnum ::= TEXTUAL-CONVENTION
    STATUS      current
    DESCRIPTION "Bfd Flap Reason"
    SYNTAX      INTEGER {bfd-deleted(1),remote-down(2),timeout(3), na(4), not-known(5), ondemand-idle-timeout-delete(6)}

WwanQosStatusEnum ::= TEXTUAL-CONVENTION
    STATUS      current
    DESCRIPTION ""
    SYNTAX      INTEGER {activated(1),modified(2),deleted(3),suspended(4),enabled(5),disabled(6)}

CertificateTypeEnum ::= TEXTUAL-CONVENTION
    STATUS      current
    DESCRIPTION "Certificate Type"
    SYNTAX      INTEGER {web-server(1),enterprise(2),vmanage(3)}

SfpDiagStateEnum ::= TEXTUAL-CONVENTION
    STATUS      current
    DESCRIPTION "SFP Diagnostic Alarm State"
    SYNTAX      INTEGER {no-alarm(0),warn-low(1),alarm-low(2),warn-high(3),alarm-high(4)}

-- Notification field definitions
eventTime OBJECT-TYPE
    SYNTAX      DateAndTime
    MAX-ACCESS  read-only
    STATUS      current
    DESCRIPTION ""
    ::= { fields 1 }

netconfNotificationSeverity OBJECT-TYPE
    SYNTAX      NetconfNotificationSeverity
    MAX-ACCESS  read-only
    STATUS      current
    DESCRIPTION ""
    ::= { fields 2 }

viptelaActionsRebootReason OBJECT-TYPE
    SYNTAX      OCTET STRING
    MAX-ACCESS  read-only
    STATUS      current
    DESCRIPTION ""
    ::= { fields 3 }

viptelaBfdSrcIp OBJECT-TYPE
    SYNTAX      ViptelaIpAddress
    MAX-ACCESS  read-only
    STATUS      current
    DESCRIPTION ""
    ::= { fields 4 }

viptelaBfdDstIp OBJECT-TYPE
    SYNTAX      ViptelaIpAddress
    MAX-ACCESS  read-only
    STATUS      current
    DESCRIPTION ""
    ::= { fields 5 }

viptelaBfdProto OBJECT-TYPE
    SYNTAX      EncapEnum
    MAX-ACCESS  read-only
    STATUS      current
    DESCRIPTION ""
    ::= { fields 6 }

viptelaBfdSrcPort OBJECT-TYPE
    SYNTAX      Unsigned32
    MAX-ACCESS  read-only
    STATUS      current
    DESCRIPTION ""
    ::= { fields 7 }

viptelaBfdDstPort OBJECT-TYPE
    SYNTAX      Unsigned32
    MAX-ACCESS  read-only
    STATUS      current
    DESCRIPTION ""
    ::= { fields 8 }

viptelaBfdLocalSystemIp OBJECT-TYPE
    SYNTAX      ViptelaIpAddress
    MAX-ACCESS  read-only
    STATUS      current
    DESCRIPTION ""
    ::= { fields 9 }

viptelaBfdLocalColor OBJECT-TYPE
    SYNTAX      OCTET STRING
    MAX-ACCESS  read-only
    STATUS      current
    DESCRIPTION ""
    ::= { fields 10 }

viptelaBfdRemoteSystemIp OBJECT-TYPE
    SYNTAX      ViptelaIpAddress
    MAX-ACCESS  read-only
    STATUS      current
    DESCRIPTION ""
    ::= { fields 11 }

viptelaBfdRemoteColor OBJECT-TYPE
    SYNTAX      OCTET STRING
    MAX-ACCESS  read-only
    STATUS      current
    DESCRIPTION ""
    ::= { fields 12 }

viptelaBfdNewState OBJECT-TYPE
    SYNTAX      OperState
    MAX-ACCESS  read-only
    STATUS      current
    DESCRIPTION ""
    ::= { fields 13 }

viptelaHardwareNewState OBJECT-TYPE
    SYNTAX      FailureStateEnum
    MAX-ACCESS  read-only
    STATUS      current
    DESCRIPTION ""
    ::= { fields 14 }

viptelaHardwareHwSensorType OBJECT-TYPE
    SYNTAX      HwSensorTypeEnum
    MAX-ACCESS  read-only
    STATUS      current
    DESCRIPTION ""
    ::= { fields 15 }

viptelaHardwareHwDevIndex OBJECT-TYPE
    SYNTAX      Unsigned32
    MAX-ACCESS  read-only
    STATUS      current
    DESCRIPTION ""
    ::= { fields 16 }

viptelaHardwareName OBJECT-TYPE
    SYNTAX      OCTET STRING
    MAX-ACCESS  read-only
    STATUS      current
    DESCRIPTION ""
    ::= { fields 17 }

viptelaHardwareTemp OBJECT-TYPE
    SYNTAX      Unsigned32
    MAX-ACCESS  read-only
    STATUS      current
    DESCRIPTION ""
    ::= { fields 18 }

viptelaHardwareFantrayId OBJECT-TYPE
    SYNTAX      Unsigned32
    MAX-ACCESS  read-only
    STATUS      current
    DESCRIPTION ""
    ::= { fields 19 }

viptelaHardwareFanId OBJECT-TYPE
    SYNTAX      Unsigned32
    MAX-ACCESS  read-only
    STATUS      current
    DESCRIPTION ""
    ::= { fields 20 }

viptelaHardwarePemId OBJECT-TYPE
    SYNTAX      Unsigned32
    MAX-ACCESS  read-only
    STATUS      current
    DESCRIPTION ""
    ::= { fields 21 }

viptelaHardwarePimId OBJECT-TYPE
    SYNTAX      Unsigned32
    MAX-ACCESS  read-only
    STATUS      current
    DESCRIPTION ""
    ::= { fields 22 }

viptelaHardwareSfpName OBJECT-TYPE
    SYNTAX      OCTET STRING
    MAX-ACCESS  read-only
    STATUS      current
    DESCRIPTION ""
    ::= { fields 23 }

viptelaHardwareUsbSlot OBJECT-TYPE
    SYNTAX      Unsigned32
    MAX-ACCESS  read-only
    STATUS      current
    DESCRIPTION ""
    ::= { fields 24 }

viptelaOmpNumberOfVsmarts OBJECT-TYPE
    SYNTAX      Unsigned32
    MAX-ACCESS  read-only
    STATUS      current
    DESCRIPTION ""
    ::= { fields 25 }

viptelaOmpNewState OBJECT-TYPE
    SYNTAX      OperState
    MAX-ACCESS  read-only
    STATUS      current
    DESCRIPTION ""
    ::= { fields 26 }

viptelaOmpPeer OBJECT-TYPE
    SYNTAX      ViptelaIpAddress
    MAX-ACCESS  read-only
    STATUS      current
    DESCRIPTION ""
    ::= { fields 27 }

viptelaOmpPeerNewState OBJECT-TYPE
    SYNTAX      PeerState
    MAX-ACCESS  read-only
    STATUS      current
    DESCRIPTION ""
    ::= { fields 28 }

viptelaOmpOmpAddressFamily OBJECT-TYPE
    SYNTAX      AfTypeEnum
    MAX-ACCESS  read-only
    STATUS      current
    DESCRIPTION ""
    ::= { fields 29 }

viptelaOmpPolicy OBJECT-TYPE
    SYNTAX      OmpPolicyState
    MAX-ACCESS  read-only
    STATUS      current
    DESCRIPTION ""
    ::= { fields 30 }

viptelaOmpVsmartPeer OBJECT-TYPE
    SYNTAX      ViptelaIpAddress
    MAX-ACCESS  read-only
    STATUS      current
    DESCRIPTION ""
    ::= { fields 31 }

viptelaSecurityPeerType OBJECT-TYPE
    SYNTAX      PersonalityEnumOper
    MAX-ACCESS  read-only
    STATUS      current
    DESCRIPTION ""
    ::= { fields 32 }

viptelaSecurityPeerSystemIp OBJECT-TYPE
    SYNTAX      ViptelaIpAddress
    MAX-ACCESS  read-only
    STATUS      current
    DESCRIPTION ""
    ::= { fields 33 }

viptelaSecurityPublicIp OBJECT-TYPE
    SYNTAX      ViptelaIpAddress
    MAX-ACCESS  read-only
    STATUS      current
    DESCRIPTION ""
    ::= { fields 34 }

viptelaSecurityPublicPort OBJECT-TYPE
    SYNTAX      Unsigned32
    MAX-ACCESS  read-only
    STATUS      current
    DESCRIPTION ""
    ::= { fields 35 }

viptelaSecuritySrcColor OBJECT-TYPE
    SYNTAX      ColorEnum
    MAX-ACCESS  read-only
    STATUS      current
    DESCRIPTION ""
    ::= { fields 36 }

viptelaSecurityRemoteColor OBJECT-TYPE
    SYNTAX      ColorEnum
    MAX-ACCESS  read-only
    STATUS      current
    DESCRIPTION ""
    ::= { fields 37 }

viptelaSecurityUptime OBJECT-TYPE
    SYNTAX      OCTET STRING
    MAX-ACCESS  read-only
    STATUS      current
    DESCRIPTION ""
    ::= { fields 38 }

viptelaSecurityNewState OBJECT-TYPE
    SYNTAX      OperState
    MAX-ACCESS  read-only
    STATUS      current
    DESCRIPTION ""
    ::= { fields 39 }

viptelaSecurityLocalSystemIp OBJECT-TYPE
    SYNTAX      ViptelaIpAddress
    MAX-ACCESS  read-only
    STATUS      current
    DESCRIPTION ""
    ::= { fields 40 }

viptelaSecurityLocalColor OBJECT-TYPE
    SYNTAX      ColorEnum
    MAX-ACCESS  read-only
    STATUS      current
    DESCRIPTION ""
    ::= { fields 41 }

viptelaSecurityReason OBJECT-TYPE
    SYNTAX      OCTET STRING
    MAX-ACCESS  read-only
    STATUS      current
    DESCRIPTION ""
    ::= { fields 42 }

viptelaSecurityOldPublicIp OBJECT-TYPE
    SYNTAX      ViptelaIpAddress
    MAX-ACCESS  read-only
    STATUS      current
    DESCRIPTION ""
    ::= { fields 43 }

viptelaSecurityOldPublicPort OBJECT-TYPE
    SYNTAX      Unsigned32
    MAX-ACCESS  read-only
    STATUS      current
    DESCRIPTION ""
    ::= { fields 44 }

viptelaSecurityNewPublicIp OBJECT-TYPE
    SYNTAX      ViptelaIpAddress
    MAX-ACCESS  read-only
    STATUS      current
    DESCRIPTION ""
    ::= { fields 45 }

viptelaSecurityNewPublicPort OBJECT-TYPE
    SYNTAX      Unsigned32
    MAX-ACCESS  read-only
    STATUS      current
    DESCRIPTION ""
    ::= { fields 46 }

viptelaSecurityColor OBJECT-TYPE
    SYNTAX      ColorEnum
    MAX-ACCESS  read-only
    STATUS      current
    DESCRIPTION ""
    ::= { fields 47 }

viptelaSecurityPersonality OBJECT-TYPE
    SYNTAX      PersonalityEnumOper
    MAX-ACCESS  read-only
    STATUS      current
    DESCRIPTION ""
    ::= { fields 48 }

viptelaSecurityUuid OBJECT-TYPE
    SYNTAX      OCTET STRING
    MAX-ACCESS  read-only
    STATUS      current
    DESCRIPTION ""
    ::= { fields 49 }

viptelaSecuritySerial OBJECT-TYPE
    SYNTAX      OCTET STRING
    MAX-ACCESS  read-only
    STATUS      current
    DESCRIPTION ""
    ::= { fields 50 }

viptelaSystemProcessName OBJECT-TYPE
    SYNTAX      OCTET STRING
    MAX-ACCESS  read-only
    STATUS      current
    DESCRIPTION ""
    ::= { fields 51 }

viptelaSystemProcessId OBJECT-TYPE
    SYNTAX      Unsigned32
    MAX-ACCESS  read-only
    STATUS      current
    DESCRIPTION ""
    ::= { fields 52 }

viptelaSystemReason OBJECT-TYPE
    SYNTAX      OCTET STRING
    MAX-ACCESS  read-only
    STATUS      current
    DESCRIPTION ""
    ::= { fields 53 }

viptelaSystemWarning OBJECT-TYPE
    SYNTAX      OCTET STRING
    MAX-ACCESS  read-only
    STATUS      current
    DESCRIPTION ""
    ::= { fields 54 }

viptelaSystemTotalMb OBJECT-TYPE
    SYNTAX      Unsigned32
    MAX-ACCESS  read-only
    STATUS      current
    DESCRIPTION ""
    ::= { fields 55 }

viptelaSystemFreeMb OBJECT-TYPE
    SYNTAX      Unsigned32
    MAX-ACCESS  read-only
    STATUS      current
    DESCRIPTION ""
    ::= { fields 56 }

viptelaSystemOldSiteId OBJECT-TYPE
    SYNTAX      SiteId
    MAX-ACCESS  read-only
    STATUS      current
    DESCRIPTION ""
    ::= { fields 57 }

viptelaSystemNewSiteId OBJECT-TYPE
    SYNTAX      SiteId
    MAX-ACCESS  read-only
    STATUS      current
    DESCRIPTION ""
    ::= { fields 58 }

viptelaSystemOldDomainId OBJECT-TYPE
    SYNTAX      DomainId
    MAX-ACCESS  read-only
    STATUS      current
    DESCRIPTION ""
    ::= { fields 59 }

viptelaSystemNewDomainId OBJECT-TYPE
    SYNTAX      DomainId
    MAX-ACCESS  read-only
    STATUS      current
    DESCRIPTION ""
    ::= { fields 60 }

viptelaSystemOldSystemIp OBJECT-TYPE
    SYNTAX      ViptelaIpAddress
    MAX-ACCESS  read-only
    STATUS      current
    DESCRIPTION ""
    ::= { fields 61 }

viptelaSystemNewSystemIp OBJECT-TYPE
    SYNTAX      ViptelaIpAddress
    MAX-ACCESS  read-only
    STATUS      current
    DESCRIPTION ""
    ::= { fields 62 }

viptelaSystemOldOrganizationName OBJECT-TYPE
    SYNTAX      OCTET STRING
    MAX-ACCESS  read-only
    STATUS      current
    DESCRIPTION ""
    ::= { fields 63 }

viptelaSystemNewOrganizationName OBJECT-TYPE
    SYNTAX      OCTET STRING
    MAX-ACCESS  read-only
    STATUS      current
    DESCRIPTION ""
    ::= { fields 64 }

viptelaSystemUserName OBJECT-TYPE
    SYNTAX      OCTET STRING
    MAX-ACCESS  read-only
    STATUS      current
    DESCRIPTION ""
    ::= { fields 65 }

viptelaSystemUserId OBJECT-TYPE
    SYNTAX      Integer32
    MAX-ACCESS  read-only
    STATUS      current
    DESCRIPTION ""
    ::= { fields 66 }

viptelaVpnVpnId OBJECT-TYPE
    SYNTAX      VpnId
    MAX-ACCESS  read-only
    STATUS      current
    DESCRIPTION ""
    ::= { fields 67 }

viptelaVpnPeer OBJECT-TYPE
    SYNTAX      ViptelaIpAddress
    MAX-ACCESS  read-only
    STATUS      current
    DESCRIPTION ""
    ::= { fields 68 }

viptelaVpnBgpNewState OBJECT-TYPE
    SYNTAX      BgpState
    MAX-ACCESS  read-only
    STATUS      current
    DESCRIPTION ""
    ::= { fields 69 }

viptelaVpnLocalAddress OBJECT-TYPE
    SYNTAX      ViptelaIpAddress
    MAX-ACCESS  read-only
    STATUS      current
    DESCRIPTION ""
    ::= { fields 70 }

viptelaVpnLocalRouterid OBJECT-TYPE
    SYNTAX      ViptelaIpAddress
    MAX-ACCESS  read-only
    STATUS      current
    DESCRIPTION ""
    ::= { fields 71 }

viptelaVpnPeerRouterid OBJECT-TYPE
    SYNTAX      ViptelaIpAddress
    MAX-ACCESS  read-only
    STATUS      current
    DESCRIPTION ""
    ::= { fields 72 }

viptelaVpnIfName OBJECT-TYPE
    SYNTAX      OCTET STRING
    MAX-ACCESS  read-only
    STATUS      current
    DESCRIPTION ""
    ::= { fields 73 }

viptelaVpnNewState OBJECT-TYPE
    SYNTAX      OperState
    MAX-ACCESS  read-only
    STATUS      current
    DESCRIPTION ""
    ::= { fields 74 }

viptelaVpnGrpId OBJECT-TYPE
    SYNTAX      Unsigned32
    MAX-ACCESS  read-only
    STATUS      current
    DESCRIPTION ""
    ::= { fields 75 }

viptelaVpnIpPrefix OBJECT-TYPE
    SYNTAX      OCTET STRING (SIZE (5))
    MAX-ACCESS  read-only
    STATUS      current
    DESCRIPTION ""
    ::= { fields 76 }

viptelaVpnFailureReason OBJECT-TYPE
    SYNTAX      OCTET STRING
    MAX-ACCESS  read-only
    STATUS      current
    DESCRIPTION ""
    ::= { fields 77 }

viptelaVpnFarEndSystemIp OBJECT-TYPE
    SYNTAX      ViptelaIpAddress
    MAX-ACCESS  read-only
    STATUS      current
    DESCRIPTION ""
    ::= { fields 78 }

viptelaVpnFarEndColor OBJECT-TYPE
    SYNTAX      ColorEnum
    MAX-ACCESS  read-only
    STATUS      current
    DESCRIPTION ""
    ::= { fields 79 }

viptelaVpnClientMac OBJECT-TYPE
    SYNTAX      OCTET STRING
    MAX-ACCESS  read-only
    STATUS      current
    DESCRIPTION ""
    ::= { fields 80 }

viptelaVpnIp OBJECT-TYPE
    SYNTAX      ViptelaIpAddress
    MAX-ACCESS  read-only
    STATUS      current
    DESCRIPTION ""
    ::= { fields 81 }

viptelaVpnReason OBJECT-TYPE
    SYNTAX      OCTET STRING
    MAX-ACCESS  read-only
    STATUS      current
    DESCRIPTION ""
    ::= { fields 82 }

viptelaVpnState OBJECT-TYPE
    SYNTAX      Enumeration
    MAX-ACCESS  read-only
    STATUS      current
    DESCRIPTION ""
    ::= { fields 83 }

viptelaVpnNeighbor OBJECT-TYPE
    SYNTAX      ViptelaIpAddress
    MAX-ACCESS  read-only
    STATUS      current
    DESCRIPTION ""
    ::= { fields 84 }

viptelaVpnPimNewState OBJECT-TYPE
    SYNTAX      StateEnum
    MAX-ACCESS  read-only
    STATUS      current
    DESCRIPTION ""
    ::= { fields 85 }

viptelaVpnInterface OBJECT-TYPE
    SYNTAX      OCTET STRING
    MAX-ACCESS  read-only
    STATUS      current
    DESCRIPTION ""
    ::= { fields 86 }

viptelaVpnTunnelAddress OBJECT-TYPE
    SYNTAX      ViptelaIpAddress
    MAX-ACCESS  read-only
    STATUS      current
    DESCRIPTION ""
    ::= { fields 87 }

viptelaVpnRouterId OBJECT-TYPE
    SYNTAX      ViptelaIpAddress
    MAX-ACCESS  read-only
    STATUS      current
    DESCRIPTION ""
    ::= { fields 88 }

viptelaVpnOspfNewState OBJECT-TYPE
    SYNTAX      OspfStateEnum
    MAX-ACCESS  read-only
    STATUS      current
    DESCRIPTION ""
    ::= { fields 89 }

viptelaVpnIfAddr OBJECT-TYPE
    SYNTAX      Ipv4UcastAddrPrefix
    MAX-ACCESS  read-only
    STATUS      current
    DESCRIPTION ""
    ::= { fields 90 }

viptelaVpnOspfInterfaceNewState OBJECT-TYPE
	SYNTAX      OspfIfStateEnum
	MAX-ACCESS  read-only
	STATUS      current
	DESCRIPTION ""
	::= { fields 91 }

viptelaVpnVrrpGroupState OBJECT-TYPE
	SYNTAX      VrrpGroupStateEnum
	MAX-ACCESS  read-only
	STATUS      current
	DESCRIPTION ""
	::= { fields 92 }

viptelaSystemStatusStr OBJECT-TYPE
    SYNTAX      OCTET STRING
    MAX-ACCESS  read-only
    STATUS      current
    DESCRIPTION ""
    ::= { fields 93 }

viptelaAppRouteSrcIp OBJECT-TYPE
    SYNTAX      ViptelaIpAddress
    MAX-ACCESS  read-only
    STATUS      current
    DESCRIPTION ""
    ::= { fields 94 }

viptelaAppRouteDstIp OBJECT-TYPE
    SYNTAX      ViptelaIpAddress
    MAX-ACCESS  read-only
    STATUS      current
    DESCRIPTION ""
    ::= { fields 95 }

viptelaAppRouteProto OBJECT-TYPE
    SYNTAX      EncapEnum
    MAX-ACCESS  read-only
    STATUS      current
    DESCRIPTION ""
    ::= { fields 96 }

viptelaAppRouteSrcPort OBJECT-TYPE
    SYNTAX      Unsigned32
    MAX-ACCESS  read-only
    STATUS      current
    DESCRIPTION ""
    ::= { fields 97 }

viptelaAppRouteDstPort OBJECT-TYPE
    SYNTAX      Unsigned32
    MAX-ACCESS  read-only
    STATUS      current
    DESCRIPTION ""
    ::= { fields 98 }

viptelaAppRouteLocalSystemIp OBJECT-TYPE
    SYNTAX      ViptelaIpAddress
    MAX-ACCESS  read-only
    STATUS      current
    DESCRIPTION ""
    ::= { fields 99 }

viptelaAppRouteLocalColor OBJECT-TYPE
    SYNTAX      OCTET STRING
    MAX-ACCESS  read-only
    STATUS      current
    DESCRIPTION ""
    ::= { fields 100 }

viptelaAppRouteRemoteSystemIp OBJECT-TYPE
    SYNTAX      ViptelaIpAddress
    MAX-ACCESS  read-only
    STATUS      current
    DESCRIPTION ""
    ::= { fields 101 }

viptelaAppRouteRemoteColor OBJECT-TYPE
    SYNTAX      OCTET STRING
    MAX-ACCESS  read-only
    STATUS      current
    DESCRIPTION ""
    ::= { fields 102 }

viptelaAppRouteMeanLoss OBJECT-TYPE
    SYNTAX      UnsignedByte
    MAX-ACCESS  read-only
    STATUS      current
    DESCRIPTION ""
    ::= { fields 103 }

viptelaAppRouteMeanLatency OBJECT-TYPE
    SYNTAX      Unsigned32
    MAX-ACCESS  read-only
    STATUS      current
    DESCRIPTION ""
    ::= { fields 104 }

viptelaAppRouteSlaClasses OBJECT-TYPE
    SYNTAX      OCTET STRING
    MAX-ACCESS  read-only
    STATUS      current
    DESCRIPTION ""
    ::= { fields 105 }

viptelaActionsStatus OBJECT-TYPE
    SYNTAX      InstallationStatus 
    MAX-ACCESS  read-only
    STATUS      current
    DESCRIPTION ""
    ::= { fields 106 }

viptelaActionsInstallId OBJECT-TYPE
    SYNTAX      OCTET STRING
    MAX-ACCESS  read-only
    STATUS      current
    DESCRIPTION ""
    ::= { fields 107 }

viptelaActionsMessage OBJECT-TYPE
    SYNTAX      OCTET STRING
    MAX-ACCESS  read-only
    STATUS      current
    DESCRIPTION ""
    ::= { fields 108 }

viptelaVpnOperState OBJECT-TYPE
    SYNTAX      StateEnum
    MAX-ACCESS  read-only
    STATUS      current
    DESCRIPTION ""
    ::= { fields 109 }

viptelaVpnAdminState OBJECT-TYPE
    SYNTAX      AdminStateEnum
    MAX-ACCESS  read-only
    STATUS      current
    DESCRIPTION ""
    ::= { fields 110 }

viptelaVpnAddressFamilyType OBJECT-TYPE
    SYNTAX      AddressFamilyEnum
    MAX-ACCESS  read-only
    STATUS      current
    DESCRIPTION "Address family"
    ::= { fields 111 }

viptelaVpnFibLastUpdateTime OBJECT-TYPE
    SYNTAX      DateAndTime
    MAX-ACCESS  read-only
    STATUS      current
    DESCRIPTION ""
    ::= { fields 112 }
    
viptelaBridgeId OBJECT-TYPE
    SYNTAX      BridgeId
    MAX-ACCESS  read-only
    STATUS      current
    DESCRIPTION "Bridge Id"
    ::= { fields 113 }

viptelaNumMacs OBJECT-TYPE
    SYNTAX      NumMacs
    MAX-ACCESS  read-only
    STATUS      current
    DESCRIPTION "Num MACs"
    ::= { fields 114 }

viptelaPolicyVpnId OBJECT-TYPE
    SYNTAX      VpnId
    MAX-ACCESS  read-only
    STATUS      current
    DESCRIPTION ""
    ::= { fields 115 }

viptelaPolicyApplication OBJECT-TYPE
    SYNTAX      OCTET STRING
    MAX-ACCESS  read-only
    STATUS      current
    DESCRIPTION ""
    ::= { fields 116 }

viptelaPolicySourceIp OBJECT-TYPE
    SYNTAX      ViptelaIpAddress
    MAX-ACCESS  read-only
    STATUS      current
    DESCRIPTION ""
    ::= { fields 117 }

viptelaPolicySourcePort OBJECT-TYPE
    SYNTAX      Unsigned32
    MAX-ACCESS  read-only
    STATUS      current
    DESCRIPTION ""
    ::= { fields 118 }

viptelaPolicyDestinationIp OBJECT-TYPE
    SYNTAX      ViptelaIpAddress
    MAX-ACCESS  read-only
    STATUS      current
    DESCRIPTION ""
    ::= { fields 119 }

viptelaPolicyDestinationPort OBJECT-TYPE
    SYNTAX      Unsigned32
    MAX-ACCESS  read-only
    STATUS      current
    DESCRIPTION ""
    ::= { fields 120 }

viptelaPolicyProtocol OBJECT-TYPE
    SYNTAX      Unsigned32
    MAX-ACCESS  read-only
    STATUS      current
    DESCRIPTION ""
    ::= { fields 121 }

viptelaPolicyDscp OBJECT-TYPE
    SYNTAX      Unsigned32
    MAX-ACCESS  read-only
    STATUS      current
    DESCRIPTION ""
    ::= { fields 122 }

viptelaPolicySlaInformation OBJECT-TYPE
    SYNTAX      OCTET STRING
    MAX-ACCESS  read-only
    STATUS      current
    DESCRIPTION ""
    ::= { fields 123 }

viptelaPolicySlaStatus OBJECT-TYPE
    SYNTAX      OCTET STRING
    MAX-ACCESS  read-only
    STATUS      current
    DESCRIPTION ""
    ::= { fields 124 }

viptelaSystemDpiOutOfMemoryState OBJECT-TYPE
    SYNTAX      TruthValue
    MAX-ACCESS  read-only
    STATUS      current
    DESCRIPTION ""
    ::= { fields 125 }

viptelaBfdDeleted OBJECT-TYPE
    SYNTAX      BoolEnum
    MAX-ACCESS  read-only
    STATUS      current
    DESCRIPTION ""
    ::= { fields 126 }

viptelaSecurityGreOldOperState OBJECT-TYPE
    SYNTAX      OperState	
    MAX-ACCESS  read-only
    STATUS	current
    DESCRIPTION ""
    ::= { fields 127 } 

viptelaSecurityGreNewOperState OBJECT-TYPE
    SYNTAX	OperState
    MAX-ACCESS  read-only
    STATUS	current
    DESCRIPTION ""
    ::= { fields 128 } 

viptelaSecurityGreIfName OBJECT-TYPE
    SYNTAX	OCTET STRING	
    MAX-ACCESS  read-only
    STATUS	current
    DESCRIPTION ""
    ::= { fields 129 } 

viptelaSecurityGreVpnId OBJECT-TYPE
    SYNTAX      VpnId	
    MAX-ACCESS  read-only
    STATUS	current
    DESCRIPTION ""
    ::= { fields 130 } 

viptelaSecurityGreTunnelSource OBJECT-TYPE
    SYNTAX      ViptelaIpAddress 	
    MAX-ACCESS  read-only
    STATUS	current
    DESCRIPTION ""
    ::= { fields 131 } 

viptelaSecurityGreTunnelDestination OBJECT-TYPE
    SYNTAX      ViptelaIpAddress	
    MAX-ACCESS  read-only
    STATUS	current
    DESCRIPTION ""
    ::= { fields 132 } 

viptelaSecurityGreGreIp OBJECT-TYPE
    SYNTAX      OCTET STRING	
    MAX-ACCESS  read-only
    STATUS	current
    DESCRIPTION ""
    ::= { fields 133 } 

viptelaVpnIfCfgBwKbps OBJECT-TYPE
    SYNTAX      Unsigned32	
    MAX-ACCESS  read-only
    STATUS	current
    DESCRIPTION ""
    ::= { fields 134 } 

viptelaVpnTrafficDirection OBJECT-TYPE
    SYNTAX      TrafficDirectionEnum	
    MAX-ACCESS  read-only
    STATUS	current
    DESCRIPTION ""
    ::= { fields 135 } 

viptelaVpnDuration OBJECT-TYPE
    SYNTAX      Unsigned32	
    MAX-ACCESS  read-only
    STATUS	current
    DESCRIPTION ""
    ::= { fields 136 }

viptelaAppRouteMeanJitter OBJECT-TYPE
    SYNTAX      Unsigned32
    MAX-ACCESS  read-only
    STATUS      current
    DESCRIPTION ""
    ::= { fields 137 }

viptelaVpnPimEnabled OBJECT-TYPE
    SYNTAX      TruthValue
    MAX-ACCESS  read-only
    STATUS      current
    DESCRIPTION ""
    ::= { fields 138 }

viptelaSystemRemoteHost OBJECT-TYPE
    SYNTAX      OCTET STRING
    MAX-ACCESS  read-only
    STATUS      current
    DESCRIPTION ""
    ::= { fields 139 }

viptelaPolicyVpnListName OBJECT-TYPE
    SYNTAX      OCTET STRING
    MAX-ACCESS  read-only
    STATUS      current
    DESCRIPTION ""
    ::= { fields 140 }

viptelaPolicyName OBJECT-TYPE
    SYNTAX      OCTET STRING
    MAX-ACCESS  read-only
    STATUS      current
    DESCRIPTION ""
    ::= { fields 141 }

viptelaPolicyAccessListName OBJECT-TYPE
    SYNTAX      OCTET STRING
    MAX-ACCESS  read-only
    STATUS      current
    DESCRIPTION ""
    ::= { fields 142 }

viptelaPolicyStatus OBJECT-TYPE
    SYNTAX      OCTET STRING
    MAX-ACCESS  read-only
    STATUS      current
    DESCRIPTION ""
    ::= { fields 143 }

viptelaSecurityVmanageConnectionPreference OBJECT-TYPE
    SYNTAX      UnsignedByte
    MAX-ACCESS  read-only
    STATUS      current
    DESCRIPTION ""
    ::= { fields 144 }

viptelaHardwareSensorNewState OBJECT-TYPE
    SYNTAX      SensorStateEnum
    MAX-ACCESS  read-only
    STATUS      current
    DESCRIPTION ""
    ::= { fields 145 }

viptelaCloudExpressApplication OBJECT-TYPE
    SYNTAX      CloudAppEnum
    MAX-ACCESS  read-only
    STATUS      current
    DESCRIPTION ""
    ::= { fields 146 }

viptelaCloudExpressExitType OBJECT-TYPE
    SYNTAX      CloudExitEnum
    MAX-ACCESS  read-only
    STATUS      current
    DESCRIPTION ""
    ::= { fields 147 }

viptelaGatewayIp OBJECT-TYPE
    SYNTAX      ViptelaIpAddress
    MAX-ACCESS  read-only
    STATUS      current
    DESCRIPTION ""
    ::= { fields 148 }

viptelaAppLatency  OBJECT-TYPE
    SYNTAX      Unsigned32
    MAX-ACCESS  read-only
    STATUS      current
    DESCRIPTION ""
    ::= { fields 149 }

viptelaAppLoss  OBJECT-TYPE
    SYNTAX      Unsigned32
    MAX-ACCESS  read-only
    STATUS      current
    DESCRIPTION ""
    ::= { fields 150 }

viptelaWwanSimSlot OBJECT-TYPE
    SYNTAX      Unsigned32
    MAX-ACCESS  read-only
    STATUS      current
    DESCRIPTION ""
    ::= { fields 151 }

viptelaWwanSimState OBJECT-TYPE
    SYNTAX      WwanSimStatusEnum
    MAX-ACCESS  read-only
    STATUS      current
    DESCRIPTION ""
    ::= { fields 152 }

viptelaAppRouteOldSlaClasses OBJECT-TYPE
    SYNTAX      OCTET STRING
    MAX-ACCESS  read-only
    STATUS      current
    DESCRIPTION ""
    ::= { fields 153 }

viptelaVpnNewAdminState OBJECT-TYPE
    SYNTAX      AdminState
    MAX-ACCESS  read-only
    STATUS      current
    DESCRIPTION ""
    ::= { fields 154 }

viptelaWwanDomainState OBJECT-TYPE
    SYNTAX      WwanDomainStatusEnum
    MAX-ACCESS  read-only
    STATUS      current
    DESCRIPTION ""
    ::= { fields 155 }
    
viptelaWwanRegState OBJECT-TYPE
    SYNTAX      WwanRegStatusEnum
    MAX-ACCESS  read-only
    STATUS      current
    DESCRIPTION ""
    ::= { fields 156 }
    
viptelaWwanBearer OBJECT-TYPE
    SYNTAX      WwanBearerEnum
    MAX-ACCESS  read-only
    STATUS      current
    DESCRIPTION ""
    ::= { fields 157 }

viptelaActionsReason OBJECT-TYPE
    SYNTAX      OCTET STRING
    MAX-ACCESS  read-only
    STATUS      current
    DESCRIPTION ""
    ::= { fields 158 }

viptelaWwanIfname OBJECT-TYPE
    SYNTAX      OCTET STRING
    MAX-ACCESS  read-only
    STATUS      current
    DESCRIPTION ""
    ::= { fields 159 }

viptelaExitLocalColor OBJECT-TYPE
    SYNTAX      OCTET STRING
    MAX-ACCESS  read-only
    STATUS      current
    DESCRIPTION ""
    ::= { fields 160 }

viptelaExitRemoteColor OBJECT-TYPE
    SYNTAX      OCTET STRING
    MAX-ACCESS  read-only
    STATUS      current
    DESCRIPTION ""
    ::= { fields 161 }

viptelaSecurityOrganizationName OBJECT-TYPE
    SYNTAX      OCTET STRING
    MAX-ACCESS  read-only
    STATUS      current
    DESCRIPTION ""
    ::= { fields 162 }

viptelaSecuritySpOrganizationName OBJECT-TYPE
    SYNTAX      OCTET STRING
    MAX-ACCESS  read-only
    STATUS      current
    DESCRIPTION ""
    ::= { fields 163 }

viptelaBfdFlapReason OBJECT-TYPE
    SYNTAX      BfdFlapReasonEnum
    MAX-ACCESS  read-only
    STATUS      current
    DESCRIPTION ""
    ::= { fields 164 }

viptelaSecurityPeerVmanageSystemIp OBJECT-TYPE
    SYNTAX      ViptelaIpAddress
    MAX-ACCESS  read-only
    STATUS      current
    DESCRIPTION ""
    ::= { fields 165 }

viptelaPolicySvcVpnId OBJECT-TYPE
    SYNTAX      VpnId
    MAX-ACCESS  read-only
    STATUS      current
    DESCRIPTION ""
    ::= { fields 166 }

viptelaPolicyZonePair OBJECT-TYPE
    SYNTAX      OCTET STRING
    MAX-ACCESS  read-only
    STATUS      current
    DESCRIPTION ""
    ::= { fields 167 }

viptelaPolicySourceVpn OBJECT-TYPE
    SYNTAX      VpnId
    MAX-ACCESS  read-only
    STATUS      current
    DESCRIPTION ""
    ::= { fields 168 }

viptelaPolicyDestinationVpn OBJECT-TYPE
    SYNTAX      VpnId
    MAX-ACCESS  read-only
    STATUS      current
    DESCRIPTION ""
    ::= { fields 169 }

viptelaPolicyState OBJECT-TYPE
    SYNTAX      OCTET STRING
    MAX-ACCESS  read-only
    STATUS      current
    DESCRIPTION ""
    ::= { fields 170 }

viptelaPolicyCurrFlows OBJECT-TYPE
    SYNTAX      Unsigned32
    MAX-ACCESS  read-only
    STATUS      current
    DESCRIPTION ""
    ::= { fields 171 }

viptelaPolicyHthreshFlows OBJECT-TYPE
    SYNTAX      Unsigned32
    MAX-ACCESS  read-only
    STATUS      current
    DESCRIPTION ""
    ::= { fields 172 }

viptelaPolicyLthreshFlows OBJECT-TYPE
    SYNTAX      Unsigned32
    MAX-ACCESS  read-only
    STATUS      current
    DESCRIPTION ""
    ::= { fields 173 }

viptelaPolicyMaxFlows OBJECT-TYPE
    SYNTAX      Unsigned32
    MAX-ACCESS  read-only
    STATUS      current
    DESCRIPTION ""
    ::= { fields 174 }

viptelaPolicyAction OBJECT-TYPE
    SYNTAX      OCTET STRING
    MAX-ACCESS  read-only
    STATUS      current
    DESCRIPTION ""
    ::= { fields 175 }

viptelaPolicyCurrHalfOpenFlows OBJECT-TYPE
    SYNTAX      Unsigned32
    MAX-ACCESS  read-only
    STATUS      current
    DESCRIPTION ""
    ::= { fields 176 }

viptelaPolicyHthreshHalfOpenFlows OBJECT-TYPE
    SYNTAX      Unsigned32
    MAX-ACCESS  read-only
    STATUS      current
    DESCRIPTION ""
    ::= { fields 177 }

viptelaPolicyMaxHalfOpenFlows OBJECT-TYPE
    SYNTAX      Unsigned32
    MAX-ACCESS  read-only
    STATUS      current
    DESCRIPTION ""
    ::= { fields 178 }

viptelaPolicyLthreshHalfOpenFlows OBJECT-TYPE
    SYNTAX      Unsigned32
    MAX-ACCESS  read-only
    STATUS      current
    DESCRIPTION ""
    ::= { fields 179 }

viptelaPolicySlaName OBJECT-TYPE
    SYNTAX      OCTET STRING
    MAX-ACCESS  read-only
    STATUS      current
    DESCRIPTION ""
    ::= { fields 180 }

viptelaPolicySlaOperation OBJECT-TYPE
    SYNTAX      OCTET STRING
    MAX-ACCESS  read-only
    STATUS      current
    DESCRIPTION ""
    ::= { fields 181 }

viptelaPolicySlaLoss OBJECT-TYPE
    SYNTAX      UnsignedByte 
    MAX-ACCESS  read-only
    STATUS      current
    DESCRIPTION ""
    ::= { fields 182 }

viptelaPolicySlaLatency OBJECT-TYPE
    SYNTAX      Unsigned32
    MAX-ACCESS  read-only
    STATUS      current
    DESCRIPTION ""
    ::= { fields 183 }

viptelaPolicySlaJitter OBJECT-TYPE
    SYNTAX      Unsigned32
    MAX-ACCESS  read-only
    STATUS      current
    DESCRIPTION ""
    ::= { fields 184 }

viptelaPolicyDevicePolicyName OBJECT-TYPE
    SYNTAX      OCTET STRING
    MAX-ACCESS  read-only
    STATUS      current
    DESCRIPTION ""
    ::= { fields 185 }

viptelaWwanQosState OBJECT-TYPE
    SYNTAX      WwanQosStatusEnum
    MAX-ACCESS  read-only
    STATUS      current
    DESCRIPTION ""
    ::= { fields 186 }

viptelaSecuritySubjectSerialNumber OBJECT-TYPE
    SYNTAX      OCTET STRING
    MAX-ACCESS  read-only
    STATUS      current
    DESCRIPTION ""
    ::= { fields 187 }

viptelaAppRouteAppProbePfrStats OBJECT-TYPE
    SYNTAX      OCTET STRING
    MAX-ACCESS  read-only
    STATUS      current
    DESCRIPTION ""
    ::= { fields 188 }

viptelaPolicySlaAppProbeClass OBJECT-TYPE
    SYNTAX      OCTET STRING
    MAX-ACCESS  read-only
    STATUS      current
    DESCRIPTION ""
    ::= { fields 189 }

viptelaSystemCpuUserPercentage OBJECT-TYPE
    SYNTAX      OCTET STRING
    MAX-ACCESS  read-only
    STATUS      current
    DESCRIPTION ""
    ::= { fields 190 }

viptelaSystemCpuSystemPercentage OBJECT-TYPE
    SYNTAX      OCTET STRING
    MAX-ACCESS  read-only
    STATUS      current
    DESCRIPTION ""
    ::= { fields 191 }

viptelaSystemCpuIdlePercentage OBJECT-TYPE
    SYNTAX      OCTET STRING
    MAX-ACCESS  read-only
    STATUS      current
    DESCRIPTION ""
    ::= { fields 192 }

viptelaSecurityCertificateType OBJECT-TYPE
    SYNTAX      CertificateTypeEnum
    MAX-ACCESS  read-only
    STATUS      current
    DESCRIPTION ""
    ::= { fields 193 }

viptelaSecurityIssuer OBJECT-TYPE
    SYNTAX      OCTET STRING
    MAX-ACCESS  read-only
    STATUS      current
    DESCRIPTION ""
    ::= { fields 194 }

viptelaSecurityDaysToExpiry OBJECT-TYPE
    SYNTAX      Integer32
    MAX-ACCESS  read-only
    STATUS      current
    DESCRIPTION ""
    ::= { fields 195 }
    
viptelaSecurityCertificateSerialNumber OBJECT-TYPE
    SYNTAX      OCTET STRING
    MAX-ACCESS  read-only
    STATUS      current
    DESCRIPTION ""
    ::= { fields 196 }

viptelaPolicyAppAlias OBJECT-TYPE
    SYNTAX      OCTET STRING
    MAX-ACCESS  read-only
    STATUS      current
    DESCRIPTION ""
    ::= { fields 197 }

viptelaPolicyUnsupportedApp OBJECT-TYPE
    SYNTAX      OCTET STRING
    MAX-ACCESS  read-only
    STATUS      current
    DESCRIPTION ""
    ::= { fields 198 }

viptelaPolicyAppListName OBJECT-TYPE
    SYNTAX      OCTET STRING
    MAX-ACCESS  read-only
    STATUS      current
    DESCRIPTION ""
    ::= { fields 199 }

viptelaHardwareSfpDiagName OBJECT-TYPE
    SYNTAX      OCTET STRING
    MAX-ACCESS  read-only
    STATUS      current
    DESCRIPTION ""
    ::= { fields 200 }

viptelaHardwareSfpDiagState OBJECT-TYPE
    SYNTAX      SfpDiagStateEnum
    MAX-ACCESS  read-only
    STATUS      current
    DESCRIPTION ""
    ::= { fields 201 }

viptelaHardwareSfpDiagStateDescription OBJECT-TYPE
    SYNTAX      OCTET STRING
    MAX-ACCESS  read-only
    STATUS      current
    DESCRIPTION ""
    ::= { fields 202 }

-- Notification definitions
viptelaActionsSystemSoftwareInstallStatus NOTIFICATION-TYPE
	OBJECTS {
		eventTime,
		netconfNotificationSeverity,
		viptelaActionsStatus,
		viptelaActionsInstallId,
		viptelaActionsMessage
	}
	STATUS current
	DESCRIPTION "Status of system software install"
	::= { traps 1 }

viptelaActionsSystemRebootIssued NOTIFICATION-TYPE
	OBJECTS {
		eventTime,
		netconfNotificationSeverity,
                viptelaActionsRebootReason
	}
	STATUS current
	DESCRIPTION "Issued a system reboot"
	::= { traps 2 }

viptelaActionsSystemRebootComplete NOTIFICATION-TYPE
	OBJECTS {
		eventTime,
		netconfNotificationSeverity
	}
	STATUS current
	DESCRIPTION "System reboot completed"
	::= { traps 3 }

viptelaBfdBfdStateChange NOTIFICATION-TYPE
	OBJECTS {
		eventTime,
		netconfNotificationSeverity,
		viptelaBfdSrcIp,
		viptelaBfdDstIp,
		viptelaBfdProto,
		viptelaBfdSrcPort,
		viptelaBfdDstPort,
		viptelaBfdLocalSystemIp,
		viptelaBfdLocalColor,
		viptelaBfdRemoteSystemIp,
		viptelaBfdRemoteColor,
		viptelaBfdNewState,
		viptelaBfdDeleted,
        viptelaBfdFlapReason
	}
	STATUS current
	DESCRIPTION "Bfd state has changed"
	::= { traps 4 }

viptelaHardwareFlashFault NOTIFICATION-TYPE
	OBJECTS {
		eventTime,
		netconfNotificationSeverity,
		viptelaHardwareNewState
	}
	STATUS current
	DESCRIPTION "Flash fault"
	::= { traps 5 }

viptelaHardwareEmmcFault NOTIFICATION-TYPE
	OBJECTS {
		eventTime,
		netconfNotificationSeverity,
		viptelaHardwareNewState
	}
	STATUS current
	DESCRIPTION "Emmc fault"
	::= { traps 6 }

viptelaHardwareSdcardFault NOTIFICATION-TYPE
	OBJECTS {
		eventTime,
		netconfNotificationSeverity,
		viptelaHardwareNewState
	}
	STATUS current
	DESCRIPTION "Sdcard fault"
	::= { traps 7 }

viptelaHardwareTempsensorFault NOTIFICATION-TYPE
	OBJECTS {
		eventTime,
		netconfNotificationSeverity,
		viptelaHardwareHwSensorType,
		viptelaHardwareHwDevIndex,
		viptelaHardwareName,
		viptelaHardwareNewState
	}
	STATUS current
	DESCRIPTION "Tempsensor fault"
	::= { traps 8 }

viptelaHardwareTempsensorState NOTIFICATION-TYPE
	OBJECTS {
		eventTime,
		netconfNotificationSeverity,
		viptelaHardwareHwSensorType,
		viptelaHardwareHwDevIndex,
		viptelaHardwareName,
		viptelaHardwareTemp,
		viptelaHardwareSensorNewState
	}
	STATUS current
	DESCRIPTION "Tempsensor state"
	::= { traps 9 }

viptelaHardwareFanFault NOTIFICATION-TYPE
	OBJECTS {
		eventTime,
		netconfNotificationSeverity,
		viptelaHardwareFantrayId,
		viptelaHardwareFanId,
		viptelaHardwareNewState
	}
	STATUS current
	DESCRIPTION "Fan fault"
	::= { traps 10 }

viptelaHardwareFantrayFault NOTIFICATION-TYPE
	OBJECTS {
		eventTime,
		netconfNotificationSeverity,
		viptelaHardwareFantrayId,
		viptelaHardwareNewState
	}
	STATUS current
	DESCRIPTION "Fantray fault"
	::= { traps 11 }

viptelaHardwarePemFault NOTIFICATION-TYPE
	OBJECTS {
		eventTime,
		netconfNotificationSeverity,
		viptelaHardwarePemId,
		viptelaHardwareNewState
	}
	STATUS current
	DESCRIPTION "Pem fault"
	::= { traps 12 }

viptelaHardwarePemStateChange NOTIFICATION-TYPE
	OBJECTS {
		eventTime,
		netconfNotificationSeverity,
		viptelaHardwarePemId,
		viptelaHardwareNewState
	}
	STATUS current
	DESCRIPTION "Pem state change"
	::= { traps 13 }

viptelaHardwarePimFault NOTIFICATION-TYPE
	OBJECTS {
		eventTime,
		netconfNotificationSeverity,
		viptelaHardwarePimId,
		viptelaHardwareNewState
	}
	STATUS current
	DESCRIPTION "Pim fault"
	::= { traps 14 }

viptelaHardwarePimStateChange NOTIFICATION-TYPE
	OBJECTS {
		eventTime,
		netconfNotificationSeverity,
		viptelaHardwarePimId,
		viptelaHardwareNewState
	}
	STATUS current
	DESCRIPTION "Pim state change"
	::= { traps 15 }

viptelaHardwareSfpStateChange NOTIFICATION-TYPE
	OBJECTS {
		eventTime,
		netconfNotificationSeverity,
		viptelaHardwareSfpName,
		viptelaHardwareNewState
	}
	STATUS current
	DESCRIPTION "Sfp state change"
	::= { traps 16 }

viptelaHardwareUsbStateChange NOTIFICATION-TYPE
	OBJECTS {
		eventTime,
		netconfNotificationSeverity,
		viptelaHardwareUsbSlot,
		viptelaHardwareNewState
	}
	STATUS current
	DESCRIPTION "Usb state change"
	::= { traps 17 }

viptelaOmpOmpNumberOfVsmartsChange NOTIFICATION-TYPE
	OBJECTS {
		eventTime,
		netconfNotificationSeverity,
		viptelaOmpNumberOfVsmarts
	}
	STATUS current
	DESCRIPTION "The number of vsmarts changed"
	::= { traps 18 }

viptelaOmpOmpStateChange NOTIFICATION-TYPE
	OBJECTS {
		eventTime,
		netconfNotificationSeverity,
		viptelaOmpNewState
	}
	STATUS current
	DESCRIPTION "Omp state changed"
	::= { traps 19 }

viptelaOmpOmpPeerStateChange NOTIFICATION-TYPE
	OBJECTS {
		eventTime,
		netconfNotificationSeverity,
		viptelaOmpPeer,
		viptelaOmpPeerNewState
	}
	STATUS current
	DESCRIPTION "Omp peer state changed"
	::= { traps 20 }

viptelaOmpOmpTlocStateChange NOTIFICATION-TYPE
	OBJECTS {
		eventTime,
		netconfNotificationSeverity,
		viptelaOmpOmpAddressFamily
	}
	STATUS current
	DESCRIPTION "Omp tloc state changed"
	::= { traps 21 }

viptelaOmpOmpPolicy NOTIFICATION-TYPE
	OBJECTS {
		eventTime,
		netconfNotificationSeverity,
		viptelaOmpPolicy,
		viptelaOmpVsmartPeer
	}
	STATUS current
	DESCRIPTION "Omp policy"
	::= { traps 22 }

viptelaSecurityControlConnectionStateChange NOTIFICATION-TYPE
	OBJECTS {
		eventTime,
		netconfNotificationSeverity,
		viptelaSecurityPersonality,
		viptelaSecurityPeerType,
		viptelaSecurityPeerSystemIp,
		viptelaSecurityPeerVmanageSystemIp,
		viptelaSecurityPublicIp,
		viptelaSecurityPublicPort,
		viptelaSecuritySrcColor,
		viptelaSecurityRemoteColor,
		viptelaSecurityUptime,
		viptelaSecurityNewState
	}
	STATUS current
	DESCRIPTION "Control connections state changed"
	::= { traps 23 }

viptelaSecurityControlConnectionAuthFail NOTIFICATION-TYPE
	OBJECTS {
		eventTime,
		netconfNotificationSeverity,
		viptelaSecurityPersonality,
		viptelaSecurityPeerType,
		viptelaSecurityPeerSystemIp,
		viptelaSecurityLocalSystemIp,
		viptelaSecurityLocalColor,
		viptelaSecurityReason
	}
	STATUS current
	DESCRIPTION "Control connection authentication failed"
	::= { traps 24 }

viptelaSecurityControlVbondStateChange NOTIFICATION-TYPE
	OBJECTS {
		eventTime,
		netconfNotificationSeverity,
		viptelaSecurityPersonality,
		viptelaSecurityNewState
	}
	STATUS current
	DESCRIPTION "Control vbond state changed"
	::= { traps 25 }

viptelaSecurityControlConnectionTlocIpChange NOTIFICATION-TYPE
	OBJECTS {
		eventTime,
		netconfNotificationSeverity,
		viptelaSecurityPersonality,
		viptelaSecurityOldPublicIp,
		viptelaSecurityOldPublicPort,
		viptelaSecurityNewPublicIp,
		viptelaSecurityNewPublicPort
	}
	STATUS current
	DESCRIPTION "Control connection tloc ip changed"
	::= { traps 26 }

viptelaSecurityControlNoActiveVsmart NOTIFICATION-TYPE
	OBJECTS {
		eventTime,
		netconfNotificationSeverity,
		viptelaSecurityPersonality
	}
	STATUS current
	DESCRIPTION "No active vsmart in control"
	::= { traps 27 }

viptelaSecurityControlNoActiveVbond NOTIFICATION-TYPE
	OBJECTS {
		eventTime,
		netconfNotificationSeverity,
		viptelaSecurityPersonality
	}
	STATUS current
	DESCRIPTION "No active vbond in control"
	::= { traps 28 }

viptelaSecurityTunnelIpsecRekey NOTIFICATION-TYPE
	OBJECTS {
		eventTime,
		netconfNotificationSeverity,
		viptelaSecurityPersonality,
		viptelaSecurityColor
	}
	STATUS current
	DESCRIPTION "Tunnel ipsec rekey"
	::= { traps 29 }

viptelaSecurityTunnelIpsecManualRekey NOTIFICATION-TYPE
	OBJECTS {
		eventTime,
		netconfNotificationSeverity,
		viptelaSecurityPersonality,
		viptelaSecurityColor
	}
	STATUS current
	DESCRIPTION "Tunnel ipsec manual rekey"
	::= { traps 30 }

viptelaSecuritySecurityRootCertChainInstalled NOTIFICATION-TYPE
	OBJECTS {
		eventTime,
		netconfNotificationSeverity
	}
	STATUS current
	DESCRIPTION "Security root cert chain was installed"
	::= { traps 31 }

viptelaSecuritySecurityCertificateInstalled NOTIFICATION-TYPE
	OBJECTS {
		eventTime,
		netconfNotificationSeverity
	}
	STATUS current
	DESCRIPTION "Security certificate was installed"
	::= { traps 32 }

viptelaSecuritySecurityNewCsrGenerated NOTIFICATION-TYPE
	OBJECTS {
		eventTime,
		netconfNotificationSeverity
	}
	STATUS current
	DESCRIPTION "Security csr was generated"
	::= { traps 33 }

viptelaSecuritySecurityRootCertChainUninstalled NOTIFICATION-TYPE
	OBJECTS {
		eventTime,
		netconfNotificationSeverity
	}
	STATUS current
	DESCRIPTION "Security root cert chain was uninstalled"
	::= { traps 34 }

viptelaSecuritySecurityClearInstalledCertificate NOTIFICATION-TYPE
	OBJECTS {
		eventTime,
		netconfNotificationSeverity
	}
	STATUS current
	DESCRIPTION "Security clear installed certificate"
	::= { traps 35 }

viptelaSecuritySecurityVedgeSerialFileUploaded NOTIFICATION-TYPE
	OBJECTS {
		eventTime,
		netconfNotificationSeverity
	}
	STATUS current
	DESCRIPTION "Security vedge serial file was uploaded"
	::= { traps 36 }

viptelaSecuritySecurityVsmartSerialFileUploaded NOTIFICATION-TYPE
	OBJECTS {
		eventTime,
		netconfNotificationSeverity
	}
	STATUS current
	DESCRIPTION "Security vsmart serial file was uploaded"
	::= { traps 37 }

viptelaSecuritySecurityVedgeEntryAdded NOTIFICATION-TYPE
	OBJECTS {
		eventTime,
		netconfNotificationSeverity,
		viptelaSecurityUuid,
		viptelaSecuritySerial
	}
	STATUS current
	DESCRIPTION "Security vedge entry was added"
	::= { traps 38 }

viptelaSecuritySecurityVedgeEntryRemoved NOTIFICATION-TYPE
	OBJECTS {
		eventTime,
		netconfNotificationSeverity,
		viptelaSecurityUuid
	}
	STATUS current
	DESCRIPTION "Security vedge entry was removed"
	::= { traps 39 }

viptelaSecuritySecurityVsmartEntryAdded NOTIFICATION-TYPE
	OBJECTS {
		eventTime,
		netconfNotificationSeverity,
		viptelaSecuritySerial
	}
	STATUS current
	DESCRIPTION "Security vsmart entry was added"
	::= { traps 40 }

viptelaSecuritySecurityVsmartEntryRemoved NOTIFICATION-TYPE
	OBJECTS {
		eventTime,
		netconfNotificationSeverity,
		viptelaSecuritySerial
	}
	STATUS current
	DESCRIPTION "Security vsmart entry was removed"
	::= { traps 41 }

viptelaSystemProcessRestart NOTIFICATION-TYPE
	OBJECTS {
		eventTime,
		netconfNotificationSeverity,
		viptelaSystemProcessName,
		viptelaSystemProcessId,
		viptelaSystemReason
	}
	STATUS current
	DESCRIPTION "Process restart"
	::= { traps 42 }

viptelaSystemDiskUsage NOTIFICATION-TYPE
	OBJECTS {
		eventTime,
		netconfNotificationSeverity,
		viptelaSystemWarning,
		viptelaSystemTotalMb,
		viptelaSystemFreeMb
	}
	STATUS current
	DESCRIPTION "Disk usage"
	::= { traps 43 }

viptelaSystemMemoryUsage NOTIFICATION-TYPE
	OBJECTS {
		eventTime,
		netconfNotificationSeverity,
		viptelaSystemWarning,
		viptelaSystemTotalMb,
		viptelaSystemFreeMb
	}
	STATUS current
	DESCRIPTION "Memory usage"
	::= { traps 44 }

viptelaSystemAaaAdminPwdChange NOTIFICATION-TYPE
	OBJECTS {
		eventTime,
		netconfNotificationSeverity
	}
	STATUS current
	DESCRIPTION "AAA admin password has changed"
	::= { traps 45 }

viptelaSystemSiteIdChange NOTIFICATION-TYPE
	OBJECTS {
		eventTime,
		netconfNotificationSeverity,
		viptelaSystemOldSiteId,
		viptelaSystemNewSiteId
	}
	STATUS current
	DESCRIPTION "Site id has changed"
	::= { traps 46 }

viptelaSystemDomainIdChange NOTIFICATION-TYPE
	OBJECTS {
		eventTime,
		netconfNotificationSeverity,
		viptelaSystemOldDomainId,
		viptelaSystemNewDomainId
	}
	STATUS current
	DESCRIPTION "Domain id has changed"
	::= { traps 47 }

viptelaSystemSystemIpChange NOTIFICATION-TYPE
	OBJECTS {
		eventTime,
		netconfNotificationSeverity,
		viptelaSystemOldSystemIp,
		viptelaSystemNewSystemIp
	}
	STATUS current
	DESCRIPTION "System ip has changed"
	::= { traps 48 }

viptelaSystemOrgNameChange NOTIFICATION-TYPE
	OBJECTS {
		eventTime,
		netconfNotificationSeverity,
		viptelaSystemOldOrganizationName,
		viptelaSystemNewOrganizationName
	}
	STATUS current
	DESCRIPTION "System organization name has changed"
	::= { traps 49 }

viptelaSystemSystemLoginChange NOTIFICATION-TYPE
	OBJECTS {
		eventTime,
		netconfNotificationSeverity,
		viptelaSystemUserName,
		viptelaSystemUserId
	}
	STATUS current
	DESCRIPTION "System login has changed"
	::= { traps 50 }

viptelaSystemSystemLogoutChange NOTIFICATION-TYPE
	OBJECTS {
		eventTime,
		netconfNotificationSeverity,
		viptelaSystemUserName,
		viptelaSystemUserId
	}
	STATUS current
	DESCRIPTION "System logout has changed"
	::= { traps 51 }

viptelaSystemSystemAaaLoginFail NOTIFICATION-TYPE
	OBJECTS {
		eventTime,
		netconfNotificationSeverity,
		viptelaSystemUserName,
		viptelaSystemRemoteHost
	}
	STATUS current
	DESCRIPTION "System aaa login has Failed"
	::= { traps 52 }

viptelaSystemSystemCommit NOTIFICATION-TYPE
	OBJECTS {
		eventTime,
		netconfNotificationSeverity,
		viptelaSystemUserName
	}
	STATUS current
	DESCRIPTION "System commit"
	::= { traps 53 }

viptelaVpnBgpPeerStateChange NOTIFICATION-TYPE
	OBJECTS {
		eventTime,
		netconfNotificationSeverity,
		viptelaVpnVpnId,
		viptelaVpnPeer,
		viptelaVpnBgpNewState,
		viptelaVpnLocalAddress,
		viptelaVpnLocalRouterid,
		viptelaVpnPeerRouterid
	}
	STATUS current
	DESCRIPTION "Bgp peer state has changed"
	::= { traps 54 }

viptelaVpnInterfaceStateChange NOTIFICATION-TYPE
	OBJECTS {
		eventTime,
		netconfNotificationSeverity,
		viptelaVpnVpnId,
		viptelaVpnIfName,
		viptelaVpnNewState
	}
	STATUS current
	DESCRIPTION "Interface state has changed"
	::= { traps 55 }

viptelaVpnVrrpGroupStateChange NOTIFICATION-TYPE
	OBJECTS {
		eventTime,
		netconfNotificationSeverity,
		viptelaVpnVpnId,
        viptelaVpnIfName,
        viptelaVpnGrpId,
        viptelaVpnVrrpGroupState
	}
	STATUS current
	DESCRIPTION "Vrrp group state has changed"
	::= { traps 56 }

viptelaVpnRouteInstallFail NOTIFICATION-TYPE
	OBJECTS {
		eventTime,
		netconfNotificationSeverity,
		viptelaVpnIpPrefix,
		viptelaVpnFailureReason
	}
	STATUS current
	DESCRIPTION "Route install has failed"
	::= { traps 57 }

viptelaVpnTunnelInstallFail NOTIFICATION-TYPE
	OBJECTS {
		eventTime,
		netconfNotificationSeverity,
		viptelaVpnFarEndSystemIp,
		viptelaVpnFarEndColor,
		viptelaVpnFailureReason
	}
	STATUS current
	DESCRIPTION "Tunnel install has failed"
	::= { traps 58 }

viptelaVpnDhcpAddressAssigned NOTIFICATION-TYPE
	OBJECTS {
		eventTime,
		netconfNotificationSeverity,
		viptelaVpnVpnId,
		viptelaVpnIfName,
		viptelaVpnClientMac,
		viptelaVpnIp
	}
	STATUS current
	DESCRIPTION "Dhcp address was assigned"
	::= { traps 59 }

viptelaVpnDhcpAddressRenewed NOTIFICATION-TYPE
	OBJECTS {
		eventTime,
		netconfNotificationSeverity,
		viptelaVpnVpnId,
		viptelaVpnIfName,
		viptelaVpnClientMac,
		viptelaVpnIp
	}
	STATUS current
	DESCRIPTION "Dhcp address was renewed"
	::= { traps 60 }

viptelaVpnDhcpAddressReleased NOTIFICATION-TYPE
	OBJECTS {
		eventTime,
		netconfNotificationSeverity,
		viptelaVpnVpnId,
		viptelaVpnIfName,
		viptelaVpnClientMac,
		viptelaVpnIp,
		viptelaVpnReason
	}
	STATUS current
	DESCRIPTION "Dhcp address was released"
	::= { traps 61 }

viptelaVpnDhcpRequestRejected NOTIFICATION-TYPE
	OBJECTS {
		eventTime,
		netconfNotificationSeverity,
		viptelaVpnVpnId,
		viptelaVpnIfName,
		viptelaVpnClientMac,
		viptelaVpnIp,
		viptelaVpnReason
	}
	STATUS current
	DESCRIPTION "Dhcp request was rejected"
	::= { traps 62 }

viptelaVpnDhcpServerStateChange NOTIFICATION-TYPE
	OBJECTS {
		eventTime,
		netconfNotificationSeverity,
		viptelaVpnVpnId,
		viptelaVpnIfName,
		viptelaVpnState
	}
	STATUS current
	DESCRIPTION "Dhcp server state has changed"
	::= { traps 63 }

viptelaVpnPimNeighborStateChange NOTIFICATION-TYPE
	OBJECTS {
		eventTime,
		netconfNotificationSeverity,
		viptelaVpnVpnId,
		viptelaVpnNeighbor,
		viptelaVpnPimNewState
	}
	STATUS current
	DESCRIPTION "Pim neighbor state has changed"
	::= { traps 64 }

viptelaVpnPimInterfaceStateChange NOTIFICATION-TYPE
	OBJECTS {
		eventTime,
		netconfNotificationSeverity,
		viptelaVpnVpnId,
		viptelaVpnInterface,
        viptelaVpnOperState,
        viptelaVpnAdminState,
        viptelaVpnPimEnabled
	}
	STATUS current
	DESCRIPTION "Pim interface state has changed"
	::= { traps 65 }

viptelaVpnPimTunnelStateChange NOTIFICATION-TYPE
	OBJECTS {
		eventTime,
		netconfNotificationSeverity,
		viptelaVpnTunnelAddress,
		viptelaVpnPimNewState
	}
	STATUS current
	DESCRIPTION "Pim tunnel state has changed"
	::= { traps 66 }

viptelaVpnOspfNeighborStateChange NOTIFICATION-TYPE
	OBJECTS {
		eventTime,
		netconfNotificationSeverity,
		viptelaVpnVpnId,
		viptelaVpnNeighbor,
		viptelaVpnRouterId,
		viptelaVpnIfAddr,
		viptelaVpnOspfNewState
	}
	STATUS current
	DESCRIPTION "Ospf neighbor state has changed"
	::= { traps 67 }

viptelaVpnOspfInterfaceStateChange NOTIFICATION-TYPE
	OBJECTS {
		eventTime,
		netconfNotificationSeverity,
		viptelaVpnVpnId,
		viptelaVpnInterface,
		viptelaVpnOspfInterfaceNewState
	}
	STATUS current
	DESCRIPTION "Ospf interface state has changed"
	::= { traps 68 }

viptelaAppRouteSlaChange NOTIFICATION-TYPE
    OBJECTS {
        eventTime,
        netconfNotificationSeverity,
        viptelaAppRouteSrcIp,
        viptelaAppRouteDstIp,
        viptelaAppRouteProto,
        viptelaAppRouteSrcPort,
        viptelaAppRouteDstPort,
        viptelaAppRouteLocalSystemIp,
        viptelaAppRouteLocalColor,
        viptelaAppRouteRemoteSystemIp,
        viptelaAppRouteRemoteColor,
        viptelaAppRouteAppProbePfrStats,
        viptelaAppRouteSlaClasses,
        viptelaAppRouteOldSlaClasses
    }
    STATUS current
    DESCRIPTION "Sla change"
    ::= { traps 70 }

viptelaSecuritySecurityCertificateExpired NOTIFICATION-TYPE
	OBJECTS {
		eventTime,
		netconfNotificationSeverity
	}
	STATUS current
	DESCRIPTION "Security certificate has expired"
	::= { traps 71 }

viptelaVpnFibStateChange NOTIFICATION-TYPE
	OBJECTS {
		eventTime,
		netconfNotificationSeverity,
		viptelaVpnVpnId,
		viptelaVpnAddressFamilyType,
		viptelaVpnFibLastUpdateTime
	}
	STATUS current
	DESCRIPTION "Fib state has changed"
	::= { traps 72 }

viptelaBridgeCreation NOTIFICATION-TYPE
	OBJECTS {
		eventTime,
		netconfNotificationSeverity,
		viptelaBridgeId
	}
	STATUS current
	DESCRIPTION "Bridge creation"
	::= { traps 73 }

viptelaBridgeDeletion NOTIFICATION-TYPE
	OBJECTS {
		eventTime,
		netconfNotificationSeverity,
		viptelaBridgeId
	}
	STATUS current
	DESCRIPTION "Bridge deletion"
	::= { traps 74 }

viptelaBridgeMaxMacReached NOTIFICATION-TYPE
	OBJECTS {
		eventTime,
		netconfNotificationSeverity,
		viptelaBridgeId,
		viptelaNumMacs
	}
	STATUS current
	DESCRIPTION "Bridge maximum mac was reached"
	::= { traps 75 }

viptelaSecurityControlVedgeListRequest NOTIFICATION-TYPE
	OBJECTS {
		eventTime,
		netconfNotificationSeverity,
		viptelaSecurityPeerType,
		viptelaSecurityPeerSystemIp,
        viptelaSecurityUuid
	}
	STATUS current
	DESCRIPTION "Control vedge list request"
	::= { traps 76 }

viptelaPolicySlaViolation NOTIFICATION-TYPE
    OBJECTS {
        eventTime,
        netconfNotificationSeverity,
        viptelaPolicyVpnId,
        viptelaPolicyApplication,
        viptelaPolicySourceIp,
        viptelaPolicySourcePort,
        viptelaPolicyDestinationIp,
        viptelaPolicyDestinationPort,
        viptelaPolicyProtocol,
        viptelaPolicyDscp,
        viptelaPolicySlaInformation,
        viptelaPolicySlaStatus
    }
    STATUS current
    DESCRIPTION "SLA violation"
    ::= { traps 77 }

viptelaPolicySlaViolationPktDrop NOTIFICATION-TYPE
    OBJECTS {
        eventTime,
        netconfNotificationSeverity,
        viptelaPolicyVpnId,
        viptelaPolicyApplication,
        viptelaPolicySourceIp,
        viptelaPolicySourcePort,
        viptelaPolicyDestinationIp,
        viptelaPolicyDestinationPort,
        viptelaPolicyProtocol,
        viptelaPolicyDscp,
        viptelaPolicySlaInformation,
        viptelaPolicySlaStatus
    }
    STATUS current
    DESCRIPTION "SLA violation packet drop"
    ::= { traps 78 }

viptelaVpnInterfacePcsFaultDetected NOTIFICATION-TYPE
	OBJECTS {
		eventTime,
		netconfNotificationSeverity,
		viptelaVpnVpnId,
		viptelaVpnIfName,
		viptelaVpnNewState
	}
	STATUS current
	DESCRIPTION "Interface pcs fault was detected"
	::= { traps 79 }

viptelaSystemAppDpiFlowsOutOfMemory NOTIFICATION-TYPE
	OBJECTS {
		eventTime,
		netconfNotificationSeverity,
		viptelaSystemDpiOutOfMemoryState
	}
	STATUS current
	DESCRIPTION "App dpi flows out of memory"
	::= { traps 80 }

viptelaSecurityGreStateUpdate NOTIFICATION-TYPE
	OBJECTS {
		eventTime,
		netconfNotificationSeverity,
		viptelaSecurityGreOldOperState,
		viptelaSecurityGreNewOperState,
		viptelaSecurityGreIfName,
		viptelaSecurityGreVpnId,
		viptelaSecurityGreTunnelSource,
		viptelaSecurityGreTunnelDestination,
		viptelaSecurityGreGreIp
	}
	STATUS current
	DESCRIPTION "Gre state was updated"
	::= { traps 81 }

viptelaVpnInterfaceBw NOTIFICATION-TYPE
	OBJECTS {
		eventTime,
		netconfNotificationSeverity,
		viptelaVpnVpnId,
		viptelaVpnIfName,
		viptelaVpnIfCfgBwKbps,
		viptelaVpnTrafficDirection,
		viptelaVpnDuration
	}
	STATUS current
	DESCRIPTION "Interface bw"
	::= { traps 82 }


viptelaHardwareSfpSupportState NOTIFICATION-TYPE
	OBJECTS {
		eventTime,
		netconfNotificationSeverity,
		viptelaHardwareSfpName,
		viptelaHardwareNewState
	}
	STATUS current
	DESCRIPTION "Sfp support state"
	::= { traps 83 }

viptelaPolicyDataPolicyAssociationStatus NOTIFICATION-TYPE
    OBJECTS {
        eventTime,
        netconfNotificationSeverity,
        viptelaPolicyVpnListName,
        viptelaPolicyName,
        viptelaPolicyStatus
    }
    STATUS current
    DESCRIPTION "Status of data policy association"
    ::= { traps 84 }

viptelaPolicyAccessListAssociationStatus NOTIFICATION-TYPE
    OBJECTS {
        eventTime,
        netconfNotificationSeverity,
        viptelaPolicyAccessListName,
        viptelaPolicyStatus
    }
    STATUS current
    DESCRIPTION "Status of access list association"
    ::= { traps 85 }

viptelaSecurityVmanageConnectionPreferenceChanged NOTIFICATION-TYPE
    OBJECTS {
        eventTime,
        netconfNotificationSeverity,
        viptelaSecurityColor,
        viptelaSecurityVmanageConnectionPreference
    }
    STATUS current
    DESCRIPTION "Vmanage connection preference has changed"
    ::= { traps 86 }

viptelaVpnCloudExpressMaxLocalExitExceeded NOTIFICATION-TYPE
    OBJECTS {
        eventTime,
        netconfNotificationSeverity
    }
    STATUS current
    DESCRIPTION "Maximum local exit of cloud express was exceeded"
    ::= { traps 87 }

viptelaVpnCloudExpressApplicationChange NOTIFICATION-TYPE
    OBJECTS {
        eventTime,
        netconfNotificationSeverity,
        viptelaVpnVpnId,
        viptelaCloudExpressApplication,
        viptelaCloudExpressExitType,
        viptelaGatewayIp,
        viptelaVpnInterface,
        viptelaAppLatency,
        viptelaAppLoss,
        viptelaExitLocalColor,
        viptelaExitRemoteColor
    }
    STATUS current
    DESCRIPTION "Cloud express application has changed"
    ::= { traps 88 }

viptelaVpnCloudExpressScoreChange NOTIFICATION-TYPE
    OBJECTS {
        eventTime,
        netconfNotificationSeverity,
        viptelaVpnVpnId,
        viptelaCloudExpressApplication,
        viptelaCloudExpressExitType,
        viptelaGatewayIp,
        viptelaVpnInterface,
        viptelaAppLatency,
        viptelaAppLoss,
        viptelaExitLocalColor,
        viptelaExitRemoteColor
    }
    STATUS current
    DESCRIPTION "Cloud express score has changed"
    ::= { traps 89 }

viptelaWwanSimStateChange NOTIFICATION-TYPE
	OBJECTS {
		eventTime,
		netconfNotificationSeverity,
		viptelaWwanSimSlot,
		viptelaWwanSimState
	}
	STATUS current
	DESCRIPTION "Sim state has changed"
	::= { traps 90 }

viptelaSystemAppDpiFlowsWriteFailedVedge NOTIFICATION-TYPE                                                                                                                             
    OBJECTS {                                                                                                                                                        
        eventTime,                                                                                                                                               
        netconfNotificationSeverity                                                                                                                              
    }                                                                                                                                                                
    STATUS current                                                                                                                                                   
    DESCRIPTION "App dpi flows write failed on vedge"
    ::= { traps 91 }

viptelaVpnInterfaceAdminStateChange NOTIFICATION-TYPE
	OBJECTS {
		eventTime,
		netconfNotificationSeverity,
		viptelaVpnVpnId,
		viptelaVpnIfName,
		viptelaVpnNewAdminState
	}
	STATUS current
	DESCRIPTION "Interface admin state has changed"
	::= { traps 92 }

viptelaWwanDomainStateChange NOTIFICATION-TYPE
	OBJECTS {
		eventTime,
		netconfNotificationSeverity,
		viptelaWwanIfname,
		viptelaWwanDomainState
	}
	STATUS current
	DESCRIPTION "Domain state has changed"
	::= { traps 93 }

viptelaWwanRegStateChange NOTIFICATION-TYPE
	OBJECTS {
		eventTime,
		netconfNotificationSeverity,
		viptelaWwanIfname,
		viptelaWwanRegState
	}
	STATUS current
	DESCRIPTION "Registration state has changed"
	::= { traps 94 }

viptelaWwanBearerChange NOTIFICATION-TYPE
	OBJECTS {
		eventTime,
		netconfNotificationSeverity,
		viptelaWwanIfname,
		viptelaWwanBearer
	}
	STATUS current
	DESCRIPTION "Bearer has changed"
	::= { traps 95 }

viptelaSystemProcessDown NOTIFICATION-TYPE
	OBJECTS {
		eventTime,
		netconfNotificationSeverity,
		viptelaSystemProcessName,
		viptelaSystemProcessId,
		viptelaSystemReason
	}
	STATUS current
	DESCRIPTION "Process is down"
	::= { traps 96 }

viptelaActionsSystemRebootAborted NOTIFICATION-TYPE
	OBJECTS {
		eventTime,
		netconfNotificationSeverity,
		viptelaActionsReason
	}
	STATUS current
	DESCRIPTION "System reboot was aborted"
	::= { traps 97 }

viptelaSecurityVbondRejectVedgeConnection NOTIFICATION-TYPE
    OBJECTS {
        eventTime,
        netconfNotificationSeverity,
        viptelaSecurityUuid,
        viptelaSecurityOrganizationName,
        viptelaSecuritySpOrganizationName,
		viptelaSecurityReason
    }
    STATUS current
    DESCRIPTION "Vbond rejected vedge connection"
    ::= { traps 98 }

viptelaSecurityDeviceTemplateMissing NOTIFICATION-TYPE
    OBJECTS {
        eventTime,
        netconfNotificationSeverity,
        viptelaSecurityUuid,
        viptelaSecurityPeerType
    }
    STATUS current
    DESCRIPTION "Device template is missing"
    ::= { traps 99 }

viptelaSecurityDeviceTemplateAttachedDuringZtp NOTIFICATION-TYPE
    OBJECTS {
        eventTime,
        netconfNotificationSeverity,
        viptelaSecurityUuid,
        viptelaSecurityPeerType
    }
    STATUS current
    DESCRIPTION "Device template was attached during ztp"
    ::= { traps 100 }

viptelaPolicyZbfFlowCreation NOTIFICATION-TYPE
    OBJECTS {
        eventTime,
        netconfNotificationSeverity,
        viptelaPolicySvcVpnId,
        viptelaPolicyZonePair,
        viptelaPolicySourceVpn,
        viptelaPolicySourceIp,
        viptelaPolicySourcePort,
        viptelaPolicyDestinationVpn,
        viptelaPolicyDestinationIp,
        viptelaPolicyDestinationPort,
        viptelaPolicyProtocol,
        viptelaPolicyState
    }
    STATUS current
    DESCRIPTION "Zbf flow creation"
    ::= { traps 101 }

viptelaPolicyZbfFlowDeletion NOTIFICATION-TYPE
    OBJECTS {
        eventTime,
        netconfNotificationSeverity,
        viptelaPolicySvcVpnId,
        viptelaPolicyZonePair,
        viptelaPolicySourceVpn,
        viptelaPolicySourceIp,
        viptelaPolicySourcePort,
        viptelaPolicyDestinationVpn,
        viptelaPolicyDestinationIp,
        viptelaPolicyDestinationPort,
        viptelaPolicyProtocol,
        viptelaPolicyState
    }
    STATUS current
    DESCRIPTION "Zbf flow deletion"
    ::= { traps 102 }

viptelaPolicyZbfFlowTableFull NOTIFICATION-TYPE
    OBJECTS {
        eventTime,
        netconfNotificationSeverity,
        viptelaPolicyCurrFlows,
        viptelaPolicyHthreshFlows,
        viptelaPolicyMaxFlows
    }
    STATUS current
    DESCRIPTION "Zbf flow table full"
    ::= { traps 103 }

viptelaPolicyZbfClearFlowTableFull NOTIFICATION-TYPE
    OBJECTS {
        eventTime,
        netconfNotificationSeverity,
        viptelaPolicyCurrFlows,
        viptelaPolicyLthreshFlows,
        viptelaPolicyMaxFlows
    }
    STATUS current
    DESCRIPTION "Zbf clear flow table full"
    ::= { traps 104 }

viptelaPolicyZbfPktLog NOTIFICATION-TYPE
    OBJECTS {
        eventTime,
        netconfNotificationSeverity,
        viptelaPolicySvcVpnId,
        viptelaPolicyZonePair,
        viptelaPolicySourceVpn,
        viptelaPolicySourceIp,
        viptelaPolicySourcePort,
        viptelaPolicyDestinationVpn,
        viptelaPolicyDestinationIp,
        viptelaPolicyDestinationPort,
        viptelaPolicyProtocol,
        viptelaPolicyAction
    }
    STATUS current
    DESCRIPTION "Zbf packet log"
    ::= { traps 105 }

viptelaPolicyZbfHalfOpenHit NOTIFICATION-TYPE
    OBJECTS {
        eventTime,
        netconfNotificationSeverity,
        viptelaPolicyCurrHalfOpenFlows,
        viptelaPolicyHthreshHalfOpenFlows,
        viptelaPolicyMaxHalfOpenFlows
    }
    STATUS current
    DESCRIPTION "Zbf half open hit"
    ::= { traps 106 }

viptelaPolicyZbfClearHalfOpenHit NOTIFICATION-TYPE
    OBJECTS {
        eventTime,
        netconfNotificationSeverity,
        viptelaPolicyCurrHalfOpenFlows,
        viptelaPolicyLthreshHalfOpenFlows,
        viptelaPolicyMaxHalfOpenFlows
    }
    STATUS current
    DESCRIPTION "Zbf clear half open hit"
    ::= { traps 107 }

viptelaPolicySlaConfig NOTIFICATION-TYPE
    OBJECTS {
        eventTime,
        netconfNotificationSeverity,
        viptelaPolicySlaName,
        viptelaPolicySlaOperation,
        viptelaPolicySlaLoss,
        viptelaPolicySlaLatency,
        viptelaPolicySlaJitter,
        viptelaPolicySlaAppProbeClass
    }
    STATUS current
    DESCRIPTION "Sla configuration"
    ::= { traps 108 }

viptelaVpnLastResortStateChange NOTIFICATION-TYPE
        OBJECTS {
                eventTime,
                netconfNotificationSeverity,
                viptelaVpnVpnId,
                viptelaVpnIfName,
                viptelaVpnNewState
        }
        STATUS current
        DESCRIPTION "Last resort state has changed"
        ::= { traps 109 }

viptelaPolicyDevicePolicyAssociationStatus NOTIFICATION-TYPE
    OBJECTS {
        eventTime,
        netconfNotificationSeverity,
        viptelaPolicyDevicePolicyName,
        viptelaPolicyStatus
    }
    STATUS current
    DESCRIPTION "Status of device policy association"
    ::= { traps 110 }

viptelaWwanQosStateChange NOTIFICATION-TYPE
	OBJECTS {
		eventTime,
		netconfNotificationSeverity,
		viptelaWwanIfname,
		viptelaWwanQosState
	}
	STATUS current
	DESCRIPTION "Qos state has changed"
	::= { traps 111 }
    
viptelaCdbUnlocked NOTIFICATION-TYPE
    OBJECTS {
        eventTime,
        netconfNotificationSeverity,
        viptelaSecurityPersonality
    }
    STATUS current
    DESCRIPTION "Cdb was unlocked"
    ::= { traps 112 }

viptelaSecuritySecurityUnclaimedVedgeEntryAdded NOTIFICATION-TYPE
    OBJECTS {
        eventTime,
        netconfNotificationSeverity,
        viptelaSecurityUuid,
        viptelaSecuritySerial,
        viptelaSecuritySubjectSerialNumber,
        viptelaSecurityOrganizationName
    }
    STATUS current
    DESCRIPTION "Security unclaimed vedge entry was added"
    ::= { traps 113 }

viptelaSystemCpuUsage NOTIFICATION-TYPE
    OBJECTS {
        eventTime,
        netconfNotificationSeverity,
        viptelaSystemWarning,
        viptelaSystemCpuUserPercentage,
        viptelaSystemCpuSystemPercentage,
        viptelaSystemCpuIdlePercentage
    }
    STATUS current
    DESCRIPTION "Cpu usage"
    ::= { traps 114 }

viptelaSecuritySecurityCertificateExpiring NOTIFICATION-TYPE
    OBJECTS {
        eventTime,
        netconfNotificationSeverity,
        viptelaSecurityCertificateType,
        viptelaSecurityCertificateSerialNumber,
        viptelaSecurityIssuer,
        viptelaSecurityDaysToExpiry
    }
    STATUS current
    DESCRIPTION "Security certificate is expiring"
    ::= { traps 115 }

viptelaPolicyAppListAppAliasesNotify NOTIFICATION-TYPE
    OBJECTS {
        eventTime,
        netconfNotificationSeverity,
        viptelaPolicyAppListName,
        viptelaPolicyAppAlias
    }
    STATUS current
    DESCRIPTION "App list app aliases notify"
    ::= { traps 116 }

viptelaPolicyAppListUnsupportedAppNotify NOTIFICATION-TYPE
    OBJECTS {
        eventTime,
        netconfNotificationSeverity,
        viptelaPolicyAppListName,
        viptelaPolicyUnsupportedApp
    }
    STATUS current
    DESCRIPTION "App list unsupported app notify"
    ::= { traps 117 }


viptelaSecuritySecurityRootCaCrlInstalled NOTIFICATION-TYPE
	OBJECTS {
		eventTime,
		netconfNotificationSeverity
	}
	STATUS current
	DESCRIPTION "Security root ca crl was installed"
	::= { traps 118 }

viptelaSecuritySecurityRootCaCrlUninstalled NOTIFICATION-TYPE
	OBJECTS {
		eventTime,
		netconfNotificationSeverity
	}
	STATUS current
	DESCRIPTION "Security root ca crl was uninstalled"
	::= { traps 119 }

viptelaHardwareSfpDiagAlarmState NOTIFICATION-TYPE
	OBJECTS {
		eventTime,
		netconfNotificationSeverity,
		viptelaHardwareSfpName,
		viptelaHardwareSfpDiagName,
		viptelaHardwareSfpDiagState,
		viptelaHardwareSfpDiagStateDescription
	}
	STATUS current
	DESCRIPTION "Sfp diagnostic alarm state change"
	::= { traps 120 }

viptelaSecurityBaseConfigDownloadError NOTIFICATION-TYPE
    OBJECTS {
        eventTime,
        netconfNotificationSeverity,
        viptelaSecurityUuid,
        viptelaSecurityPeerType,
        viptelaSecurityReason
    }
    STATUS current
    DESCRIPTION "Unable to send rest api request"
    ::= { traps 121 }

viptelaAaaUserLocked NOTIFICATION-TYPE
    OBJECTS {
        eventTime,
        netconfNotificationSeverity,
        viptelaSystemUserName,
        viptelaSystemRemoteHost
    }
    STATUS current
    DESCRIPTION "AAA user is locked"
    ::= { traps 122 }

viptelaAaaUserLoginAnomaly NOTIFICATION-TYPE
    OBJECTS {
        eventTime,
        netconfNotificationSeverity,
        viptelaSystemUserName,
        viptelaSystemRemoteHost
    }
    STATUS current
    DESCRIPTION "AAA user anomalous login"
    ::= { traps 123 }

END
