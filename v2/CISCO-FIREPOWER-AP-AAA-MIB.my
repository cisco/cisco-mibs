-- *********************************************************************
-- CISCO-FIREPOWER-AP-AAA-MIB.my
-- 
-- MIB representation of the Cisco Firepower
-- AAA management information model package
-- 
-- Created January 2023 by Charles Bullis
-- 
-- Copyright (c) 2005-2023 Cisco Systems, Inc. All rights reserved.
-- 
-- *********************************************************************

CISCO-FIREPOWER-AP-AAA-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApAaaAccess,
    CfprApAaaAccountStatus,
    CfprApAaaAuthRealmFsmCurrentFsm,
    CfprApAaaAuthRealmFsmStageName,
    CfprApAaaCimcSessionType,
    CfprApAaaClear,
    CfprApAaaConfigState,
    CfprApAaaDomainAuthRealm,
    CfprApAaaEpAccess,
    CfprApAaaEpFsmCurrentFsm,
    CfprApAaaEpFsmStageName,
    CfprApAaaEpFsmTaskItem,
    CfprApAaaExtMgmtAccess,
    CfprApAaaIpmiOverLan,
    CfprApAaaLdapEpFsmCurrentFsm,
    CfprApAaaLdapEpFsmStageName,
    CfprApAaaLdapGroupRuleAuthorization,
    CfprApAaaLdapGroupRuleTraversal,
    CfprApAaaLdapSsl,
    CfprApAaaLdapVendor,
    CfprApAaaNoRolePolicy,
    CfprApAaaPwdPolicy,
    CfprApAaaRadiusEpFsmCurrentFsm,
    CfprApAaaRadiusEpFsmStageName,
    CfprApAaaRadiusService,
    CfprApAaaRealm,
    CfprApAaaRealmFsmCurrentFsm,
    CfprApAaaRealmFsmStageName,
    CfprApAaaRealmFsmTaskItem,
    CfprApAaaSession,
    CfprApAaaSessionState,
    CfprApAaaSshStr,
    CfprApAaaTacacsPlusEpFsmCurrentFsm,
    CfprApAaaTacacsPlusEpFsmStageName,
    CfprApAaaUserEpFsmCurrentFsm,
    CfprApAaaUserEpFsmStageName,
    CfprApAaaUserEpFsmTaskItem,
    CfprApAaaUserInterface,
    CfprApConditionActionIndicator,
    CfprApConditionCause,
    CfprApConditionCode,
    CfprApConditionRemoteInvRslt,
    CfprApConditionSeverity,
    CfprApFsmCompletion,
    CfprApFsmFlags,
    CfprApFsmFsmStageStatus,
    CfprApNetworkSwitchId,
    CfprApPolicyPolicyOwner
        FROM CISCO-FIREPOWER-AP-TC-MIB;

cfprApAaaObjects MODULE-IDENTITY
    LAST-UPDATED    "202301250000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        AAA management information model package"
    ::= { ciscoFirepowerApMIBObjects 2 }

cfprApAaaAuthRealmTable OBJECT-TYPE
    SYNTAX           SEQUENCE OF CfprApAaaAuthRealmEntry
    MAX-ACCESS       not-accessible
    STATUS           current
    DESCRIPTION
        "Cisco Firepower aaa:AuthRealm managed object table"
    ::= { cfprApAaaObjects 1 }

cfprApAaaAuthRealmEntry OBJECT-TYPE
    SYNTAX           CfprApAaaAuthRealmEntry
    MAX-ACCESS       not-accessible
    STATUS           current
    DESCRIPTION
        "Entry for the cfprApAaaAuthRealmTable table."
    INDEX { cfprApAaaAuthRealmInstanceId }
    ::= { cfprApAaaAuthRealmTable 1 }

CfprApAaaAuthRealmEntry ::= SEQUENCE {
    cfprApAaaAuthRealmInstanceId                                     CfprApManagedObjectId,
    cfprApAaaAuthRealmDn                                             CfprApManagedObjectDn,
    cfprApAaaAuthRealmRn                                             SnmpAdminString,
    cfprApAaaAuthRealmConLogin                                       CfprApAaaRealm,
    cfprApAaaAuthRealmDefLogin                                       CfprApAaaRealm,
    cfprApAaaAuthRealmDefRolePolicy                                  CfprApAaaNoRolePolicy,
    cfprApAaaAuthRealmDescr                                          SnmpAdminString,
    cfprApAaaAuthRealmFsmDescr                                       SnmpAdminString,
    cfprApAaaAuthRealmFsmPrev                                        SnmpAdminString,
    cfprApAaaAuthRealmFsmProgr                                       Gauge32,
    cfprApAaaAuthRealmFsmRmtInvErrCode                               Gauge32,
    cfprApAaaAuthRealmFsmRmtInvErrDescr                              SnmpAdminString,
    cfprApAaaAuthRealmFsmRmtInvRslt                                  CfprApConditionRemoteInvRslt,
    cfprApAaaAuthRealmFsmStageDescr                                  SnmpAdminString,
    cfprApAaaAuthRealmFsmStamp                                       DateAndTime,
    cfprApAaaAuthRealmFsmStatus                                      SnmpAdminString,
    cfprApAaaAuthRealmFsmTry                                         Gauge32,
    cfprApAaaAuthRealmIntId                                          SnmpAdminString,
    cfprApAaaAuthRealmName                                           SnmpAdminString,
    cfprApAaaAuthRealmPolicyLevel                                    Gauge32,
    cfprApAaaAuthRealmPolicyOwner                                    CfprApPolicyPolicyOwner
}

cfprApAaaAuthRealmInstanceId OBJECT-TYPE
    SYNTAX       CfprApManagedObjectId
    MAX-ACCESS   not-accessible
    STATUS       current
    DESCRIPTION
        "Instance identifier of the managed object."
    ::= { cfprApAaaAuthRealmEntry 1 }

cfprApAaaAuthRealmDn OBJECT-TYPE
    SYNTAX       CfprApManagedObjectDn
    MAX-ACCESS   read-only
    STATUS       current
    DESCRIPTION
        "Cisco Firepower aaa:AuthRealm:dn managed object property"
    ::= { cfprApAaaAuthRealmEntry 2 }

cfprApAaaAuthRealmRn OBJECT-TYPE
    SYNTAX       SnmpAdminString
    MAX-ACCESS   read-only
    STATUS       current
    DESCRIPTION
        "Cisco Firepower aaa:AuthRealm:rn managed object property"
    ::= { cfprApAaaAuthRealmEntry 3 }

cfprApAaaAuthRealmConLogin OBJECT-TYPE
    SYNTAX       CfprApAaaRealm
    MAX-ACCESS   read-only
    STATUS       current
    DESCRIPTION
        "Cisco Firepower aaa:AuthRealm:conLogin managed object property"
    ::= { cfprApAaaAuthRealmEntry 4 }

cfprApAaaAuthRealmDefLogin OBJECT-TYPE
    SYNTAX       CfprApAaaRealm
    MAX-ACCESS   read-only
    STATUS       current
    DESCRIPTION
        "Cisco Firepower aaa:AuthRealm:defLogin managed object property"
    ::= { cfprApAaaAuthRealmEntry 5 }

cfprApAaaAuthRealmDefRolePolicy OBJECT-TYPE
    SYNTAX       CfprApAaaNoRolePolicy
    MAX-ACCESS   read-only
    STATUS       current
    DESCRIPTION
        "Cisco Firepower aaa:AuthRealm:defRolePolicy managed
        object property"
    ::= { cfprApAaaAuthRealmEntry 6 }

cfprApAaaAuthRealmDescr OBJECT-TYPE
    SYNTAX       SnmpAdminString
    MAX-ACCESS   read-only
    STATUS       current
    DESCRIPTION
        "Cisco Firepower aaa:AuthRealm:descr managed object property"
    ::= { cfprApAaaAuthRealmEntry 7 }

cfprApAaaAuthRealmFsmDescr OBJECT-TYPE
    SYNTAX       SnmpAdminString
    MAX-ACCESS   read-only
    STATUS       current
    DESCRIPTION
        "Cisco Firepower aaa:AuthRealm:fsmDescr managed object property"
    ::= { cfprApAaaAuthRealmEntry 8 }

cfprApAaaAuthRealmFsmPrev OBJECT-TYPE
    SYNTAX       SnmpAdminString
    MAX-ACCESS   read-only
    STATUS       current
    DESCRIPTION
        "Cisco Firepower aaa:AuthRealm:fsmPrev managed object property"
    ::= { cfprApAaaAuthRealmEntry 9 }

cfprApAaaAuthRealmFsmProgr OBJECT-TYPE
    SYNTAX       Gauge32
    MAX-ACCESS   read-only
    STATUS       current
    DESCRIPTION
        "Cisco Firepower aaa:AuthRealm:fsmProgr managed object property"
    ::= { cfprApAaaAuthRealmEntry 10 }

cfprApAaaAuthRealmFsmRmtInvErrCode OBJECT-TYPE
    SYNTAX       Gauge32
    MAX-ACCESS   read-only
    STATUS       current
    DESCRIPTION
        "Cisco Firepower aaa:AuthRealm:fsmRmtInvErrCode
        managed object property"
    ::= { cfprApAaaAuthRealmEntry 11 }

cfprApAaaAuthRealmFsmRmtInvErrDescr OBJECT-TYPE
    SYNTAX       SnmpAdminString
    MAX-ACCESS   read-only
    STATUS       current
    DESCRIPTION
        "Cisco Firepower aaa:AuthRealm:fsmRmtInvErrDescr
        managed object property"
    ::= { cfprApAaaAuthRealmEntry 12 }

cfprApAaaAuthRealmFsmRmtInvRslt OBJECT-TYPE
    SYNTAX       CfprApConditionRemoteInvRslt
    MAX-ACCESS   read-only
    STATUS       current
    DESCRIPTION
        "Cisco Firepower aaa:AuthRealm:fsmRmtInvRslt managed
        object property"
    ::= { cfprApAaaAuthRealmEntry 13 }

cfprApAaaAuthRealmFsmStageDescr OBJECT-TYPE
    SYNTAX       SnmpAdminString
    MAX-ACCESS   read-only
    STATUS       current
    DESCRIPTION
        "Cisco Firepower aaa:AuthRealm:fsmStageDescr managed
        object property"
    ::= { cfprApAaaAuthRealmEntry 14 }

cfprApAaaAuthRealmFsmStamp OBJECT-TYPE
    SYNTAX       DateAndTime
    MAX-ACCESS   read-only
    STATUS       current
    DESCRIPTION
        "Cisco Firepower aaa:AuthRealm:fsmStamp managed object property"
    ::= { cfprApAaaAuthRealmEntry 15 }

cfprApAaaAuthRealmFsmStatus OBJECT-TYPE
    SYNTAX       SnmpAdminString
    MAX-ACCESS   read-only
    STATUS       current
    DESCRIPTION
        "Cisco Firepower aaa:AuthRealm:fsmStatus managed object property"
    ::= { cfprApAaaAuthRealmEntry 16 }

cfprApAaaAuthRealmFsmTry OBJECT-TYPE
    SYNTAX       Gauge32
    MAX-ACCESS   read-only
    STATUS       current
    DESCRIPTION
        "Cisco Firepower aaa:AuthRealm:fsmTry managed object property"
    ::= { cfprApAaaAuthRealmEntry 17 }

cfprApAaaAuthRealmIntId OBJECT-TYPE
    SYNTAX       SnmpAdminString
    MAX-ACCESS   read-only
    STATUS       current
    DESCRIPTION
        "Cisco Firepower aaa:AuthRealm:intId managed object property"
    ::= { cfprApAaaAuthRealmEntry 18 }

cfprApAaaAuthRealmName OBJECT-TYPE
    SYNTAX       SnmpAdminString
    MAX-ACCESS   read-only
    STATUS       current
    DESCRIPTION
        "Cisco Firepower aaa:AuthRealm:name managed object property"
    ::= { cfprApAaaAuthRealmEntry 19 }

cfprApAaaAuthRealmPolicyLevel OBJECT-TYPE
    SYNTAX       Gauge32
    MAX-ACCESS   read-only
    STATUS       current
    DESCRIPTION
        "Cisco Firepower aaa:AuthRealm:policyLevel managed
        object property"
    ::= { cfprApAaaAuthRealmEntry 20 }

cfprApAaaAuthRealmPolicyOwner OBJECT-TYPE
    SYNTAX       CfprApPolicyPolicyOwner
    MAX-ACCESS   read-only
    STATUS       current
    DESCRIPTION
        "Cisco Firepower aaa:AuthRealm:policyOwner managed
        object property"
    ::= { cfprApAaaAuthRealmEntry 21 }

cfprApAaaAuthRealmFsmTable OBJECT-TYPE
    SYNTAX           SEQUENCE OF CfprApAaaAuthRealmFsmEntry
    MAX-ACCESS       not-accessible
    STATUS           current
    DESCRIPTION
        "Cisco Firepower aaa:AuthRealmFsm managed object table"
    ::= { cfprApAaaObjects 2 }

cfprApAaaAuthRealmFsmEntry OBJECT-TYPE
    SYNTAX           CfprApAaaAuthRealmFsmEntry
    MAX-ACCESS       not-accessible
    STATUS           current
    DESCRIPTION
        "Entry for the cfprApAaaAuthRealmFsmTable table."
    INDEX { cfprApAaaAuthRealmFsmInstanceId }
    ::= { cfprApAaaAuthRealmFsmTable 1 }

CfprApAaaAuthRealmFsmEntry ::= SEQUENCE {
    cfprApAaaAuthRealmFsmInstanceId                                  CfprApManagedObjectId,
    cfprApAaaAuthRealmFsmDn                                          CfprApManagedObjectDn,
    cfprApAaaAuthRealmFsmRn                                          SnmpAdminString,
    cfprApAaaAuthRealmFsmCompletionTime                              DateAndTime,
    cfprApAaaAuthRealmFsmCurrentFsm                                  CfprApAaaAuthRealmFsmCurrentFsm,
    cfprApAaaAuthRealmFsmDescrData                                   SnmpAdminString,
    cfprApAaaAuthRealmFsmFsmStatus                                   CfprApFsmFsmStageStatus,
    cfprApAaaAuthRealmFsmProgress                                    Gauge32,
    cfprApAaaAuthRealmFsmRmtErrCode                                  Gauge32,
    cfprApAaaAuthRealmFsmRmtErrDescr                                 SnmpAdminString,
    cfprApAaaAuthRealmFsmRmtRslt                                     CfprApConditionRemoteInvRslt
}

cfprApAaaAuthRealmFsmInstanceId OBJECT-TYPE
    SYNTAX       CfprApManagedObjectId
    MAX-ACCESS   not-accessible
    STATUS       current
    DESCRIPTION
        "Instance identifier of the managed object."
    ::= { cfprApAaaAuthRealmFsmEntry 1 }

cfprApAaaAuthRealmFsmDn OBJECT-TYPE
    SYNTAX       CfprApManagedObjectDn
    MAX-ACCESS   read-only
    STATUS       current
    DESCRIPTION
        "Cisco Firepower aaa:AuthRealmFsm:dn managed object property"
    ::= { cfprApAaaAuthRealmFsmEntry 2 }

cfprApAaaAuthRealmFsmRn OBJECT-TYPE
    SYNTAX       SnmpAdminString
    MAX-ACCESS   read-only
    STATUS       current
    DESCRIPTION
        "Cisco Firepower aaa:AuthRealmFsm:rn managed object property"
    ::= { cfprApAaaAuthRealmFsmEntry 3 }

cfprApAaaAuthRealmFsmCompletionTime OBJECT-TYPE
    SYNTAX       DateAndTime
    MAX-ACCESS   read-only
    STATUS       current
    DESCRIPTION
        "Cisco Firepower aaa:AuthRealmFsm:completionTime
        managed object property"
    ::= { cfprApAaaAuthRealmFsmEntry 4 }

cfprApAaaAuthRealmFsmCurrentFsm OBJECT-TYPE
    SYNTAX       CfprApAaaAuthRealmFsmCurrentFsm
    MAX-ACCESS   read-only
    STATUS       current
    DESCRIPTION
        "Cisco Firepower aaa:AuthRealmFsm:currentFsm managed
        object property"
    ::= { cfprApAaaAuthRealmFsmEntry 5 }

cfprApAaaAuthRealmFsmDescrData OBJECT-TYPE
    SYNTAX       SnmpAdminString
    MAX-ACCESS   read-only
    STATUS       current
    DESCRIPTION
        "Cisco Firepower aaa:AuthRealmFsm:descr managed object property"
    ::= { cfprApAaaAuthRealmFsmEntry 6 }

cfprApAaaAuthRealmFsmFsmStatus OBJECT-TYPE
    SYNTAX       CfprApFsmFsmStageStatus
    MAX-ACCESS   read-only
    STATUS       current
    DESCRIPTION
        "Cisco Firepower aaa:AuthRealmFsm:fsmStatus managed
        object property"
    ::= { cfprApAaaAuthRealmFsmEntry 7 }

cfprApAaaAuthRealmFsmProgress OBJECT-TYPE
    SYNTAX       Gauge32
    MAX-ACCESS   read-only
    STATUS       current
    DESCRIPTION
        "Cisco Firepower aaa:AuthRealmFsm:progress managed
        object property"
    ::= { cfprApAaaAuthRealmFsmEntry 8 }

cfprApAaaAuthRealmFsmRmtErrCode OBJECT-TYPE
    SYNTAX       Gauge32
    MAX-ACCESS   read-only
    STATUS       current
    DESCRIPTION
        "Cisco Firepower aaa:AuthRealmFsm:rmtErrCode managed
        object property"
    ::= { cfprApAaaAuthRealmFsmEntry 9 }

cfprApAaaAuthRealmFsmRmtErrDescr OBJECT-TYPE
    SYNTAX       SnmpAdminString
    MAX-ACCESS   read-only
    STATUS       current
    DESCRIPTION
        "Cisco Firepower aaa:AuthRealmFsm:rmtErrDescr managed
        object property"
    ::= { cfprApAaaAuthRealmFsmEntry 10 }

cfprApAaaAuthRealmFsmRmtRslt OBJECT-TYPE
    SYNTAX       CfprApConditionRemoteInvRslt
    MAX-ACCESS   read-only
    STATUS       current
    DESCRIPTION
        "Cisco Firepower aaa:AuthRealmFsm:rmtRslt managed object property"
    ::= { cfprApAaaAuthRealmFsmEntry 11 }

cfprApAaaAuthRealmFsmStageTable OBJECT-TYPE
    SYNTAX           SEQUENCE OF CfprApAaaAuthRealmFsmStageEntry
    MAX-ACCESS       not-accessible
    STATUS           current
    DESCRIPTION
        "Cisco Firepower aaa:AuthRealmFsmStage managed object table"
    ::= { cfprApAaaObjects 3 }

cfprApAaaAuthRealmFsmStageEntry OBJECT-TYPE
    SYNTAX           CfprApAaaAuthRealmFsmStageEntry
    MAX-ACCESS       not-accessible
    STATUS           current
    DESCRIPTION
        "Entry for the cfprApAaaAuthRealmFsmStageTable table."
    INDEX { cfprApAaaAuthRealmFsmStageInstanceId }
    ::= { cfprApAaaAuthRealmFsmStageTable 1 }

CfprApAaaAuthRealmFsmStageEntry ::= SEQUENCE {
    cfprApAaaAuthRealmFsmStageInstanceId                             CfprApManagedObjectId,
    cfprApAaaAuthRealmFsmStageDn                                     CfprApManagedObjectDn,
    cfprApAaaAuthRealmFsmStageRn                                     SnmpAdminString,
    cfprApAaaAuthRealmFsmStageDescrData                              SnmpAdminString,
    cfprApAaaAuthRealmFsmStageLastUpdateTime                         DateAndTime,
    cfprApAaaAuthRealmFsmStageName                                   CfprApAaaAuthRealmFsmStageName,
    cfprApAaaAuthRealmFsmStageOrder                                  Gauge32,
    cfprApAaaAuthRealmFsmStageRetry                                  Gauge32,
    cfprApAaaAuthRealmFsmStageStageStatus                            CfprApFsmFsmStageStatus
}

cfprApAaaAuthRealmFsmStageInstanceId OBJECT-TYPE
    SYNTAX       CfprApManagedObjectId
    MAX-ACCESS   not-accessible
    STATUS       current
    DESCRIPTION
        "Instance identifier of the managed object."
    ::= { cfprApAaaAuthRealmFsmStageEntry 1 }

cfprApAaaAuthRealmFsmStageDn OBJECT-TYPE
    SYNTAX       CfprApManagedObjectDn
    MAX-ACCESS   read-only
    STATUS       current
    DESCRIPTION
        "Cisco Firepower aaa:AuthRealmFsmStage:dn managed object property"
    ::= { cfprApAaaAuthRealmFsmStageEntry 2 }

cfprApAaaAuthRealmFsmStageRn OBJECT-TYPE
    SYNTAX       SnmpAdminString
    MAX-ACCESS   read-only
    STATUS       current
    DESCRIPTION
        "Cisco Firepower aaa:AuthRealmFsmStage:rn managed object property"
    ::= { cfprApAaaAuthRealmFsmStageEntry 3 }

cfprApAaaAuthRealmFsmStageDescrData OBJECT-TYPE
    SYNTAX       SnmpAdminString
    MAX-ACCESS   read-only
    STATUS       current
    DESCRIPTION
        "Cisco Firepower aaa:AuthRealmFsmStage:descr managed
        object property"
    ::= { cfprApAaaAuthRealmFsmStageEntry 4 }

cfprApAaaAuthRealmFsmStageLastUpdateTime OBJECT-TYPE
    SYNTAX       DateAndTime
    MAX-ACCESS   read-only
    STATUS       current
    DESCRIPTION
        "Cisco Firepower aaa:AuthRealmFsmStage:lastUpdateTime
        managed object property"
    ::= { cfprApAaaAuthRealmFsmStageEntry 5 }

cfprApAaaAuthRealmFsmStageName OBJECT-TYPE
    SYNTAX       CfprApAaaAuthRealmFsmStageName
    MAX-ACCESS   read-only
    STATUS       current
    DESCRIPTION
        "Cisco Firepower aaa:AuthRealmFsmStage:name managed
        object property"
    ::= { cfprApAaaAuthRealmFsmStageEntry 6 }

cfprApAaaAuthRealmFsmStageOrder OBJECT-TYPE
    SYNTAX       Gauge32
    MAX-ACCESS   read-only
    STATUS       current
    DESCRIPTION
        "Cisco Firepower aaa:AuthRealmFsmStage:order managed
        object property"
    ::= { cfprApAaaAuthRealmFsmStageEntry 7 }

cfprApAaaAuthRealmFsmStageRetry OBJECT-TYPE
    SYNTAX       Gauge32
    MAX-ACCESS   read-only
    STATUS       current
    DESCRIPTION
        "Cisco Firepower aaa:AuthRealmFsmStage:retry managed
        object property"
    ::= { cfprApAaaAuthRealmFsmStageEntry 8 }

cfprApAaaAuthRealmFsmStageStageStatus OBJECT-TYPE
    SYNTAX       CfprApFsmFsmStageStatus
    MAX-ACCESS   read-only
    STATUS       current
    DESCRIPTION
        "Cisco Firepower aaa:AuthRealmFsmStage:stageStatus
        managed object property"
    ::= { cfprApAaaAuthRealmFsmStageEntry 9 }

cfprApAaaCimcSessionTable OBJECT-TYPE
    SYNTAX           SEQUENCE OF CfprApAaaCimcSessionEntry
    MAX-ACCESS       not-accessible
    STATUS           current
    DESCRIPTION
        "Cisco Firepower aaa:CimcSession managed object table"
    ::= { cfprApAaaObjects 4 }

cfprApAaaCimcSessionEntry OBJECT-TYPE
    SYNTAX           CfprApAaaCimcSessionEntry
    MAX-ACCESS       not-accessible
    STATUS           current
    DESCRIPTION
        "Entry for the cfprApAaaCimcSessionTable table."
    INDEX { cfprApAaaCimcSessionInstanceId }
    ::= { cfprApAaaCimcSessionTable 1 }

CfprApAaaCimcSessionEntry ::= SEQUENCE {
    cfprApAaaCimcSessionInstanceId                                   CfprApManagedObjectId,
    cfprApAaaCimcSessionDn                                           CfprApManagedObjectDn,
    cfprApAaaCimcSessionRn                                           SnmpAdminString,
    cfprApAaaCimcSessionAdminState                                   CfprApAaaSessionState,
    cfprApAaaCimcSessionCimcAddr                                     SnmpAdminString,
    cfprApAaaCimcSessionId                                           SnmpAdminString,
    cfprApAaaCimcSessionIntDel                                       TruthValue,
    cfprApAaaCimcSessionIsDelete                                     CfprApAaaClear,
    cfprApAaaCimcSessionLastUpdatedTime                              DateAndTime,
    cfprApAaaCimcSessionLoginTime                                    DateAndTime,
    cfprApAaaCimcSessionLsDn                                         SnmpAdminString,
    cfprApAaaCimcSessionPid                                          Gauge32,
    cfprApAaaCimcSessionPnDn                                         SnmpAdminString,
    cfprApAaaCimcSessionPriv                                         SnmpAdminString,
    cfprApAaaCimcSessionSourceAddr                                   SnmpAdminString,
    cfprApAaaCimcSessionType                                         CfprApAaaCimcSessionType,
    cfprApAaaCimcSessionUser                                         SnmpAdminString
}

cfprApAaaCimcSessionInstanceId OBJECT-TYPE
    SYNTAX       CfprApManagedObjectId
    MAX-ACCESS   not-accessible
    STATUS       current
    DESCRIPTION
        "Instance identifier of the managed object."
    ::= { cfprApAaaCimcSessionEntry 1 }

cfprApAaaCimcSessionDn OBJECT-TYPE
    SYNTAX       CfprApManagedObjectDn
    MAX-ACCESS   read-only
    STATUS       current
    DESCRIPTION
        "Cisco Firepower aaa:CimcSession:dn managed object property"
    ::= { cfprApAaaCimcSessionEntry 2 }

cfprApAaaCimcSessionRn OBJECT-TYPE
    SYNTAX       SnmpAdminString
    MAX-ACCESS   read-only
    STATUS       current
    DESCRIPTION
        "Cisco Firepower aaa:CimcSession:rn managed object property"
    ::= { cfprApAaaCimcSessionEntry 3 }

cfprApAaaCimcSessionAdminState OBJECT-TYPE
    SYNTAX       CfprApAaaSessionState
    MAX-ACCESS   read-only
    STATUS       current
    DESCRIPTION
        "Cisco Firepower aaa:CimcSession:adminState managed
        object property"
    ::= { cfprApAaaCimcSessionEntry 4 }

cfprApAaaCimcSessionCimcAddr OBJECT-TYPE
    SYNTAX       SnmpAdminString
    MAX-ACCESS   read-only
    STATUS       current
    DESCRIPTION
        "Cisco Firepower aaa:CimcSession:cimcAddr managed object property"
    ::= { cfprApAaaCimcSessionEntry 5 }

cfprApAaaCimcSessionId OBJECT-TYPE
    SYNTAX       SnmpAdminString
    MAX-ACCESS   read-only
    STATUS       current
    DESCRIPTION
        "Cisco Firepower aaa:CimcSession:id managed object property"
    ::= { cfprApAaaCimcSessionEntry 6 }

cfprApAaaCimcSessionIntDel OBJECT-TYPE
    SYNTAX       TruthValue
    MAX-ACCESS   read-only
    STATUS       current
    DESCRIPTION
        "Cisco Firepower aaa:CimcSession:intDel managed object property"
    ::= { cfprApAaaCimcSessionEntry 7 }

cfprApAaaCimcSessionIsDelete OBJECT-TYPE
    SYNTAX       CfprApAaaClear
    MAX-ACCESS   read-only
    STATUS       current
    DESCRIPTION
        "Cisco Firepower aaa:CimcSession:isDelete managed object property"
    ::= { cfprApAaaCimcSessionEntry 8 }

cfprApAaaCimcSessionLastUpdatedTime OBJECT-TYPE
    SYNTAX       DateAndTime
    MAX-ACCESS   read-only
    STATUS       current
    DESCRIPTION
        "Cisco Firepower aaa:CimcSession:lastUpdatedTime
        managed object property"
    ::= { cfprApAaaCimcSessionEntry 9 }

cfprApAaaCimcSessionLoginTime OBJECT-TYPE
    SYNTAX       DateAndTime
    MAX-ACCESS   read-only
    STATUS       current
    DESCRIPTION
        "Cisco Firepower aaa:CimcSession:loginTime managed
        object property"
    ::= { cfprApAaaCimcSessionEntry 10 }

cfprApAaaCimcSessionLsDn OBJECT-TYPE
    SYNTAX       SnmpAdminString
    MAX-ACCESS   read-only
    STATUS       current
    DESCRIPTION
        "Cisco Firepower aaa:CimcSession:lsDn managed object property"
    ::= { cfprApAaaCimcSessionEntry 11 }

cfprApAaaCimcSessionPid OBJECT-TYPE
    SYNTAX       Gauge32
    MAX-ACCESS   read-only
    STATUS       current
    DESCRIPTION
        "Cisco Firepower aaa:CimcSession:pid managed object property"
    ::= { cfprApAaaCimcSessionEntry 12 }

cfprApAaaCimcSessionPnDn OBJECT-TYPE
    SYNTAX       SnmpAdminString
    MAX-ACCESS   read-only
    STATUS       current
    DESCRIPTION
        "Cisco Firepower aaa:CimcSession:pnDn managed object property"
    ::= { cfprApAaaCimcSessionEntry 13 }

cfprApAaaCimcSessionPriv OBJECT-TYPE
    SYNTAX       SnmpAdminString
    MAX-ACCESS   read-only
    STATUS       current
    DESCRIPTION
        "Cisco Firepower aaa:CimcSession:priv managed object property"
    ::= { cfprApAaaCimcSessionEntry 14 }

cfprApAaaCimcSessionSourceAddr OBJECT-TYPE
    SYNTAX       SnmpAdminString
    MAX-ACCESS   read-only
    STATUS       current
    DESCRIPTION
        "Cisco Firepower aaa:CimcSession:sourceAddr managed
        object property"
    ::= { cfprApAaaCimcSessionEntry 15 }

cfprApAaaCimcSessionType OBJECT-TYPE
    SYNTAX       CfprApAaaCimcSessionType
    MAX-ACCESS   read-only
    STATUS       current
    DESCRIPTION
        "Cisco Firepower aaa:CimcSession:type managed object property"
    ::= { cfprApAaaCimcSessionEntry 16 }

cfprApAaaCimcSessionUser OBJECT-TYPE
    SYNTAX       SnmpAdminString
    MAX-ACCESS   read-only
    STATUS       current
    DESCRIPTION
        "Cisco Firepower aaa:CimcSession:user managed object property"
    ::= { cfprApAaaCimcSessionEntry 17 }

cfprApAaaConsoleAuthTable OBJECT-TYPE
    SYNTAX           SEQUENCE OF CfprApAaaConsoleAuthEntry
    MAX-ACCESS       not-accessible
    STATUS           current
    DESCRIPTION
        "Cisco Firepower aaa:ConsoleAuth managed object table"
    ::= { cfprApAaaObjects 5 }

cfprApAaaConsoleAuthEntry OBJECT-TYPE
    SYNTAX           CfprApAaaConsoleAuthEntry
    MAX-ACCESS       not-accessible
    STATUS           current
    DESCRIPTION
        "Entry for the cfprApAaaConsoleAuthTable table."
    INDEX { cfprApAaaConsoleAuthInstanceId }
    ::= { cfprApAaaConsoleAuthTable 1 }

CfprApAaaConsoleAuthEntry ::= SEQUENCE {
    cfprApAaaConsoleAuthInstanceId                                   CfprApManagedObjectId,
    cfprApAaaConsoleAuthDn                                           CfprApManagedObjectDn,
    cfprApAaaConsoleAuthRn                                           SnmpAdminString,
    cfprApAaaConsoleAuthDescr                                        SnmpAdminString,
    cfprApAaaConsoleAuthName                                         SnmpAdminString,
    cfprApAaaConsoleAuthOperProviderGroup                            SnmpAdminString,
    cfprApAaaConsoleAuthOperRealm                                    CfprApAaaRealm,
    cfprApAaaConsoleAuthProviderGroup                                SnmpAdminString,
    cfprApAaaConsoleAuthRealm                                        CfprApAaaRealm,
    cfprApAaaConsoleAuthUse2Factor                                   TruthValue
}

cfprApAaaConsoleAuthInstanceId OBJECT-TYPE
    SYNTAX       CfprApManagedObjectId
    MAX-ACCESS   not-accessible
    STATUS       current
    DESCRIPTION
        "Instance identifier of the managed object."
    ::= { cfprApAaaConsoleAuthEntry 1 }

cfprApAaaConsoleAuthDn OBJECT-TYPE
    SYNTAX       CfprApManagedObjectDn
    MAX-ACCESS   read-only
    STATUS       current
    DESCRIPTION
        "Cisco Firepower aaa:ConsoleAuth:dn managed object property"
    ::= { cfprApAaaConsoleAuthEntry 2 }

cfprApAaaConsoleAuthRn OBJECT-TYPE
    SYNTAX       SnmpAdminString
    MAX-ACCESS   read-only
    STATUS       current
    DESCRIPTION
        "Cisco Firepower aaa:ConsoleAuth:rn managed object property"
    ::= { cfprApAaaConsoleAuthEntry 3 }

cfprApAaaConsoleAuthDescr OBJECT-TYPE
    SYNTAX       SnmpAdminString
    MAX-ACCESS   read-only
    STATUS       current
    DESCRIPTION
        "Cisco Firepower aaa:ConsoleAuth:descr managed object property"
    ::= { cfprApAaaConsoleAuthEntry 4 }

cfprApAaaConsoleAuthName OBJECT-TYPE
    SYNTAX       SnmpAdminString
    MAX-ACCESS   read-only
    STATUS       current
    DESCRIPTION
        "Cisco Firepower aaa:ConsoleAuth:name managed object property"
    ::= { cfprApAaaConsoleAuthEntry 5 }

cfprApAaaConsoleAuthOperProviderGroup OBJECT-TYPE
    SYNTAX       SnmpAdminString
    MAX-ACCESS   read-only
    STATUS       current
    DESCRIPTION
        "Cisco Firepower aaa:ConsoleAuth:operProviderGroup
        managed object property"
    ::= { cfprApAaaConsoleAuthEntry 6 }

cfprApAaaConsoleAuthOperRealm OBJECT-TYPE
    SYNTAX       CfprApAaaRealm
    MAX-ACCESS   read-only
    STATUS       current
    DESCRIPTION
        "Cisco Firepower aaa:ConsoleAuth:operRealm managed
        object property"
    ::= { cfprApAaaConsoleAuthEntry 7 }

cfprApAaaConsoleAuthProviderGroup OBJECT-TYPE
    SYNTAX       SnmpAdminString
    MAX-ACCESS   read-only
    STATUS       current
    DESCRIPTION
        "Cisco Firepower aaa:ConsoleAuth:providerGroup
        managed object property"
    ::= { cfprApAaaConsoleAuthEntry 8 }

cfprApAaaConsoleAuthRealm OBJECT-TYPE
    SYNTAX       CfprApAaaRealm
    MAX-ACCESS   read-only
    STATUS       current
    DESCRIPTION
        "Cisco Firepower aaa:ConsoleAuth:realm managed object property"
    ::= { cfprApAaaConsoleAuthEntry 9 }

cfprApAaaConsoleAuthUse2Factor OBJECT-TYPE
    SYNTAX       TruthValue
    MAX-ACCESS   read-only
    STATUS       current
    DESCRIPTION
        "Cisco Firepower aaa:ConsoleAuth:use2Factor managed
        object property"
    ::= { cfprApAaaConsoleAuthEntry 10 }

cfprApAaaDefaultAuthTable OBJECT-TYPE
    SYNTAX           SEQUENCE OF CfprApAaaDefaultAuthEntry
    MAX-ACCESS       not-accessible
    STATUS           current
    DESCRIPTION
        "Cisco Firepower aaa:DefaultAuth managed object table"
    ::= { cfprApAaaObjects 6 }

cfprApAaaDefaultAuthEntry OBJECT-TYPE
    SYNTAX           CfprApAaaDefaultAuthEntry
    MAX-ACCESS       not-accessible
    STATUS           current
    DESCRIPTION
        "Entry for the cfprApAaaDefaultAuthTable table."
    INDEX { cfprApAaaDefaultAuthInstanceId }
    ::= { cfprApAaaDefaultAuthTable 1 }

CfprApAaaDefaultAuthEntry ::= SEQUENCE {
    cfprApAaaDefaultAuthInstanceId                                   CfprApManagedObjectId,
    cfprApAaaDefaultAuthDn                                           CfprApManagedObjectDn,
    cfprApAaaDefaultAuthRn                                           SnmpAdminString,
    cfprApAaaDefaultAuthDescr                                        SnmpAdminString,
    cfprApAaaDefaultAuthName                                         SnmpAdminString,
    cfprApAaaDefaultAuthOperProviderGroup                            SnmpAdminString,
    cfprApAaaDefaultAuthOperRealm                                    CfprApAaaRealm,
    cfprApAaaDefaultAuthProviderGroup                                SnmpAdminString,
    cfprApAaaDefaultAuthRealm                                        CfprApAaaRealm,
    cfprApAaaDefaultAuthRefreshPeriod                                Gauge32,
    cfprApAaaDefaultAuthSessionTimeout                               Gauge32,
    cfprApAaaDefaultAuthUse2Factor                                   TruthValue
}

cfprApAaaDefaultAuthInstanceId OBJECT-TYPE
    SYNTAX       CfprApManagedObjectId
    MAX-ACCESS   not-accessible
    STATUS       current
    DESCRIPTION
        "Instance identifier of the managed object."
    ::= { cfprApAaaDefaultAuthEntry 1 }

cfprApAaaDefaultAuthDn OBJECT-TYPE
    SYNTAX       CfprApManagedObjectDn
    MAX-ACCESS   read-only
    STATUS       current
    DESCRIPTION
        "Cisco Firepower aaa:DefaultAuth:dn managed object property"
    ::= { cfprApAaaDefaultAuthEntry 2 }

cfprApAaaDefaultAuthRn OBJECT-TYPE
    SYNTAX       SnmpAdminString
    MAX-ACCESS   read-only
    STATUS       current
    DESCRIPTION
        "Cisco Firepower aaa:DefaultAuth:rn managed object property"
    ::= { cfprApAaaDefaultAuthEntry 3 }

cfprApAaaDefaultAuthDescr OBJECT-TYPE
    SYNTAX       SnmpAdminString
    MAX-ACCESS   read-only
    STATUS       current
    DESCRIPTION
        "Cisco Firepower aaa:DefaultAuth:descr managed object property"
    ::= { cfprApAaaDefaultAuthEntry 4 }

cfprApAaaDefaultAuthName OBJECT-TYPE
    SYNTAX       SnmpAdminString
    MAX-ACCESS   read-only
    STATUS       current
    DESCRIPTION
        "Cisco Firepower aaa:DefaultAuth:name managed object property"
    ::= { cfprApAaaDefaultAuthEntry 5 }

cfprApAaaDefaultAuthOperProviderGroup OBJECT-TYPE
    SYNTAX       SnmpAdminString
    MAX-ACCESS   read-only
    STATUS       current
    DESCRIPTION
        "Cisco Firepower aaa:DefaultAuth:operProviderGroup
        managed object property"
    ::= { cfprApAaaDefaultAuthEntry 6 }

cfprApAaaDefaultAuthOperRealm OBJECT-TYPE
    SYNTAX       CfprApAaaRealm
    MAX-ACCESS   read-only
    STATUS       current
    DESCRIPTION
        "Cisco Firepower aaa:DefaultAuth:operRealm managed
        object property"
    ::= { cfprApAaaDefaultAuthEntry 7 }

cfprApAaaDefaultAuthProviderGroup OBJECT-TYPE
    SYNTAX       SnmpAdminString
    MAX-ACCESS   read-only
    STATUS       current
    DESCRIPTION
        "Cisco Firepower aaa:DefaultAuth:providerGroup
        managed object property"
    ::= { cfprApAaaDefaultAuthEntry 8 }

cfprApAaaDefaultAuthRealm OBJECT-TYPE
    SYNTAX       CfprApAaaRealm
    MAX-ACCESS   read-only
    STATUS       current
    DESCRIPTION
        "Cisco Firepower aaa:DefaultAuth:realm managed object property"
    ::= { cfprApAaaDefaultAuthEntry 9 }

cfprApAaaDefaultAuthRefreshPeriod OBJECT-TYPE
    SYNTAX       Gauge32
    MAX-ACCESS   read-only
    STATUS       current
    DESCRIPTION
        "Cisco Firepower aaa:DefaultAuth:refreshPeriod
        managed object property"
    ::= { cfprApAaaDefaultAuthEntry 10 }

cfprApAaaDefaultAuthSessionTimeout OBJECT-TYPE
    SYNTAX       Gauge32
    MAX-ACCESS   read-only
    STATUS       current
    DESCRIPTION
        "Cisco Firepower aaa:DefaultAuth:sessionTimeout
        managed object property"
    ::= { cfprApAaaDefaultAuthEntry 11 }

cfprApAaaDefaultAuthUse2Factor OBJECT-TYPE
    SYNTAX       TruthValue
    MAX-ACCESS   read-only
    STATUS       current
    DESCRIPTION
        "Cisco Firepower aaa:DefaultAuth:use2Factor managed
        object property"
    ::= { cfprApAaaDefaultAuthEntry 12 }

cfprApAaaDomainTable OBJECT-TYPE
    SYNTAX           SEQUENCE OF CfprApAaaDomainEntry
    MAX-ACCESS       not-accessible
    STATUS           current
    DESCRIPTION
        "Cisco Firepower aaa:Domain managed object table"
    ::= { cfprApAaaObjects 7 }

cfprApAaaDomainEntry OBJECT-TYPE
    SYNTAX           CfprApAaaDomainEntry
    MAX-ACCESS       not-accessible
    STATUS           current
    DESCRIPTION
        "Entry for the cfprApAaaDomainTable table."
    INDEX { cfprApAaaDomainInstanceId }
    ::= { cfprApAaaDomainTable 1 }

CfprApAaaDomainEntry ::= SEQUENCE {
    cfprApAaaDomainInstanceId                                        CfprApManagedObjectId,
    cfprApAaaDomainDn                                                CfprApManagedObjectDn,
    cfprApAaaDomainRn                                                SnmpAdminString,
    cfprApAaaDomainDescr                                             SnmpAdminString,
    cfprApAaaDomainName                                              SnmpAdminString,
    cfprApAaaDomainRefreshPeriod                                     Gauge32,
    cfprApAaaDomainSessionTimeout                                    Gauge32
}

cfprApAaaDomainInstanceId OBJECT-TYPE
    SYNTAX       CfprApManagedObjectId
    MAX-ACCESS   not-accessible
    STATUS       current
    DESCRIPTION
        "Instance identifier of the managed object."
    ::= { cfprApAaaDomainEntry 1 }

cfprApAaaDomainDn OBJECT-TYPE
    SYNTAX       CfprApManagedObjectDn
    MAX-ACCESS   read-only
    STATUS       current
    DESCRIPTION
        "Cisco Firepower aaa:Domain:dn managed object property"
    ::= { cfprApAaaDomainEntry 2 }

cfprApAaaDomainRn OBJECT-TYPE
    SYNTAX       SnmpAdminString
    MAX-ACCESS   read-only
    STATUS       current
    DESCRIPTION
        "Cisco Firepower aaa:Domain:rn managed object property"
    ::= { cfprApAaaDomainEntry 3 }

cfprApAaaDomainDescr OBJECT-TYPE
    SYNTAX       SnmpAdminString
    MAX-ACCESS   read-only
    STATUS       current
    DESCRIPTION
        "Cisco Firepower aaa:Domain:descr managed object property"
    ::= { cfprApAaaDomainEntry 4 }

cfprApAaaDomainName OBJECT-TYPE
    SYNTAX       SnmpAdminString
    MAX-ACCESS   read-only
    STATUS       current
    DESCRIPTION
        "Cisco Firepower aaa:Domain:name managed object property"
    ::= { cfprApAaaDomainEntry 5 }

cfprApAaaDomainRefreshPeriod OBJECT-TYPE
    SYNTAX       Gauge32
    MAX-ACCESS   read-only
    STATUS       current
    DESCRIPTION
        "Cisco Firepower aaa:Domain:refreshPeriod managed object property"
    ::= { cfprApAaaDomainEntry 6 }

cfprApAaaDomainSessionTimeout OBJECT-TYPE
    SYNTAX       Gauge32
    MAX-ACCESS   read-only
    STATUS       current
    DESCRIPTION
        "Cisco Firepower aaa:Domain:sessionTimeout managed
        object property"
    ::= { cfprApAaaDomainEntry 7 }

cfprApAaaDomainAuthTable OBJECT-TYPE
    SYNTAX           SEQUENCE OF CfprApAaaDomainAuthEntry
    MAX-ACCESS       not-accessible
    STATUS           current
    DESCRIPTION
        "Cisco Firepower aaa:DomainAuth managed object table"
    ::= { cfprApAaaObjects 8 }

cfprApAaaDomainAuthEntry OBJECT-TYPE
    SYNTAX           CfprApAaaDomainAuthEntry
    MAX-ACCESS       not-accessible
    STATUS           current
    DESCRIPTION
        "Entry for the cfprApAaaDomainAuthTable table."
    INDEX { cfprApAaaDomainAuthInstanceId }
    ::= { cfprApAaaDomainAuthTable 1 }

CfprApAaaDomainAuthEntry ::= SEQUENCE {
    cfprApAaaDomainAuthInstanceId                                    CfprApManagedObjectId,
    cfprApAaaDomainAuthDn                                            CfprApManagedObjectDn,
    cfprApAaaDomainAuthRn                                            SnmpAdminString,
    cfprApAaaDomainAuthDescr                                         SnmpAdminString,
    cfprApAaaDomainAuthName                                          SnmpAdminString,
    cfprApAaaDomainAuthOperProviderGroup                             SnmpAdminString,
    cfprApAaaDomainAuthOperRealm                                     CfprApAaaRealm,
    cfprApAaaDomainAuthProviderGroup                                 SnmpAdminString,
    cfprApAaaDomainAuthRealm                                         CfprApAaaDomainAuthRealm,
    cfprApAaaDomainAuthUse2Factor                                    TruthValue
}

cfprApAaaDomainAuthInstanceId OBJECT-TYPE
    SYNTAX       CfprApManagedObjectId
    MAX-ACCESS   not-accessible
    STATUS       current
    DESCRIPTION
        "Instance identifier of the managed object."
    ::= { cfprApAaaDomainAuthEntry 1 }

cfprApAaaDomainAuthDn OBJECT-TYPE
    SYNTAX       CfprApManagedObjectDn
    MAX-ACCESS   read-only
    STATUS       current
    DESCRIPTION
        "Cisco Firepower aaa:DomainAuth:dn managed object property"
    ::= { cfprApAaaDomainAuthEntry 2 }

cfprApAaaDomainAuthRn OBJECT-TYPE
    SYNTAX       SnmpAdminString
    MAX-ACCESS   read-only
    STATUS       current
    DESCRIPTION
        "Cisco Firepower aaa:DomainAuth:rn managed object property"
    ::= { cfprApAaaDomainAuthEntry 3 }

cfprApAaaDomainAuthDescr OBJECT-TYPE
    SYNTAX       SnmpAdminString
    MAX-ACCESS   read-only
    STATUS       current
    DESCRIPTION
        "Cisco Firepower aaa:DomainAuth:descr managed object property"
    ::= { cfprApAaaDomainAuthEntry 4 }

cfprApAaaDomainAuthName OBJECT-TYPE
    SYNTAX       SnmpAdminString
    MAX-ACCESS   read-only
    STATUS       current
    DESCRIPTION
        "Cisco Firepower aaa:DomainAuth:name managed object property"
    ::= { cfprApAaaDomainAuthEntry 5 }

cfprApAaaDomainAuthOperProviderGroup OBJECT-TYPE
    SYNTAX       SnmpAdminString
    MAX-ACCESS   read-only
    STATUS       current
    DESCRIPTION
        "Cisco Firepower aaa:DomainAuth:operProviderGroup
        managed object property"
    ::= { cfprApAaaDomainAuthEntry 6 }

cfprApAaaDomainAuthOperRealm OBJECT-TYPE
    SYNTAX       CfprApAaaRealm
    MAX-ACCESS   read-only
    STATUS       current
    DESCRIPTION
        "Cisco Firepower aaa:DomainAuth:operRealm managed object property"
    ::= { cfprApAaaDomainAuthEntry 7 }

cfprApAaaDomainAuthProviderGroup OBJECT-TYPE
    SYNTAX       SnmpAdminString
    MAX-ACCESS   read-only
    STATUS       current
    DESCRIPTION
        "Cisco Firepower aaa:DomainAuth:providerGroup managed
        object property"
    ::= { cfprApAaaDomainAuthEntry 8 }

cfprApAaaDomainAuthRealm OBJECT-TYPE
    SYNTAX       CfprApAaaDomainAuthRealm
    MAX-ACCESS   read-only
    STATUS       current
    DESCRIPTION
        "Cisco Firepower aaa:DomainAuth:realm managed object property"
    ::= { cfprApAaaDomainAuthEntry 9 }

cfprApAaaDomainAuthUse2Factor OBJECT-TYPE
    SYNTAX       TruthValue
    MAX-ACCESS   read-only
    STATUS       current
    DESCRIPTION
        "Cisco Firepower aaa:DomainAuth:use2Factor managed
        object property"
    ::= { cfprApAaaDomainAuthEntry 10 }

cfprApAaaEpAuthProfileTable OBJECT-TYPE
    SYNTAX           SEQUENCE OF CfprApAaaEpAuthProfileEntry
    MAX-ACCESS       not-accessible
    STATUS           current
    DESCRIPTION
        "Cisco Firepower aaa:EpAuthProfile managed object table"
    ::= { cfprApAaaObjects 9 }

cfprApAaaEpAuthProfileEntry OBJECT-TYPE
    SYNTAX           CfprApAaaEpAuthProfileEntry
    MAX-ACCESS       not-accessible
    STATUS           current
    DESCRIPTION
        "Entry for the cfprApAaaEpAuthProfileTable table."
    INDEX { cfprApAaaEpAuthProfileInstanceId }
    ::= { cfprApAaaEpAuthProfileTable 1 }

CfprApAaaEpAuthProfileEntry ::= SEQUENCE {
    cfprApAaaEpAuthProfileInstanceId                                 CfprApManagedObjectId,
    cfprApAaaEpAuthProfileDn                                         CfprApManagedObjectDn,
    cfprApAaaEpAuthProfileRn                                         SnmpAdminString,
    cfprApAaaEpAuthProfileDescr                                      SnmpAdminString,
    cfprApAaaEpAuthProfileIntId                                      SnmpAdminString,
    cfprApAaaEpAuthProfileIpmiOverLan                                CfprApAaaIpmiOverLan,
    cfprApAaaEpAuthProfileName                                       SnmpAdminString,
    cfprApAaaEpAuthProfilePolicyLevel                                Gauge32,
    cfprApAaaEpAuthProfilePolicyOwner                                CfprApPolicyPolicyOwner
}

cfprApAaaEpAuthProfileInstanceId OBJECT-TYPE
    SYNTAX       CfprApManagedObjectId
    MAX-ACCESS   not-accessible
    STATUS       current
    DESCRIPTION
        "Instance identifier of the managed object."
    ::= { cfprApAaaEpAuthProfileEntry 1 }

cfprApAaaEpAuthProfileDn OBJECT-TYPE
    SYNTAX       CfprApManagedObjectDn
    MAX-ACCESS   read-only
    STATUS       current
    DESCRIPTION
        "Cisco Firepower aaa:EpAuthProfile:dn managed object property"
    ::= { cfprApAaaEpAuthProfileEntry 2 }

cfprApAaaEpAuthProfileRn OBJECT-TYPE
    SYNTAX       SnmpAdminString
    MAX-ACCESS   read-only
    STATUS       current
    DESCRIPTION
        "Cisco Firepower aaa:EpAuthProfile:rn managed object property"
    ::= { cfprApAaaEpAuthProfileEntry 3 }

cfprApAaaEpAuthProfileDescr OBJECT-TYPE
    SYNTAX       SnmpAdminString
    MAX-ACCESS   read-only
    STATUS       current
    DESCRIPTION
        "Cisco Firepower aaa:EpAuthProfile:descr managed object property"
    ::= { cfprApAaaEpAuthProfileEntry 4 }

cfprApAaaEpAuthProfileIntId OBJECT-TYPE
    SYNTAX       SnmpAdminString
    MAX-ACCESS   read-only
    STATUS       current
    DESCRIPTION
        "Cisco Firepower aaa:EpAuthProfile:intId managed object property"
    ::= { cfprApAaaEpAuthProfileEntry 5 }

cfprApAaaEpAuthProfileIpmiOverLan OBJECT-TYPE
    SYNTAX       CfprApAaaIpmiOverLan
    MAX-ACCESS   read-only
    STATUS       current
    DESCRIPTION
        "Cisco Firepower aaa:EpAuthProfile:ipmiOverLan
        managed object property"
    ::= { cfprApAaaEpAuthProfileEntry 6 }

cfprApAaaEpAuthProfileName OBJECT-TYPE
    SYNTAX       SnmpAdminString
    MAX-ACCESS   read-only
    STATUS       current
    DESCRIPTION
        "Cisco Firepower aaa:EpAuthProfile:name managed object property"
    ::= { cfprApAaaEpAuthProfileEntry 7 }

cfprApAaaEpAuthProfilePolicyLevel OBJECT-TYPE
    SYNTAX       Gauge32
    MAX-ACCESS   read-only
    STATUS       current
    DESCRIPTION
        "Cisco Firepower aaa:EpAuthProfile:policyLevel
        managed object property"
    ::= { cfprApAaaEpAuthProfileEntry 8 }

cfprApAaaEpAuthProfilePolicyOwner OBJECT-TYPE
    SYNTAX       CfprApPolicyPolicyOwner
    MAX-ACCESS   read-only
    STATUS       current
    DESCRIPTION
        "Cisco Firepower aaa:EpAuthProfile:policyOwner
        managed object property"
    ::= { cfprApAaaEpAuthProfileEntry 9 }

cfprApAaaEpFsmTable OBJECT-TYPE
    SYNTAX           SEQUENCE OF CfprApAaaEpFsmEntry
    MAX-ACCESS       not-accessible
    STATUS           current
    DESCRIPTION
        "Cisco Firepower aaa:EpFsm managed object table"
    ::= { cfprApAaaObjects 10 }

cfprApAaaEpFsmEntry OBJECT-TYPE
    SYNTAX           CfprApAaaEpFsmEntry
    MAX-ACCESS       not-accessible
    STATUS           current
    DESCRIPTION
        "Entry for the cfprApAaaEpFsmTable table."
    INDEX { cfprApAaaEpFsmInstanceId }
    ::= { cfprApAaaEpFsmTable 1 }

CfprApAaaEpFsmEntry ::= SEQUENCE {
    cfprApAaaEpFsmInstanceId                                         CfprApManagedObjectId,
    cfprApAaaEpFsmDn                                                 CfprApManagedObjectDn,
    cfprApAaaEpFsmRn                                                 SnmpAdminString,
    cfprApAaaEpFsmCompletionTime                                     DateAndTime,
    cfprApAaaEpFsmCurrentFsm                                         CfprApAaaEpFsmCurrentFsm,
    cfprApAaaEpFsmDescr                                              SnmpAdminString,
    cfprApAaaEpFsmFsmStatus                                          CfprApFsmFsmStageStatus,
    cfprApAaaEpFsmProgress                                           Gauge32,
    cfprApAaaEpFsmRmtErrCode                                         Gauge32,
    cfprApAaaEpFsmRmtErrDescr                                        SnmpAdminString,
    cfprApAaaEpFsmRmtRslt                                            CfprApConditionRemoteInvRslt
}

cfprApAaaEpFsmInstanceId OBJECT-TYPE
    SYNTAX       CfprApManagedObjectId
    MAX-ACCESS   not-accessible
    STATUS       current
    DESCRIPTION
        "Instance identifier of the managed object."
    ::= { cfprApAaaEpFsmEntry 1 }

cfprApAaaEpFsmDn OBJECT-TYPE
    SYNTAX       CfprApManagedObjectDn
    MAX-ACCESS   read-only
    STATUS       current
    DESCRIPTION
        "Cisco Firepower aaa:EpFsm:dn managed object property"
    ::= { cfprApAaaEpFsmEntry 2 }

cfprApAaaEpFsmRn OBJECT-TYPE
    SYNTAX       SnmpAdminString
    MAX-ACCESS   read-only
    STATUS       current
    DESCRIPTION
        "Cisco Firepower aaa:EpFsm:rn managed object property"
    ::= { cfprApAaaEpFsmEntry 3 }

cfprApAaaEpFsmCompletionTime OBJECT-TYPE
    SYNTAX       DateAndTime
    MAX-ACCESS   read-only
    STATUS       current
    DESCRIPTION
        "Cisco Firepower aaa:EpFsm:completionTime managed object property"
    ::= { cfprApAaaEpFsmEntry 4 }

cfprApAaaEpFsmCurrentFsm OBJECT-TYPE
    SYNTAX       CfprApAaaEpFsmCurrentFsm
    MAX-ACCESS   read-only
    STATUS       current
    DESCRIPTION
        "Cisco Firepower aaa:EpFsm:currentFsm managed object property"
    ::= { cfprApAaaEpFsmEntry 5 }

cfprApAaaEpFsmDescr OBJECT-TYPE
    SYNTAX       SnmpAdminString
    MAX-ACCESS   read-only
    STATUS       current
    DESCRIPTION
        "Cisco Firepower aaa:EpFsm:descr managed object property"
    ::= { cfprApAaaEpFsmEntry 6 }

cfprApAaaEpFsmFsmStatus OBJECT-TYPE
    SYNTAX       CfprApFsmFsmStageStatus
    MAX-ACCESS   read-only
    STATUS       current
    DESCRIPTION
        "Cisco Firepower aaa:EpFsm:fsmStatus managed object property"
    ::= { cfprApAaaEpFsmEntry 7 }

cfprApAaaEpFsmProgress OBJECT-TYPE
    SYNTAX       Gauge32
    MAX-ACCESS   read-only
    STATUS       current
    DESCRIPTION
        "Cisco Firepower aaa:EpFsm:progress managed object property"
    ::= { cfprApAaaEpFsmEntry 8 }

cfprApAaaEpFsmRmtErrCode OBJECT-TYPE
    SYNTAX       Gauge32
    MAX-ACCESS   read-only
    STATUS       current
    DESCRIPTION
        "Cisco Firepower aaa:EpFsm:rmtErrCode managed object property"
    ::= { cfprApAaaEpFsmEntry 9 }

cfprApAaaEpFsmRmtErrDescr OBJECT-TYPE
    SYNTAX       SnmpAdminString
    MAX-ACCESS   read-only
    STATUS       current
    DESCRIPTION
        "Cisco Firepower aaa:EpFsm:rmtErrDescr managed object property"
    ::= { cfprApAaaEpFsmEntry 10 }

cfprApAaaEpFsmRmtRslt OBJECT-TYPE
    SYNTAX       CfprApConditionRemoteInvRslt
    MAX-ACCESS   read-only
    STATUS       current
    DESCRIPTION
        "Cisco Firepower aaa:EpFsm:rmtRslt managed object property"
    ::= { cfprApAaaEpFsmEntry 11 }

cfprApAaaEpFsmStageTable OBJECT-TYPE
    SYNTAX           SEQUENCE OF CfprApAaaEpFsmStageEntry
    MAX-ACCESS       not-accessible
    STATUS           current
    DESCRIPTION
        "Cisco Firepower aaa:EpFsmStage managed object table"
    ::= { cfprApAaaObjects 11 }

cfprApAaaEpFsmStageEntry OBJECT-TYPE
    SYNTAX           CfprApAaaEpFsmStageEntry
    MAX-ACCESS       not-accessible
    STATUS           current
    DESCRIPTION
        "Entry for the cfprApAaaEpFsmStageTable table."
    INDEX { cfprApAaaEpFsmStageInstanceId }
    ::= { cfprApAaaEpFsmStageTable 1 }

CfprApAaaEpFsmStageEntry ::= SEQUENCE {
    cfprApAaaEpFsmStageInstanceId                                    CfprApManagedObjectId,
    cfprApAaaEpFsmStageDn                                            CfprApManagedObjectDn,
    cfprApAaaEpFsmStageRn                                            SnmpAdminString,
    cfprApAaaEpFsmStageDescr                                         SnmpAdminString,
    cfprApAaaEpFsmStageLastUpdateTime                                DateAndTime,
    cfprApAaaEpFsmStageName                                          CfprApAaaEpFsmStageName,
    cfprApAaaEpFsmStageOrder                                         Gauge32,
    cfprApAaaEpFsmStageRetry                                         Gauge32,
    cfprApAaaEpFsmStageStageStatus                                   CfprApFsmFsmStageStatus
}

cfprApAaaEpFsmStageInstanceId OBJECT-TYPE
    SYNTAX       CfprApManagedObjectId
    MAX-ACCESS   not-accessible
    STATUS       current
    DESCRIPTION
        "Instance identifier of the managed object."
    ::= { cfprApAaaEpFsmStageEntry 1 }

cfprApAaaEpFsmStageDn OBJECT-TYPE
    SYNTAX       CfprApManagedObjectDn
    MAX-ACCESS   read-only
    STATUS       current
    DESCRIPTION
        "Cisco Firepower aaa:EpFsmStage:dn managed object property"
    ::= { cfprApAaaEpFsmStageEntry 2 }

cfprApAaaEpFsmStageRn OBJECT-TYPE
    SYNTAX       SnmpAdminString
    MAX-ACCESS   read-only
    STATUS       current
    DESCRIPTION
        "Cisco Firepower aaa:EpFsmStage:rn managed object property"
    ::= { cfprApAaaEpFsmStageEntry 3 }

cfprApAaaEpFsmStageDescr OBJECT-TYPE
    SYNTAX       SnmpAdminString
    MAX-ACCESS   read-only
    STATUS       current
    DESCRIPTION
        "Cisco Firepower aaa:EpFsmStage:descr managed object property"
    ::= { cfprApAaaEpFsmStageEntry 4 }

cfprApAaaEpFsmStageLastUpdateTime OBJECT-TYPE
    SYNTAX       DateAndTime
    MAX-ACCESS   read-only
    STATUS       current
    DESCRIPTION
        "Cisco Firepower aaa:EpFsmStage:lastUpdateTime
        managed object property"
    ::= { cfprApAaaEpFsmStageEntry 5 }

cfprApAaaEpFsmStageName OBJECT-TYPE
    SYNTAX       CfprApAaaEpFsmStageName
    MAX-ACCESS   read-only
    STATUS       current
    DESCRIPTION
        "Cisco Firepower aaa:EpFsmStage:name managed object property"
    ::= { cfprApAaaEpFsmStageEntry 6 }

cfprApAaaEpFsmStageOrder OBJECT-TYPE
    SYNTAX       Gauge32
    MAX-ACCESS   read-only
    STATUS       current
    DESCRIPTION
        "Cisco Firepower aaa:EpFsmStage:order managed object property"
    ::= { cfprApAaaEpFsmStageEntry 7 }

cfprApAaaEpFsmStageRetry OBJECT-TYPE
    SYNTAX       Gauge32
    MAX-ACCESS   read-only
    STATUS       current
    DESCRIPTION
        "Cisco Firepower aaa:EpFsmStage:retry managed object property"
    ::= { cfprApAaaEpFsmStageEntry 8 }

cfprApAaaEpFsmStageStageStatus OBJECT-TYPE
    SYNTAX       CfprApFsmFsmStageStatus
    MAX-ACCESS   read-only
    STATUS       current
    DESCRIPTION
        "Cisco Firepower aaa:EpFsmStage:stageStatus managed
        object property"
    ::= { cfprApAaaEpFsmStageEntry 9 }

cfprApAaaEpFsmTaskTable OBJECT-TYPE
    SYNTAX           SEQUENCE OF CfprApAaaEpFsmTaskEntry
    MAX-ACCESS       not-accessible
    STATUS           current
    DESCRIPTION
        "Cisco Firepower aaa:EpFsmTask managed object table"
    ::= { cfprApAaaObjects 12 }

cfprApAaaEpFsmTaskEntry OBJECT-TYPE
    SYNTAX           CfprApAaaEpFsmTaskEntry
    MAX-ACCESS       not-accessible
    STATUS           current
    DESCRIPTION
        "Entry for the cfprApAaaEpFsmTaskTable table."
    INDEX { cfprApAaaEpFsmTaskInstanceId }
    ::= { cfprApAaaEpFsmTaskTable 1 }

CfprApAaaEpFsmTaskEntry ::= SEQUENCE {
    cfprApAaaEpFsmTaskInstanceId                                     CfprApManagedObjectId,
    cfprApAaaEpFsmTaskDn                                             CfprApManagedObjectDn,
    cfprApAaaEpFsmTaskRn                                             SnmpAdminString,
    cfprApAaaEpFsmTaskCompletion                                     CfprApFsmCompletion,
    cfprApAaaEpFsmTaskFlags                                          CfprApFsmFlags,
    cfprApAaaEpFsmTaskItem                                           CfprApAaaEpFsmTaskItem,
    cfprApAaaEpFsmTaskSeqId                                          Gauge32
}

cfprApAaaEpFsmTaskInstanceId OBJECT-TYPE
    SYNTAX       CfprApManagedObjectId
    MAX-ACCESS   not-accessible
    STATUS       current
    DESCRIPTION
        "Instance identifier of the managed object."
    ::= { cfprApAaaEpFsmTaskEntry 1 }

cfprApAaaEpFsmTaskDn OBJECT-TYPE
    SYNTAX       CfprApManagedObjectDn
    MAX-ACCESS   read-only
    STATUS       current
    DESCRIPTION
        "Cisco Firepower aaa:EpFsmTask:dn managed object property"
    ::= { cfprApAaaEpFsmTaskEntry 2 }

cfprApAaaEpFsmTaskRn OBJECT-TYPE
    SYNTAX       SnmpAdminString
    MAX-ACCESS   read-only
    STATUS       current
    DESCRIPTION
        "Cisco Firepower aaa:EpFsmTask:rn managed object property"
    ::= { cfprApAaaEpFsmTaskEntry 3 }

cfprApAaaEpFsmTaskCompletion OBJECT-TYPE
    SYNTAX       CfprApFsmCompletion
    MAX-ACCESS   read-only
    STATUS       current
    DESCRIPTION
        "Cisco Firepower aaa:EpFsmTask:completion managed object property"
    ::= { cfprApAaaEpFsmTaskEntry 4 }

cfprApAaaEpFsmTaskFlags OBJECT-TYPE
    SYNTAX       CfprApFsmFlags
    MAX-ACCESS   read-only
    STATUS       current
    DESCRIPTION
        "Cisco Firepower aaa:EpFsmTask:flags managed object property"
    ::= { cfprApAaaEpFsmTaskEntry 5 }

cfprApAaaEpFsmTaskItem OBJECT-TYPE
    SYNTAX       CfprApAaaEpFsmTaskItem
    MAX-ACCESS   read-only
    STATUS       current
    DESCRIPTION
        "Cisco Firepower aaa:EpFsmTask:item managed object property"
    ::= { cfprApAaaEpFsmTaskEntry 6 }

cfprApAaaEpFsmTaskSeqId OBJECT-TYPE
    SYNTAX       Gauge32
    MAX-ACCESS   read-only
    STATUS       current
    DESCRIPTION
        "Cisco Firepower aaa:EpFsmTask:seqId managed object property"
    ::= { cfprApAaaEpFsmTaskEntry 7 }

cfprApAaaEpLoginTable OBJECT-TYPE
    SYNTAX           SEQUENCE OF CfprApAaaEpLoginEntry
    MAX-ACCESS       not-accessible
    STATUS           current
    DESCRIPTION
        "Cisco Firepower aaa:EpLogin managed object table"
    ::= { cfprApAaaObjects 13 }

cfprApAaaEpLoginEntry OBJECT-TYPE
    SYNTAX           CfprApAaaEpLoginEntry
    MAX-ACCESS       not-accessible
    STATUS           current
    DESCRIPTION
        "Entry for the cfprApAaaEpLoginTable table."
    INDEX { cfprApAaaEpLoginInstanceId }
    ::= { cfprApAaaEpLoginTable 1 }

CfprApAaaEpLoginEntry ::= SEQUENCE {
    cfprApAaaEpLoginInstanceId                                       CfprApManagedObjectId,
    cfprApAaaEpLoginDn                                               CfprApManagedObjectDn,
    cfprApAaaEpLoginRn                                               SnmpAdminString,
    cfprApAaaEpLoginDescr                                            SnmpAdminString,
    cfprApAaaEpLoginId                                               SnmpAdminString,
    cfprApAaaEpLoginIntId                                            SnmpAdminString,
    cfprApAaaEpLoginLocalHost                                        SnmpAdminString,
    cfprApAaaEpLoginName                                             SnmpAdminString,
    cfprApAaaEpLoginPolicyLevel                                      Gauge32,
    cfprApAaaEpLoginPolicyOwner                                      CfprApPolicyPolicyOwner,
    cfprApAaaEpLoginRemoteHost                                       SnmpAdminString,
    cfprApAaaEpLoginSession                                          CfprApAaaSession,
    cfprApAaaEpLoginSwitchId                                         CfprApNetworkSwitchId
}

cfprApAaaEpLoginInstanceId OBJECT-TYPE
    SYNTAX       CfprApManagedObjectId
    MAX-ACCESS   not-accessible
    STATUS       current
    DESCRIPTION
        "Instance identifier of the managed object."
    ::= { cfprApAaaEpLoginEntry 1 }

cfprApAaaEpLoginDn OBJECT-TYPE
    SYNTAX       CfprApManagedObjectDn
    MAX-ACCESS   read-only
    STATUS       current
    DESCRIPTION
        "Cisco Firepower aaa:EpLogin:dn managed object property"
    ::= { cfprApAaaEpLoginEntry 2 }

cfprApAaaEpLoginRn OBJECT-TYPE
    SYNTAX       SnmpAdminString
    MAX-ACCESS   read-only
    STATUS       current
    DESCRIPTION
        "Cisco Firepower aaa:EpLogin:rn managed object property"
    ::= { cfprApAaaEpLoginEntry 3 }

cfprApAaaEpLoginDescr OBJECT-TYPE
    SYNTAX       SnmpAdminString
    MAX-ACCESS   read-only
    STATUS       current
    DESCRIPTION
        "Cisco Firepower aaa:EpLogin:descr managed object property"
    ::= { cfprApAaaEpLoginEntry 4 }

cfprApAaaEpLoginId OBJECT-TYPE
    SYNTAX       SnmpAdminString
    MAX-ACCESS   read-only
    STATUS       current
    DESCRIPTION
        "Cisco Firepower aaa:EpLogin:id managed object property"
    ::= { cfprApAaaEpLoginEntry 5 }

cfprApAaaEpLoginIntId OBJECT-TYPE
    SYNTAX       SnmpAdminString
    MAX-ACCESS   read-only
    STATUS       current
    DESCRIPTION
        "Cisco Firepower aaa:EpLogin:intId managed object property"
    ::= { cfprApAaaEpLoginEntry 6 }

cfprApAaaEpLoginLocalHost OBJECT-TYPE
    SYNTAX       SnmpAdminString
    MAX-ACCESS   read-only
    STATUS       current
    DESCRIPTION
        "Cisco Firepower aaa:EpLogin:localHost managed object property"
    ::= { cfprApAaaEpLoginEntry 7 }

cfprApAaaEpLoginName OBJECT-TYPE
    SYNTAX       SnmpAdminString
    MAX-ACCESS   read-only
    STATUS       current
    DESCRIPTION
        "Cisco Firepower aaa:EpLogin:name managed object property"
    ::= { cfprApAaaEpLoginEntry 8 }

cfprApAaaEpLoginPolicyLevel OBJECT-TYPE
    SYNTAX       Gauge32
    MAX-ACCESS   read-only
    STATUS       current
    DESCRIPTION
        "Cisco Firepower aaa:EpLogin:policyLevel managed object property"
    ::= { cfprApAaaEpLoginEntry 9 }

cfprApAaaEpLoginPolicyOwner OBJECT-TYPE
    SYNTAX       CfprApPolicyPolicyOwner
    MAX-ACCESS   read-only
    STATUS       current
    DESCRIPTION
        "Cisco Firepower aaa:EpLogin:policyOwner managed object property"
    ::= { cfprApAaaEpLoginEntry 10 }

cfprApAaaEpLoginRemoteHost OBJECT-TYPE
    SYNTAX       SnmpAdminString
    MAX-ACCESS   read-only
    STATUS       current
    DESCRIPTION
        "Cisco Firepower aaa:EpLogin:remoteHost managed object property"
    ::= { cfprApAaaEpLoginEntry 11 }

cfprApAaaEpLoginSession OBJECT-TYPE
    SYNTAX       CfprApAaaSession
    MAX-ACCESS   read-only
    STATUS       current
    DESCRIPTION
        "Cisco Firepower aaa:EpLogin:session managed object property"
    ::= { cfprApAaaEpLoginEntry 12 }

cfprApAaaEpLoginSwitchId OBJECT-TYPE
    SYNTAX       CfprApNetworkSwitchId
    MAX-ACCESS   read-only
    STATUS       current
    DESCRIPTION
        "Cisco Firepower aaa:EpLogin:switchId managed object property"
    ::= { cfprApAaaEpLoginEntry 13 }

cfprApAaaEpUserTable OBJECT-TYPE
    SYNTAX           SEQUENCE OF CfprApAaaEpUserEntry
    MAX-ACCESS       not-accessible
    STATUS           current
    DESCRIPTION
        "Cisco Firepower aaa:EpUser managed object table"
    ::= { cfprApAaaObjects 14 }

cfprApAaaEpUserEntry OBJECT-TYPE
    SYNTAX           CfprApAaaEpUserEntry
    MAX-ACCESS       not-accessible
    STATUS           current
    DESCRIPTION
        "Entry for the cfprApAaaEpUserTable table."
    INDEX { cfprApAaaEpUserInstanceId }
    ::= { cfprApAaaEpUserTable 1 }

CfprApAaaEpUserEntry ::= SEQUENCE {
    cfprApAaaEpUserInstanceId                                        CfprApManagedObjectId,
    cfprApAaaEpUserDn                                                CfprApManagedObjectDn,
    cfprApAaaEpUserRn                                                SnmpAdminString,
    cfprApAaaEpUserConfigState                                       CfprApAaaConfigState,
    cfprApAaaEpUserConfigStatusMessage                               SnmpAdminString,
    cfprApAaaEpUserDescr                                             SnmpAdminString,
    cfprApAaaEpUserName                                              SnmpAdminString,
    cfprApAaaEpUserPriv                                              CfprApAaaEpAccess,
    cfprApAaaEpUserPwd                                               SnmpAdminString,
    cfprApAaaEpUserPwdSet                                            TruthValue
}

cfprApAaaEpUserInstanceId OBJECT-TYPE
    SYNTAX       CfprApManagedObjectId
    MAX-ACCESS   not-accessible
    STATUS       current
    DESCRIPTION
        "Instance identifier of the managed object."
    ::= { cfprApAaaEpUserEntry 1 }

cfprApAaaEpUserDn OBJECT-TYPE
    SYNTAX       CfprApManagedObjectDn
    MAX-ACCESS   read-only
    STATUS       current
    DESCRIPTION
        "Cisco Firepower aaa:EpUser:dn managed object property"
    ::= { cfprApAaaEpUserEntry 2 }

cfprApAaaEpUserRn OBJECT-TYPE
    SYNTAX       SnmpAdminString
    MAX-ACCESS   read-only
    STATUS       current
    DESCRIPTION
        "Cisco Firepower aaa:EpUser:rn managed object property"
    ::= { cfprApAaaEpUserEntry 3 }

cfprApAaaEpUserConfigState OBJECT-TYPE
    SYNTAX       CfprApAaaConfigState
    MAX-ACCESS   read-only
    STATUS       current
    DESCRIPTION
        "Cisco Firepower aaa:EpUser:configState managed object property"
    ::= { cfprApAaaEpUserEntry 4 }

cfprApAaaEpUserConfigStatusMessage OBJECT-TYPE
    SYNTAX       SnmpAdminString
    MAX-ACCESS   read-only
    STATUS       current
    DESCRIPTION
        "Cisco Firepower aaa:EpUser:configStatusMessage
        managed object property"
    ::= { cfprApAaaEpUserEntry 5 }

cfprApAaaEpUserDescr OBJECT-TYPE
    SYNTAX       SnmpAdminString
    MAX-ACCESS   read-only
    STATUS       current
    DESCRIPTION
        "Cisco Firepower aaa:EpUser:descr managed object property"
    ::= { cfprApAaaEpUserEntry 6 }

cfprApAaaEpUserName OBJECT-TYPE
    SYNTAX       SnmpAdminString
    MAX-ACCESS   read-only
    STATUS       current
    DESCRIPTION
        "Cisco Firepower aaa:EpUser:name managed object property"
    ::= { cfprApAaaEpUserEntry 7 }

cfprApAaaEpUserPriv OBJECT-TYPE
    SYNTAX       CfprApAaaEpAccess
    MAX-ACCESS   read-only
    STATUS       current
    DESCRIPTION
        "Cisco Firepower aaa:EpUser:priv managed object property"
    ::= { cfprApAaaEpUserEntry 8 }

cfprApAaaEpUserPwd OBJECT-TYPE
    SYNTAX       SnmpAdminString
    MAX-ACCESS   read-only
    STATUS       current
    DESCRIPTION
        "Cisco Firepower aaa:EpUser:pwd managed object property"
    ::= { cfprApAaaEpUserEntry 9 }

cfprApAaaEpUserPwdSet OBJECT-TYPE
    SYNTAX       TruthValue
    MAX-ACCESS   read-only
    STATUS       current
    DESCRIPTION
        "Cisco Firepower aaa:EpUser:pwdSet managed object property"
    ::= { cfprApAaaEpUserEntry 10 }

cfprApAaaExtMgmtCutThruTknTable OBJECT-TYPE
    SYNTAX           SEQUENCE OF CfprApAaaExtMgmtCutThruTknEntry
    MAX-ACCESS       not-accessible
    STATUS           current
    DESCRIPTION
        "Cisco Firepower aaa:ExtMgmtCutThruTkn managed object table"
    ::= { cfprApAaaObjects 15 }

cfprApAaaExtMgmtCutThruTknEntry OBJECT-TYPE
    SYNTAX           CfprApAaaExtMgmtCutThruTknEntry
    MAX-ACCESS       not-accessible
    STATUS           current
    DESCRIPTION
        "Entry for the cfprApAaaExtMgmtCutThruTknTable table."
    INDEX { cfprApAaaExtMgmtCutThruTknInstanceId }
    ::= { cfprApAaaExtMgmtCutThruTknTable 1 }

CfprApAaaExtMgmtCutThruTknEntry ::= SEQUENCE {
    cfprApAaaExtMgmtCutThruTknInstanceId                             CfprApManagedObjectId,
    cfprApAaaExtMgmtCutThruTknDn                                     CfprApManagedObjectDn,
    cfprApAaaExtMgmtCutThruTknRn                                     SnmpAdminString,
    cfprApAaaExtMgmtCutThruTknAuthDomain                             SnmpAdminString,
    cfprApAaaExtMgmtCutThruTknAuthUser                               SnmpAdminString,
    cfprApAaaExtMgmtCutThruTknCreationTime                           DateAndTime,
    cfprApAaaExtMgmtCutThruTknDescr                                  SnmpAdminString,
    cfprApAaaExtMgmtCutThruTknIntId                                  SnmpAdminString,
    cfprApAaaExtMgmtCutThruTknLocales                                SnmpAdminString,
    cfprApAaaExtMgmtCutThruTknName                                   SnmpAdminString,
    cfprApAaaExtMgmtCutThruTknPnDn                                   SnmpAdminString,
    cfprApAaaExtMgmtCutThruTknPolicyLevel                            Gauge32,
    cfprApAaaExtMgmtCutThruTknPolicyOwner                            CfprApPolicyPolicyOwner,
    cfprApAaaExtMgmtCutThruTknPriv                                   CfprApAaaAccess,
    cfprApAaaExtMgmtCutThruTknRemote                                 TruthValue,
    cfprApAaaExtMgmtCutThruTknToken                                  SnmpAdminString,
    cfprApAaaExtMgmtCutThruTknType                                   CfprApAaaExtMgmtAccess,
    cfprApAaaExtMgmtCutThruTknUser                                   SnmpAdminString
}

cfprApAaaExtMgmtCutThruTknInstanceId OBJECT-TYPE
    SYNTAX       CfprApManagedObjectId
    MAX-ACCESS   not-accessible
    STATUS       current
    DESCRIPTION
        "Instance identifier of the managed object."
    ::= { cfprApAaaExtMgmtCutThruTknEntry 1 }

cfprApAaaExtMgmtCutThruTknDn OBJECT-TYPE
    SYNTAX       CfprApManagedObjectDn
    MAX-ACCESS   read-only
    STATUS       current
    DESCRIPTION
        "Cisco Firepower aaa:ExtMgmtCutThruTkn:dn managed object property"
    ::= { cfprApAaaExtMgmtCutThruTknEntry 2 }

cfprApAaaExtMgmtCutThruTknRn OBJECT-TYPE
    SYNTAX       SnmpAdminString
    MAX-ACCESS   read-only
    STATUS       current
    DESCRIPTION
        "Cisco Firepower aaa:ExtMgmtCutThruTkn:rn managed object property"
    ::= { cfprApAaaExtMgmtCutThruTknEntry 3 }

cfprApAaaExtMgmtCutThruTknAuthDomain OBJECT-TYPE
    SYNTAX       SnmpAdminString
    MAX-ACCESS   read-only
    STATUS       current
    DESCRIPTION
        "Cisco Firepower aaa:ExtMgmtCutThruTkn:authDomain
        managed object property"
    ::= { cfprApAaaExtMgmtCutThruTknEntry 4 }

cfprApAaaExtMgmtCutThruTknAuthUser OBJECT-TYPE
    SYNTAX       SnmpAdminString
    MAX-ACCESS   read-only
    STATUS       current
    DESCRIPTION
        "Cisco Firepower aaa:ExtMgmtCutThruTkn:authUser
        managed object property"
    ::= { cfprApAaaExtMgmtCutThruTknEntry 5 }

cfprApAaaExtMgmtCutThruTknCreationTime OBJECT-TYPE
    SYNTAX       DateAndTime
    MAX-ACCESS   read-only
    STATUS       current
    DESCRIPTION
        "Cisco Firepower aaa:ExtMgmtCutThruTkn:creationTime
        managed object property"
    ::= { cfprApAaaExtMgmtCutThruTknEntry 6 }

cfprApAaaExtMgmtCutThruTknDescr OBJECT-TYPE
    SYNTAX       SnmpAdminString
    MAX-ACCESS   read-only
    STATUS       current
    DESCRIPTION
        "Cisco Firepower aaa:ExtMgmtCutThruTkn:descr managed
        object property"
    ::= { cfprApAaaExtMgmtCutThruTknEntry 7 }

cfprApAaaExtMgmtCutThruTknIntId OBJECT-TYPE
    SYNTAX       SnmpAdminString
    MAX-ACCESS   read-only
    STATUS       current
    DESCRIPTION
        "Cisco Firepower aaa:ExtMgmtCutThruTkn:intId managed
        object property"
    ::= { cfprApAaaExtMgmtCutThruTknEntry 8 }

cfprApAaaExtMgmtCutThruTknLocales OBJECT-TYPE
    SYNTAX       SnmpAdminString
    MAX-ACCESS   read-only
    STATUS       current
    DESCRIPTION
        "Cisco Firepower aaa:ExtMgmtCutThruTkn:locales
        managed object property"
    ::= { cfprApAaaExtMgmtCutThruTknEntry 9 }

cfprApAaaExtMgmtCutThruTknName OBJECT-TYPE
    SYNTAX       SnmpAdminString
    MAX-ACCESS   read-only
    STATUS       current
    DESCRIPTION
        "Cisco Firepower aaa:ExtMgmtCutThruTkn:name managed
        object property"
    ::= { cfprApAaaExtMgmtCutThruTknEntry 10 }

cfprApAaaExtMgmtCutThruTknPnDn OBJECT-TYPE
    SYNTAX       SnmpAdminString
    MAX-ACCESS   read-only
    STATUS       current
    DESCRIPTION
        "Cisco Firepower aaa:ExtMgmtCutThruTkn:pnDn managed
        object property"
    ::= { cfprApAaaExtMgmtCutThruTknEntry 11 }

cfprApAaaExtMgmtCutThruTknPolicyLevel OBJECT-TYPE
    SYNTAX       Gauge32
    MAX-ACCESS   read-only
    STATUS       current
    DESCRIPTION
        "Cisco Firepower aaa:ExtMgmtCutThruTkn:policyLevel
        managed object property"
    ::= { cfprApAaaExtMgmtCutThruTknEntry 12 }

cfprApAaaExtMgmtCutThruTknPolicyOwner OBJECT-TYPE
    SYNTAX       CfprApPolicyPolicyOwner
    MAX-ACCESS   read-only
    STATUS       current
    DESCRIPTION
        "Cisco Firepower aaa:ExtMgmtCutThruTkn:policyOwner
        managed object property"
    ::= { cfprApAaaExtMgmtCutThruTknEntry 13 }

cfprApAaaExtMgmtCutThruTknPriv OBJECT-TYPE
    SYNTAX       CfprApAaaAccess
    MAX-ACCESS   read-only
    STATUS       current
    DESCRIPTION
        "Cisco Firepower aaa:ExtMgmtCutThruTkn:priv managed
        object property"
    ::= { cfprApAaaExtMgmtCutThruTknEntry 14 }

cfprApAaaExtMgmtCutThruTknRemote OBJECT-TYPE
    SYNTAX       TruthValue
    MAX-ACCESS   read-only
    STATUS       current
    DESCRIPTION
        "Cisco Firepower aaa:ExtMgmtCutThruTkn:remote managed
        object property"
    ::= { cfprApAaaExtMgmtCutThruTknEntry 15 }

cfprApAaaExtMgmtCutThruTknToken OBJECT-TYPE
    SYNTAX       SnmpAdminString
    MAX-ACCESS   read-only
    STATUS       current
    DESCRIPTION
        "Cisco Firepower aaa:ExtMgmtCutThruTkn:token managed
        object property"
    ::= { cfprApAaaExtMgmtCutThruTknEntry 16 }

cfprApAaaExtMgmtCutThruTknType OBJECT-TYPE
    SYNTAX       CfprApAaaExtMgmtAccess
    MAX-ACCESS   read-only
    STATUS       current
    DESCRIPTION
        "Cisco Firepower aaa:ExtMgmtCutThruTkn:type managed
        object property"
    ::= { cfprApAaaExtMgmtCutThruTknEntry 17 }

cfprApAaaExtMgmtCutThruTknUser OBJECT-TYPE
    SYNTAX       SnmpAdminString
    MAX-ACCESS   read-only
    STATUS       current
    DESCRIPTION
        "Cisco Firepower aaa:ExtMgmtCutThruTkn:user managed
        object property"
    ::= { cfprApAaaExtMgmtCutThruTknEntry 18 }

cfprApAaaLdapEpTable OBJECT-TYPE
    SYNTAX           SEQUENCE OF CfprApAaaLdapEpEntry
    MAX-ACCESS       not-accessible
    STATUS           current
    DESCRIPTION
        "Cisco Firepower aaa:LdapEp managed object table"
    ::= { cfprApAaaObjects 16 }

cfprApAaaLdapEpEntry OBJECT-TYPE
    SYNTAX           CfprApAaaLdapEpEntry
    MAX-ACCESS       not-accessible
    STATUS           current
    DESCRIPTION
        "Entry for the cfprApAaaLdapEpTable table."
    INDEX { cfprApAaaLdapEpInstanceId }
    ::= { cfprApAaaLdapEpTable 1 }

CfprApAaaLdapEpEntry ::= SEQUENCE {
    cfprApAaaLdapEpInstanceId                                        CfprApManagedObjectId,
    cfprApAaaLdapEpDn                                                CfprApManagedObjectDn,
    cfprApAaaLdapEpRn                                                SnmpAdminString,
    cfprApAaaLdapEpAttribute                                         SnmpAdminString,
    cfprApAaaLdapEpBasedn                                            SnmpAdminString,
    cfprApAaaLdapEpDescr                                             SnmpAdminString,
    cfprApAaaLdapEpFilter                                            SnmpAdminString,
    cfprApAaaLdapEpFsmDescr                                          SnmpAdminString,
    cfprApAaaLdapEpFsmPrev                                           SnmpAdminString,
    cfprApAaaLdapEpFsmProgr                                          Gauge32,
    cfprApAaaLdapEpFsmRmtInvErrCode                                  Gauge32,
    cfprApAaaLdapEpFsmRmtInvErrDescr                                 SnmpAdminString,
    cfprApAaaLdapEpFsmRmtInvRslt                                     CfprApConditionRemoteInvRslt,
    cfprApAaaLdapEpFsmStageDescr                                     SnmpAdminString,
    cfprApAaaLdapEpFsmStamp                                          DateAndTime,
    cfprApAaaLdapEpFsmStatus                                         SnmpAdminString,
    cfprApAaaLdapEpFsmTry                                            Gauge32,
    cfprApAaaLdapEpIntId                                             SnmpAdminString,
    cfprApAaaLdapEpName                                              SnmpAdminString,
    cfprApAaaLdapEpPolicyLevel                                       Gauge32,
    cfprApAaaLdapEpPolicyOwner                                       CfprApPolicyPolicyOwner,
    cfprApAaaLdapEpRetries                                           Gauge32,
    cfprApAaaLdapEpTimeout                                           Gauge32
}

cfprApAaaLdapEpInstanceId OBJECT-TYPE
    SYNTAX       CfprApManagedObjectId
    MAX-ACCESS   not-accessible
    STATUS       current
    DESCRIPTION
        "Instance identifier of the managed object."
    ::= { cfprApAaaLdapEpEntry 1 }

cfprApAaaLdapEpDn OBJECT-TYPE
    SYNTAX       CfprApManagedObjectDn
    MAX-ACCESS   read-only
    STATUS       current
    DESCRIPTION
        "Cisco Firepower aaa:LdapEp:dn managed object property"
    ::= { cfprApAaaLdapEpEntry 2 }

cfprApAaaLdapEpRn OBJECT-TYPE
    SYNTAX       SnmpAdminString
    MAX-ACCESS   read-only
    STATUS       current
    DESCRIPTION
        "Cisco Firepower aaa:LdapEp:rn managed object property"
    ::= { cfprApAaaLdapEpEntry 3 }

cfprApAaaLdapEpAttribute OBJECT-TYPE
    SYNTAX       SnmpAdminString
    MAX-ACCESS   read-only
    STATUS       current
    DESCRIPTION
        "Cisco Firepower aaa:LdapEp:attribute managed object property"
    ::= { cfprApAaaLdapEpEntry 4 }

cfprApAaaLdapEpBasedn OBJECT-TYPE
    SYNTAX       SnmpAdminString
    MAX-ACCESS   read-only
    STATUS       current
    DESCRIPTION
        "Cisco Firepower aaa:LdapEp:basedn managed object property"
    ::= { cfprApAaaLdapEpEntry 5 }

cfprApAaaLdapEpDescr OBJECT-TYPE
    SYNTAX       SnmpAdminString
    MAX-ACCESS   read-only
    STATUS       current
    DESCRIPTION
        "Cisco Firepower aaa:LdapEp:descr managed object property"
    ::= { cfprApAaaLdapEpEntry 6 }

cfprApAaaLdapEpFilter OBJECT-TYPE
    SYNTAX       SnmpAdminString
    MAX-ACCESS   read-only
    STATUS       current
    DESCRIPTION
        "Cisco Firepower aaa:LdapEp:filter managed object property"
    ::= { cfprApAaaLdapEpEntry 7 }

cfprApAaaLdapEpFsmDescr OBJECT-TYPE
    SYNTAX       SnmpAdminString
    MAX-ACCESS   read-only
    STATUS       current
    DESCRIPTION
        "Cisco Firepower aaa:LdapEp:fsmDescr managed object property"
    ::= { cfprApAaaLdapEpEntry 8 }

cfprApAaaLdapEpFsmPrev OBJECT-TYPE
    SYNTAX       SnmpAdminString
    MAX-ACCESS   read-only
    STATUS       current
    DESCRIPTION
        "Cisco Firepower aaa:LdapEp:fsmPrev managed object property"
    ::= { cfprApAaaLdapEpEntry 9 }

cfprApAaaLdapEpFsmProgr OBJECT-TYPE
    SYNTAX       Gauge32
    MAX-ACCESS   read-only
    STATUS       current
    DESCRIPTION
        "Cisco Firepower aaa:LdapEp:fsmProgr managed object property"
    ::= { cfprApAaaLdapEpEntry 10 }

cfprApAaaLdapEpFsmRmtInvErrCode OBJECT-TYPE
    SYNTAX       Gauge32
    MAX-ACCESS   read-only
    STATUS       current
    DESCRIPTION
        "Cisco Firepower aaa:LdapEp:fsmRmtInvErrCode managed
        object property"
    ::= { cfprApAaaLdapEpEntry 11 }

cfprApAaaLdapEpFsmRmtInvErrDescr OBJECT-TYPE
    SYNTAX       SnmpAdminString
    MAX-ACCESS   read-only
    STATUS       current
    DESCRIPTION
        "Cisco Firepower aaa:LdapEp:fsmRmtInvErrDescr managed
        object property"
    ::= { cfprApAaaLdapEpEntry 12 }

cfprApAaaLdapEpFsmRmtInvRslt OBJECT-TYPE
    SYNTAX       CfprApConditionRemoteInvRslt
    MAX-ACCESS   read-only
    STATUS       current
    DESCRIPTION
        "Cisco Firepower aaa:LdapEp:fsmRmtInvRslt managed object property"
    ::= { cfprApAaaLdapEpEntry 13 }

cfprApAaaLdapEpFsmStageDescr OBJECT-TYPE
    SYNTAX       SnmpAdminString
    MAX-ACCESS   read-only
    STATUS       current
    DESCRIPTION
        "Cisco Firepower aaa:LdapEp:fsmStageDescr managed object property"
    ::= { cfprApAaaLdapEpEntry 14 }

cfprApAaaLdapEpFsmStamp OBJECT-TYPE
    SYNTAX       DateAndTime
    MAX-ACCESS   read-only
    STATUS       current
    DESCRIPTION
        "Cisco Firepower aaa:LdapEp:fsmStamp managed object property"
    ::= { cfprApAaaLdapEpEntry 15 }

cfprApAaaLdapEpFsmStatus OBJECT-TYPE
    SYNTAX       SnmpAdminString
    MAX-ACCESS   read-only
    STATUS       current
    DESCRIPTION
        "Cisco Firepower aaa:LdapEp:fsmStatus managed object property"
    ::= { cfprApAaaLdapEpEntry 16 }

cfprApAaaLdapEpFsmTry OBJECT-TYPE
    SYNTAX       Gauge32
    MAX-ACCESS   read-only
    STATUS       current
    DESCRIPTION
        "Cisco Firepower aaa:LdapEp:fsmTry managed object property"
    ::= { cfprApAaaLdapEpEntry 17 }

cfprApAaaLdapEpIntId OBJECT-TYPE
    SYNTAX       SnmpAdminString
    MAX-ACCESS   read-only
    STATUS       current
    DESCRIPTION
        "Cisco Firepower aaa:LdapEp:intId managed object property"
    ::= { cfprApAaaLdapEpEntry 18 }

cfprApAaaLdapEpName OBJECT-TYPE
    SYNTAX       SnmpAdminString
    MAX-ACCESS   read-only
    STATUS       current
    DESCRIPTION
        "Cisco Firepower aaa:LdapEp:name managed object property"
    ::= { cfprApAaaLdapEpEntry 19 }

cfprApAaaLdapEpPolicyLevel OBJECT-TYPE
    SYNTAX       Gauge32
    MAX-ACCESS   read-only
    STATUS       current
    DESCRIPTION
        "Cisco Firepower aaa:LdapEp:policyLevel managed object property"
    ::= { cfprApAaaLdapEpEntry 20 }

cfprApAaaLdapEpPolicyOwner OBJECT-TYPE
    SYNTAX       CfprApPolicyPolicyOwner
    MAX-ACCESS   read-only
    STATUS       current
    DESCRIPTION
        "Cisco Firepower aaa:LdapEp:policyOwner managed object property"
    ::= { cfprApAaaLdapEpEntry 21 }

cfprApAaaLdapEpRetries OBJECT-TYPE
    SYNTAX       Gauge32
    MAX-ACCESS   read-only
    STATUS       current
    DESCRIPTION
        "Cisco Firepower aaa:LdapEp:retries managed object property"
    ::= { cfprApAaaLdapEpEntry 22 }

cfprApAaaLdapEpTimeout OBJECT-TYPE
    SYNTAX       Gauge32
    MAX-ACCESS   read-only
    STATUS       current
    DESCRIPTION
        "Cisco Firepower aaa:LdapEp:timeout managed object property"
    ::= { cfprApAaaLdapEpEntry 23 }

cfprApAaaLdapEpFsmTable OBJECT-TYPE
    SYNTAX           SEQUENCE OF CfprApAaaLdapEpFsmEntry
    MAX-ACCESS       not-accessible
    STATUS           current
    DESCRIPTION
        "Cisco Firepower aaa:LdapEpFsm managed object table"
    ::= { cfprApAaaObjects 17 }

cfprApAaaLdapEpFsmEntry OBJECT-TYPE
    SYNTAX           CfprApAaaLdapEpFsmEntry
    MAX-ACCESS       not-accessible
    STATUS           current
    DESCRIPTION
        "Entry for the cfprApAaaLdapEpFsmTable table."
    INDEX { cfprApAaaLdapEpFsmInstanceId }
    ::= { cfprApAaaLdapEpFsmTable 1 }

CfprApAaaLdapEpFsmEntry ::= SEQUENCE {
    cfprApAaaLdapEpFsmInstanceId                                     CfprApManagedObjectId,
    cfprApAaaLdapEpFsmDn                                             CfprApManagedObjectDn,
    cfprApAaaLdapEpFsmRn                                             SnmpAdminString,
    cfprApAaaLdapEpFsmCompletionTime                                 DateAndTime,
    cfprApAaaLdapEpFsmCurrentFsm                                     CfprApAaaLdapEpFsmCurrentFsm,
    cfprApAaaLdapEpFsmDescrData                                      SnmpAdminString,
    cfprApAaaLdapEpFsmFsmStatus                                      CfprApFsmFsmStageStatus,
    cfprApAaaLdapEpFsmProgress                                       Gauge32,
    cfprApAaaLdapEpFsmRmtErrCode                                     Gauge32,
    cfprApAaaLdapEpFsmRmtErrDescr                                    SnmpAdminString,
    cfprApAaaLdapEpFsmRmtRslt                                        CfprApConditionRemoteInvRslt
}

cfprApAaaLdapEpFsmInstanceId OBJECT-TYPE
    SYNTAX       CfprApManagedObjectId
    MAX-ACCESS   not-accessible
    STATUS       current
    DESCRIPTION
        "Instance identifier of the managed object."
    ::= { cfprApAaaLdapEpFsmEntry 1 }

cfprApAaaLdapEpFsmDn OBJECT-TYPE
    SYNTAX       CfprApManagedObjectDn
    MAX-ACCESS   read-only
    STATUS       current
    DESCRIPTION
        "Cisco Firepower aaa:LdapEpFsm:dn managed object property"
    ::= { cfprApAaaLdapEpFsmEntry 2 }

cfprApAaaLdapEpFsmRn OBJECT-TYPE
    SYNTAX       SnmpAdminString
    MAX-ACCESS   read-only
    STATUS       current
    DESCRIPTION
        "Cisco Firepower aaa:LdapEpFsm:rn managed object property"
    ::= { cfprApAaaLdapEpFsmEntry 3 }

cfprApAaaLdapEpFsmCompletionTime OBJECT-TYPE
    SYNTAX       DateAndTime
    MAX-ACCESS   read-only
    STATUS       current
    DESCRIPTION
        "Cisco Firepower aaa:LdapEpFsm:completionTime managed
        object property"
    ::= { cfprApAaaLdapEpFsmEntry 4 }

cfprApAaaLdapEpFsmCurrentFsm OBJECT-TYPE
    SYNTAX       CfprApAaaLdapEpFsmCurrentFsm
    MAX-ACCESS   read-only
    STATUS       current
    DESCRIPTION
        "Cisco Firepower aaa:LdapEpFsm:currentFsm managed object property"
    ::= { cfprApAaaLdapEpFsmEntry 5 }

cfprApAaaLdapEpFsmDescrData OBJECT-TYPE
    SYNTAX       SnmpAdminString
    MAX-ACCESS   read-only
    STATUS       current
    DESCRIPTION
        "Cisco Firepower aaa:LdapEpFsm:descr managed object property"
    ::= { cfprApAaaLdapEpFsmEntry 6 }

cfprApAaaLdapEpFsmFsmStatus OBJECT-TYPE
    SYNTAX       CfprApFsmFsmStageStatus
    MAX-ACCESS   read-only
    STATUS       current
    DESCRIPTION
        "Cisco Firepower aaa:LdapEpFsm:fsmStatus managed object property"
    ::= { cfprApAaaLdapEpFsmEntry 7 }

cfprApAaaLdapEpFsmProgress OBJECT-TYPE
    SYNTAX       Gauge32
    MAX-ACCESS   read-only
    STATUS       current
    DESCRIPTION
        "Cisco Firepower aaa:LdapEpFsm:progress managed object property"
    ::= { cfprApAaaLdapEpFsmEntry 8 }

cfprApAaaLdapEpFsmRmtErrCode OBJECT-TYPE
    SYNTAX       Gauge32
    MAX-ACCESS   read-only
    STATUS       current
    DESCRIPTION
        "Cisco Firepower aaa:LdapEpFsm:rmtErrCode managed object property"
    ::= { cfprApAaaLdapEpFsmEntry 9 }

cfprApAaaLdapEpFsmRmtErrDescr OBJECT-TYPE
    SYNTAX       SnmpAdminString
    MAX-ACCESS   read-only
    STATUS       current
    DESCRIPTION
        "Cisco Firepower aaa:LdapEpFsm:rmtErrDescr managed
        object property"
    ::= { cfprApAaaLdapEpFsmEntry 10 }

cfprApAaaLdapEpFsmRmtRslt OBJECT-TYPE
    SYNTAX       CfprApConditionRemoteInvRslt
    MAX-ACCESS   read-only
    STATUS       current
    DESCRIPTION
        "Cisco Firepower aaa:LdapEpFsm:rmtRslt managed object property"
    ::= { cfprApAaaLdapEpFsmEntry 11 }

cfprApAaaLdapEpFsmStageTable OBJECT-TYPE
    SYNTAX           SEQUENCE OF CfprApAaaLdapEpFsmStageEntry
    MAX-ACCESS       not-accessible
    STATUS           current
    DESCRIPTION
        "Cisco Firepower aaa:LdapEpFsmStage managed object table"
    ::= { cfprApAaaObjects 18 }

cfprApAaaLdapEpFsmStageEntry OBJECT-TYPE
    SYNTAX           CfprApAaaLdapEpFsmStageEntry
    MAX-ACCESS       not-accessible
    STATUS           current
    DESCRIPTION
        "Entry for the cfprApAaaLdapEpFsmStageTable table."
    INDEX { cfprApAaaLdapEpFsmStageInstanceId }
    ::= { cfprApAaaLdapEpFsmStageTable 1 }

CfprApAaaLdapEpFsmStageEntry ::= SEQUENCE {
    cfprApAaaLdapEpFsmStageInstanceId                                CfprApManagedObjectId,
    cfprApAaaLdapEpFsmStageDn                                        CfprApManagedObjectDn,
    cfprApAaaLdapEpFsmStageRn                                        SnmpAdminString,
    cfprApAaaLdapEpFsmStageDescrData                                 SnmpAdminString,
    cfprApAaaLdapEpFsmStageLastUpdateTime                            DateAndTime,
    cfprApAaaLdapEpFsmStageName                                      CfprApAaaLdapEpFsmStageName,
    cfprApAaaLdapEpFsmStageOrder                                     Gauge32,
    cfprApAaaLdapEpFsmStageRetry                                     Gauge32,
    cfprApAaaLdapEpFsmStageStageStatus                               CfprApFsmFsmStageStatus
}

cfprApAaaLdapEpFsmStageInstanceId OBJECT-TYPE
    SYNTAX       CfprApManagedObjectId
    MAX-ACCESS   not-accessible
    STATUS       current
    DESCRIPTION
        "Instance identifier of the managed object."
    ::= { cfprApAaaLdapEpFsmStageEntry 1 }

cfprApAaaLdapEpFsmStageDn OBJECT-TYPE
    SYNTAX       CfprApManagedObjectDn
    MAX-ACCESS   read-only
    STATUS       current
    DESCRIPTION
        "Cisco Firepower aaa:LdapEpFsmStage:dn managed object property"
    ::= { cfprApAaaLdapEpFsmStageEntry 2 }

cfprApAaaLdapEpFsmStageRn OBJECT-TYPE
    SYNTAX       SnmpAdminString
    MAX-ACCESS   read-only
    STATUS       current
    DESCRIPTION
        "Cisco Firepower aaa:LdapEpFsmStage:rn managed object property"
    ::= { cfprApAaaLdapEpFsmStageEntry 3 }

cfprApAaaLdapEpFsmStageDescrData OBJECT-TYPE
    SYNTAX       SnmpAdminString
    MAX-ACCESS   read-only
    STATUS       current
    DESCRIPTION
        "Cisco Firepower aaa:LdapEpFsmStage:descr managed object property"
    ::= { cfprApAaaLdapEpFsmStageEntry 4 }

cfprApAaaLdapEpFsmStageLastUpdateTime OBJECT-TYPE
    SYNTAX       DateAndTime
    MAX-ACCESS   read-only
    STATUS       current
    DESCRIPTION
        "Cisco Firepower aaa:LdapEpFsmStage:lastUpdateTime
        managed object property"
    ::= { cfprApAaaLdapEpFsmStageEntry 5 }

cfprApAaaLdapEpFsmStageName OBJECT-TYPE
    SYNTAX       CfprApAaaLdapEpFsmStageName
    MAX-ACCESS   read-only
    STATUS       current
    DESCRIPTION
        "Cisco Firepower aaa:LdapEpFsmStage:name managed object property"
    ::= { cfprApAaaLdapEpFsmStageEntry 6 }

cfprApAaaLdapEpFsmStageOrder OBJECT-TYPE
    SYNTAX       Gauge32
    MAX-ACCESS   read-only
    STATUS       current
    DESCRIPTION
        "Cisco Firepower aaa:LdapEpFsmStage:order managed object property"
    ::= { cfprApAaaLdapEpFsmStageEntry 7 }

cfprApAaaLdapEpFsmStageRetry OBJECT-TYPE
    SYNTAX       Gauge32
    MAX-ACCESS   read-only
    STATUS       current
    DESCRIPTION
        "Cisco Firepower aaa:LdapEpFsmStage:retry managed object property"
    ::= { cfprApAaaLdapEpFsmStageEntry 8 }

cfprApAaaLdapEpFsmStageStageStatus OBJECT-TYPE
    SYNTAX       CfprApFsmFsmStageStatus
    MAX-ACCESS   read-only
    STATUS       current
    DESCRIPTION
        "Cisco Firepower aaa:LdapEpFsmStage:stageStatus
        managed object property"
    ::= { cfprApAaaLdapEpFsmStageEntry 9 }

cfprApAaaLdapGroupTable OBJECT-TYPE
    SYNTAX           SEQUENCE OF CfprApAaaLdapGroupEntry
    MAX-ACCESS       not-accessible
    STATUS           current
    DESCRIPTION
        "Cisco Firepower aaa:LdapGroup managed object table"
    ::= { cfprApAaaObjects 19 }

cfprApAaaLdapGroupEntry OBJECT-TYPE
    SYNTAX           CfprApAaaLdapGroupEntry
    MAX-ACCESS       not-accessible
    STATUS           current
    DESCRIPTION
        "Entry for the cfprApAaaLdapGroupTable table."
    INDEX { cfprApAaaLdapGroupInstanceId }
    ::= { cfprApAaaLdapGroupTable 1 }

CfprApAaaLdapGroupEntry ::= SEQUENCE {
    cfprApAaaLdapGroupInstanceId                                     CfprApManagedObjectId,
    cfprApAaaLdapGroupDn                                             CfprApManagedObjectDn,
    cfprApAaaLdapGroupRn                                             SnmpAdminString,
    cfprApAaaLdapGroupDescr                                          SnmpAdminString,
    cfprApAaaLdapGroupName                                           SnmpAdminString
}

cfprApAaaLdapGroupInstanceId OBJECT-TYPE
    SYNTAX       CfprApManagedObjectId
    MAX-ACCESS   not-accessible
    STATUS       current
    DESCRIPTION
        "Instance identifier of the managed object."
    ::= { cfprApAaaLdapGroupEntry 1 }

cfprApAaaLdapGroupDn OBJECT-TYPE
    SYNTAX       CfprApManagedObjectDn
    MAX-ACCESS   read-only
    STATUS       current
    DESCRIPTION
        "Cisco Firepower aaa:LdapGroup:dn managed object property"
    ::= { cfprApAaaLdapGroupEntry 2 }

cfprApAaaLdapGroupRn OBJECT-TYPE
    SYNTAX       SnmpAdminString
    MAX-ACCESS   read-only
    STATUS       current
    DESCRIPTION
        "Cisco Firepower aaa:LdapGroup:rn managed object property"
    ::= { cfprApAaaLdapGroupEntry 3 }

cfprApAaaLdapGroupDescr OBJECT-TYPE
    SYNTAX       SnmpAdminString
    MAX-ACCESS   read-only
    STATUS       current
    DESCRIPTION
        "Cisco Firepower aaa:LdapGroup:descr managed object property"
    ::= { cfprApAaaLdapGroupEntry 4 }

cfprApAaaLdapGroupName OBJECT-TYPE
    SYNTAX       SnmpAdminString
    MAX-ACCESS   read-only
    STATUS       current
    DESCRIPTION
        "Cisco Firepower aaa:LdapGroup:name managed object property"
    ::= { cfprApAaaLdapGroupEntry 5 }

cfprApAaaLdapGroupRuleTable OBJECT-TYPE
    SYNTAX           SEQUENCE OF CfprApAaaLdapGroupRuleEntry
    MAX-ACCESS       not-accessible
    STATUS           current
    DESCRIPTION
        "Cisco Firepower aaa:LdapGroupRule managed object table"
    ::= { cfprApAaaObjects 20 }

cfprApAaaLdapGroupRuleEntry OBJECT-TYPE
    SYNTAX           CfprApAaaLdapGroupRuleEntry
    MAX-ACCESS       not-accessible
    STATUS           current
    DESCRIPTION
        "Entry for the cfprApAaaLdapGroupRuleTable table."
    INDEX { cfprApAaaLdapGroupRuleInstanceId }
    ::= { cfprApAaaLdapGroupRuleTable 1 }

CfprApAaaLdapGroupRuleEntry ::= SEQUENCE {
    cfprApAaaLdapGroupRuleInstanceId                                 CfprApManagedObjectId,
    cfprApAaaLdapGroupRuleDn                                         CfprApManagedObjectDn,
    cfprApAaaLdapGroupRuleRn                                         SnmpAdminString,
    cfprApAaaLdapGroupRuleAuthorization                              CfprApAaaLdapGroupRuleAuthorization,
    cfprApAaaLdapGroupRuleDescr                                      SnmpAdminString,
    cfprApAaaLdapGroupRuleName                                       SnmpAdminString,
    cfprApAaaLdapGroupRuleTargetAttr                                 SnmpAdminString,
    cfprApAaaLdapGroupRuleTraversal                                  CfprApAaaLdapGroupRuleTraversal,
    cfprApAaaLdapGroupRuleUsePrimaryGroup                            TruthValue
}

cfprApAaaLdapGroupRuleInstanceId OBJECT-TYPE
    SYNTAX       CfprApManagedObjectId
    MAX-ACCESS   not-accessible
    STATUS       current
    DESCRIPTION
        "Instance identifier of the managed object."
    ::= { cfprApAaaLdapGroupRuleEntry 1 }

cfprApAaaLdapGroupRuleDn OBJECT-TYPE
    SYNTAX       CfprApManagedObjectDn
    MAX-ACCESS   read-only
    STATUS       current
    DESCRIPTION
        "Cisco Firepower aaa:LdapGroupRule:dn managed object property"
    ::= { cfprApAaaLdapGroupRuleEntry 2 }

cfprApAaaLdapGroupRuleRn OBJECT-TYPE
    SYNTAX       SnmpAdminString
    MAX-ACCESS   read-only
    STATUS       current
    DESCRIPTION
        "Cisco Firepower aaa:LdapGroupRule:rn managed object property"
    ::= { cfprApAaaLdapGroupRuleEntry 3 }

cfprApAaaLdapGroupRuleAuthorization OBJECT-TYPE
    SYNTAX       CfprApAaaLdapGroupRuleAuthorization
    MAX-ACCESS   read-only
    STATUS       current
    DESCRIPTION
        "Cisco Firepower aaa:LdapGroupRule:authorization
        managed object property"
    ::= { cfprApAaaLdapGroupRuleEntry 4 }

cfprApAaaLdapGroupRuleDescr OBJECT-TYPE
    SYNTAX       SnmpAdminString
    MAX-ACCESS   read-only
    STATUS       current
    DESCRIPTION
        "Cisco Firepower aaa:LdapGroupRule:descr managed object property"
    ::= { cfprApAaaLdapGroupRuleEntry 5 }

cfprApAaaLdapGroupRuleName OBJECT-TYPE
    SYNTAX       SnmpAdminString
    MAX-ACCESS   read-only
    STATUS       current
    DESCRIPTION
        "Cisco Firepower aaa:LdapGroupRule:name managed object property"
    ::= { cfprApAaaLdapGroupRuleEntry 6 }

cfprApAaaLdapGroupRuleTargetAttr OBJECT-TYPE
    SYNTAX       SnmpAdminString
    MAX-ACCESS   read-only
    STATUS       current
    DESCRIPTION
        "Cisco Firepower aaa:LdapGroupRule:targetAttr managed
        object property"
    ::= { cfprApAaaLdapGroupRuleEntry 7 }

cfprApAaaLdapGroupRuleTraversal OBJECT-TYPE
    SYNTAX       CfprApAaaLdapGroupRuleTraversal
    MAX-ACCESS   read-only
    STATUS       current
    DESCRIPTION
        "Cisco Firepower aaa:LdapGroupRule:traversal managed
        object property"
    ::= { cfprApAaaLdapGroupRuleEntry 8 }

cfprApAaaLdapGroupRuleUsePrimaryGroup OBJECT-TYPE
    SYNTAX       TruthValue
    MAX-ACCESS   read-only
    STATUS       current
    DESCRIPTION
        "Cisco Firepower aaa:LdapGroupRule:usePrimaryGroup
        managed object property"
    ::= { cfprApAaaLdapGroupRuleEntry 9 }

cfprApAaaLdapProviderTable OBJECT-TYPE
    SYNTAX           SEQUENCE OF CfprApAaaLdapProviderEntry
    MAX-ACCESS       not-accessible
    STATUS           current
    DESCRIPTION
        "Cisco Firepower aaa:LdapProvider managed object table"
    ::= { cfprApAaaObjects 21 }

cfprApAaaLdapProviderEntry OBJECT-TYPE
    SYNTAX           CfprApAaaLdapProviderEntry
    MAX-ACCESS       not-accessible
    STATUS           current
    DESCRIPTION
        "Entry for the cfprApAaaLdapProviderTable table."
    INDEX { cfprApAaaLdapProviderInstanceId }
    ::= { cfprApAaaLdapProviderTable 1 }

CfprApAaaLdapProviderEntry ::= SEQUENCE {
    cfprApAaaLdapProviderInstanceId                                  CfprApManagedObjectId,
    cfprApAaaLdapProviderDn                                          CfprApManagedObjectDn,
    cfprApAaaLdapProviderRn                                          SnmpAdminString,
    cfprApAaaLdapProviderAttribute                                   SnmpAdminString,
    cfprApAaaLdapProviderBasedn                                      SnmpAdminString,
    cfprApAaaLdapProviderDescr                                       SnmpAdminString,
    cfprApAaaLdapProviderEnableSSL                                   TruthValue,
    cfprApAaaLdapProviderEncKey                                      SnmpAdminString,
    cfprApAaaLdapProviderFilter                                      SnmpAdminString,
    cfprApAaaLdapProviderKey                                         SnmpAdminString,
    cfprApAaaLdapProviderKeySet                                      TruthValue,
    cfprApAaaLdapProviderName                                        SnmpAdminString,
    cfprApAaaLdapProviderOrder                                       Gauge32,
    cfprApAaaLdapProviderPort                                        Gauge32,
    cfprApAaaLdapProviderRetries                                     Gauge32,
    cfprApAaaLdapProviderRootdn                                      SnmpAdminString,
    cfprApAaaLdapProviderTimeout                                     Gauge32,
    cfprApAaaLdapProviderVendor                                      CfprApAaaLdapVendor
}

cfprApAaaLdapProviderInstanceId OBJECT-TYPE
    SYNTAX       CfprApManagedObjectId
    MAX-ACCESS   not-accessible
    STATUS       current
    DESCRIPTION
        "Instance identifier of the managed object."
    ::= { cfprApAaaLdapProviderEntry 1 }

cfprApAaaLdapProviderDn OBJECT-TYPE
    SYNTAX       CfprApManagedObjectDn
    MAX-ACCESS   read-only
    STATUS       current
    DESCRIPTION
        "Cisco Firepower aaa:LdapProvider:dn managed object property"
    ::= { cfprApAaaLdapProviderEntry 2 }

cfprApAaaLdapProviderRn OBJECT-TYPE
    SYNTAX       SnmpAdminString
    MAX-ACCESS   read-only
    STATUS       current
    DESCRIPTION
        "Cisco Firepower aaa:LdapProvider:rn managed object property"
    ::= { cfprApAaaLdapProviderEntry 3 }

cfprApAaaLdapProviderAttribute OBJECT-TYPE
    SYNTAX       SnmpAdminString
    MAX-ACCESS   read-only
    STATUS       current
    DESCRIPTION
        "Cisco Firepower aaa:LdapProvider:attribute managed
        object property"
    ::= { cfprApAaaLdapProviderEntry 4 }

cfprApAaaLdapProviderBasedn OBJECT-TYPE
    SYNTAX       SnmpAdminString
    MAX-ACCESS   read-only
    STATUS       current
    DESCRIPTION
        "Cisco Firepower aaa:LdapProvider:basedn managed object property"
    ::= { cfprApAaaLdapProviderEntry 5 }

cfprApAaaLdapProviderDescr OBJECT-TYPE
    SYNTAX       SnmpAdminString
    MAX-ACCESS   read-only
    STATUS       current
    DESCRIPTION
        "Cisco Firepower aaa:LdapProvider:descr managed object property"
    ::= { cfprApAaaLdapProviderEntry 6 }

cfprApAaaLdapProviderEnableSSL OBJECT-TYPE
    SYNTAX       TruthValue
    MAX-ACCESS   read-only
    STATUS       current
    DESCRIPTION
        "Cisco Firepower aaa:LdapProvider:enableSSL managed
        object property"
    ::= { cfprApAaaLdapProviderEntry 7 }

cfprApAaaLdapProviderEncKey OBJECT-TYPE
    SYNTAX       SnmpAdminString
    MAX-ACCESS   read-only
    STATUS       current
    DESCRIPTION
        "Cisco Firepower aaa:LdapProvider:encKey managed object property"
    ::= { cfprApAaaLdapProviderEntry 8 }

cfprApAaaLdapProviderFilter OBJECT-TYPE
    SYNTAX       SnmpAdminString
    MAX-ACCESS   read-only
    STATUS       current
    DESCRIPTION
        "Cisco Firepower aaa:LdapProvider:filter managed object property"
    ::= { cfprApAaaLdapProviderEntry 9 }

cfprApAaaLdapProviderKey OBJECT-TYPE
    SYNTAX       SnmpAdminString
    MAX-ACCESS   read-only
    STATUS       current
    DESCRIPTION
        "Cisco Firepower aaa:LdapProvider:key managed object property"
    ::= { cfprApAaaLdapProviderEntry 10 }

cfprApAaaLdapProviderKeySet OBJECT-TYPE
    SYNTAX       TruthValue
    MAX-ACCESS   read-only
    STATUS       current
    DESCRIPTION
        "Cisco Firepower aaa:LdapProvider:keySet managed object property"
    ::= { cfprApAaaLdapProviderEntry 11 }

cfprApAaaLdapProviderName OBJECT-TYPE
    SYNTAX       SnmpAdminString
    MAX-ACCESS   read-only
    STATUS       current
    DESCRIPTION
        "Cisco Firepower aaa:LdapProvider:name managed object property"
    ::= { cfprApAaaLdapProviderEntry 12 }

cfprApAaaLdapProviderOrder OBJECT-TYPE
    SYNTAX       Gauge32
    MAX-ACCESS   read-only
    STATUS       current
    DESCRIPTION
        "Cisco Firepower aaa:LdapProvider:order managed object property"
    ::= { cfprApAaaLdapProviderEntry 13 }

cfprApAaaLdapProviderPort OBJECT-TYPE
    SYNTAX       Gauge32
    MAX-ACCESS   read-only
    STATUS       current
    DESCRIPTION
        "Cisco Firepower aaa:LdapProvider:port managed object property"
    ::= { cfprApAaaLdapProviderEntry 14 }

cfprApAaaLdapProviderRetries OBJECT-TYPE
    SYNTAX       Gauge32
    MAX-ACCESS   read-only
    STATUS       current
    DESCRIPTION
        "Cisco Firepower aaa:LdapProvider:retries managed object property"
    ::= { cfprApAaaLdapProviderEntry 15 }

cfprApAaaLdapProviderRootdn OBJECT-TYPE
    SYNTAX       SnmpAdminString
    MAX-ACCESS   read-only
    STATUS       current
    DESCRIPTION
        "Cisco Firepower aaa:LdapProvider:rootdn managed object property"
    ::= { cfprApAaaLdapProviderEntry 16 }

cfprApAaaLdapProviderTimeout OBJECT-TYPE
    SYNTAX       Gauge32
    MAX-ACCESS   read-only
    STATUS       current
    DESCRIPTION
        "Cisco Firepower aaa:LdapProvider:timeout managed object property"
    ::= { cfprApAaaLdapProviderEntry 17 }

cfprApAaaLdapProviderVendor OBJECT-TYPE
    SYNTAX       CfprApAaaLdapVendor
    MAX-ACCESS   read-only
    STATUS       current
    DESCRIPTION
        "Cisco Firepower aaa:LdapProvider:vendor managed object property"
    ::= { cfprApAaaLdapProviderEntry 18 }

cfprApAaaLocaleTable OBJECT-TYPE
    SYNTAX           SEQUENCE OF CfprApAaaLocaleEntry
    MAX-ACCESS       not-accessible
    STATUS           current
    DESCRIPTION
        "Cisco Firepower aaa:Locale managed object table"
    ::= { cfprApAaaObjects 22 }

cfprApAaaLocaleEntry OBJECT-TYPE
    SYNTAX           CfprApAaaLocaleEntry
    MAX-ACCESS       not-accessible
    STATUS           current
    DESCRIPTION
        "Entry for the cfprApAaaLocaleTable table."
    INDEX { cfprApAaaLocaleInstanceId }
    ::= { cfprApAaaLocaleTable 1 }

CfprApAaaLocaleEntry ::= SEQUENCE {
    cfprApAaaLocaleInstanceId                                        CfprApManagedObjectId,
    cfprApAaaLocaleDn                                                CfprApManagedObjectDn,
    cfprApAaaLocaleRn                                                SnmpAdminString,
    cfprApAaaLocaleConfigState                                       CfprApAaaConfigState,
    cfprApAaaLocaleConfigStatusMessage                               SnmpAdminString,
    cfprApAaaLocaleDescr                                             SnmpAdminString,
    cfprApAaaLocaleIntId                                             SnmpAdminString,
    cfprApAaaLocaleName                                              SnmpAdminString,
    cfprApAaaLocalePolicyLevel                                       Gauge32,
    cfprApAaaLocalePolicyOwner                                       CfprApPolicyPolicyOwner
}

cfprApAaaLocaleInstanceId OBJECT-TYPE
    SYNTAX       CfprApManagedObjectId
    MAX-ACCESS   not-accessible
    STATUS       current
    DESCRIPTION
        "Instance identifier of the managed object."
    ::= { cfprApAaaLocaleEntry 1 }

cfprApAaaLocaleDn OBJECT-TYPE
    SYNTAX       CfprApManagedObjectDn
    MAX-ACCESS   read-only
    STATUS       current
    DESCRIPTION
        "Cisco Firepower aaa:Locale:dn managed object property"
    ::= { cfprApAaaLocaleEntry 2 }

cfprApAaaLocaleRn OBJECT-TYPE
    SYNTAX       SnmpAdminString
    MAX-ACCESS   read-only
    STATUS       current
    DESCRIPTION
        "Cisco Firepower aaa:Locale:rn managed object property"
    ::= { cfprApAaaLocaleEntry 3 }

cfprApAaaLocaleConfigState OBJECT-TYPE
    SYNTAX       CfprApAaaConfigState
    MAX-ACCESS   read-only
    STATUS       current
    DESCRIPTION
        "Cisco Firepower aaa:Locale:configState managed object property"
    ::= { cfprApAaaLocaleEntry 4 }

cfprApAaaLocaleConfigStatusMessage OBJECT-TYPE
    SYNTAX       SnmpAdminString
    MAX-ACCESS   read-only
    STATUS       current
    DESCRIPTION
        "Cisco Firepower aaa:Locale:configStatusMessage
        managed object property"
    ::= { cfprApAaaLocaleEntry 5 }

cfprApAaaLocaleDescr OBJECT-TYPE
    SYNTAX       SnmpAdminString
    MAX-ACCESS   read-only
    STATUS       current
    DESCRIPTION
        "Cisco Firepower aaa:Locale:descr managed object property"
    ::= { cfprApAaaLocaleEntry 6 }

cfprApAaaLocaleIntId OBJECT-TYPE
    SYNTAX       SnmpAdminString
    MAX-ACCESS   read-only
    STATUS       current
    DESCRIPTION
        "Cisco Firepower aaa:Locale:intId managed object property"
    ::= { cfprApAaaLocaleEntry 7 }

cfprApAaaLocaleName OBJECT-TYPE
    SYNTAX       SnmpAdminString
    MAX-ACCESS   read-only
    STATUS       current
    DESCRIPTION
        "Cisco Firepower aaa:Locale:name managed object property"
    ::= { cfprApAaaLocaleEntry 8 }

cfprApAaaLocalePolicyLevel OBJECT-TYPE
    SYNTAX       Gauge32
    MAX-ACCESS   read-only
    STATUS       current
    DESCRIPTION
        "Cisco Firepower aaa:Locale:policyLevel managed object property"
    ::= { cfprApAaaLocaleEntry 9 }

cfprApAaaLocalePolicyOwner OBJECT-TYPE
    SYNTAX       CfprApPolicyPolicyOwner
    MAX-ACCESS   read-only
    STATUS       current
    DESCRIPTION
        "Cisco Firepower aaa:Locale:policyOwner managed object property"
    ::= { cfprApAaaLocaleEntry 10 }

cfprApAaaLogTable OBJECT-TYPE
    SYNTAX           SEQUENCE OF CfprApAaaLogEntry
    MAX-ACCESS       not-accessible
    STATUS           current
    DESCRIPTION
        "Cisco Firepower aaa:Log managed object table"
    ::= { cfprApAaaObjects 23 }

cfprApAaaLogEntry OBJECT-TYPE
    SYNTAX           CfprApAaaLogEntry
    MAX-ACCESS       not-accessible
    STATUS           current
    DESCRIPTION
        "Entry for the cfprApAaaLogTable table."
    INDEX { cfprApAaaLogInstanceId }
    ::= { cfprApAaaLogTable 1 }

CfprApAaaLogEntry ::= SEQUENCE {
    cfprApAaaLogInstanceId                                           CfprApManagedObjectId,
    cfprApAaaLogDn                                                   CfprApManagedObjectDn,
    cfprApAaaLogRn                                                   SnmpAdminString,
    cfprApAaaLogMaxSize                                              Gauge32,
    cfprApAaaLogPurgeWindow                                          Gauge32,
    cfprApAaaLogSize                                                 Gauge32
}

cfprApAaaLogInstanceId OBJECT-TYPE
    SYNTAX       CfprApManagedObjectId
    MAX-ACCESS   not-accessible
    STATUS       current
    DESCRIPTION
        "Instance identifier of the managed object."
    ::= { cfprApAaaLogEntry 1 }

cfprApAaaLogDn OBJECT-TYPE
    SYNTAX       CfprApManagedObjectDn
    MAX-ACCESS   read-only
    STATUS       current
    DESCRIPTION
        "Cisco Firepower aaa:Log:dn managed object property"
    ::= { cfprApAaaLogEntry 2 }

cfprApAaaLogRn OBJECT-TYPE
    SYNTAX       SnmpAdminString
    MAX-ACCESS   read-only
    STATUS       current
    DESCRIPTION
        "Cisco Firepower aaa:Log:rn managed object property"
    ::= { cfprApAaaLogEntry 3 }

cfprApAaaLogMaxSize OBJECT-TYPE
    SYNTAX       Gauge32
    MAX-ACCESS   read-only
    STATUS       current
    DESCRIPTION
        "Cisco Firepower aaa:Log:maxSize managed object property"
    ::= { cfprApAaaLogEntry 4 }

cfprApAaaLogPurgeWindow OBJECT-TYPE
    SYNTAX       Gauge32
    MAX-ACCESS   read-only
    STATUS       current
    DESCRIPTION
        "Cisco Firepower aaa:Log:purgeWindow managed object property"
    ::= { cfprApAaaLogEntry 5 }

cfprApAaaLogSize OBJECT-TYPE
    SYNTAX       Gauge32
    MAX-ACCESS   read-only
    STATUS       current
    DESCRIPTION
        "Cisco Firepower aaa:Log:size managed object property"
    ::= { cfprApAaaLogEntry 6 }

cfprApAaaModLRTable OBJECT-TYPE
    SYNTAX           SEQUENCE OF CfprApAaaModLREntry
    MAX-ACCESS       not-accessible
    STATUS           current
    DESCRIPTION
        "Cisco Firepower aaa:ModLR managed object table"
    ::= { cfprApAaaObjects 24 }

cfprApAaaModLREntry OBJECT-TYPE
    SYNTAX           CfprApAaaModLREntry
    MAX-ACCESS       not-accessible
    STATUS           current
    DESCRIPTION
        "Entry for the cfprApAaaModLRTable table."
    INDEX { cfprApAaaModLRInstanceId }
    ::= { cfprApAaaModLRTable 1 }

CfprApAaaModLREntry ::= SEQUENCE {
    cfprApAaaModLRInstanceId                                         CfprApManagedObjectId,
    cfprApAaaModLRDn                                                 CfprApManagedObjectDn,
    cfprApAaaModLRRn                                                 SnmpAdminString,
    cfprApAaaModLRAffected                                           SnmpAdminString,
    cfprApAaaModLRCause                                              CfprApConditionCause,
    cfprApAaaModLRChangeSet                                          SnmpAdminString,
    cfprApAaaModLRCode                                               CfprApConditionCode,
    cfprApAaaModLRCreated                                            DateAndTime,
    cfprApAaaModLRDescr                                              SnmpAdminString,
    cfprApAaaModLRId                                                 Gauge32,
    cfprApAaaModLRInd                                                CfprApConditionActionIndicator,
    cfprApAaaModLRSessionId                                          SnmpAdminString,
    cfprApAaaModLRSeverity                                           CfprApConditionSeverity,
    cfprApAaaModLRTrig                                               Gauge32,
    cfprApAaaModLRTxId                                               Unsigned64,
    cfprApAaaModLRUser                                               SnmpAdminString
}

cfprApAaaModLRInstanceId OBJECT-TYPE
    SYNTAX       CfprApManagedObjectId
    MAX-ACCESS   not-accessible
    STATUS       current
    DESCRIPTION
        "Instance identifier of the managed object."
    ::= { cfprApAaaModLREntry 1 }

cfprApAaaModLRDn OBJECT-TYPE
    SYNTAX       CfprApManagedObjectDn
    MAX-ACCESS   read-only
    STATUS       current
    DESCRIPTION
        "Cisco Firepower aaa:ModLR:dn managed object property"
    ::= { cfprApAaaModLREntry 2 }

cfprApAaaModLRRn OBJECT-TYPE
    SYNTAX       SnmpAdminString
    MAX-ACCESS   read-only
    STATUS       current
    DESCRIPTION
        "Cisco Firepower aaa:ModLR:rn managed object property"
    ::= { cfprApAaaModLREntry 3 }

cfprApAaaModLRAffected OBJECT-TYPE
    SYNTAX       SnmpAdminString
    MAX-ACCESS   read-only
    STATUS       current
    DESCRIPTION
        "Cisco Firepower aaa:ModLR:affected managed object property"
    ::= { cfprApAaaModLREntry 4 }

cfprApAaaModLRCause OBJECT-TYPE
    SYNTAX       CfprApConditionCause
    MAX-ACCESS   read-only
    STATUS       current
    DESCRIPTION
        "Cisco Firepower aaa:ModLR:cause managed object property"
    ::= { cfprApAaaModLREntry 5 }

cfprApAaaModLRChangeSet OBJECT-TYPE
    SYNTAX       SnmpAdminString
    MAX-ACCESS   read-only
    STATUS       current
    DESCRIPTION
        "Cisco Firepower aaa:ModLR:changeSet managed object property"
    ::= { cfprApAaaModLREntry 6 }

cfprApAaaModLRCode OBJECT-TYPE
    SYNTAX       CfprApConditionCode
    MAX-ACCESS   read-only
    STATUS       current
    DESCRIPTION
        "Cisco Firepower aaa:ModLR:code managed object property"
    ::= { cfprApAaaModLREntry 7 }

cfprApAaaModLRCreated OBJECT-TYPE
    SYNTAX       DateAndTime
    MAX-ACCESS   read-only
    STATUS       current
    DESCRIPTION
        "Cisco Firepower aaa:ModLR:created managed object property"
    ::= { cfprApAaaModLREntry 8 }

cfprApAaaModLRDescr OBJECT-TYPE
    SYNTAX       SnmpAdminString
    MAX-ACCESS   read-only
    STATUS       current
    DESCRIPTION
        "Cisco Firepower aaa:ModLR:descr managed object property"
    ::= { cfprApAaaModLREntry 9 }

cfprApAaaModLRId OBJECT-TYPE
    SYNTAX       Gauge32
    MAX-ACCESS   read-only
    STATUS       current
    DESCRIPTION
        "Cisco Firepower aaa:ModLR:id managed object property"
    ::= { cfprApAaaModLREntry 10 }

cfprApAaaModLRInd OBJECT-TYPE
    SYNTAX       CfprApConditionActionIndicator
    MAX-ACCESS   read-only
    STATUS       current
    DESCRIPTION
        "Cisco Firepower aaa:ModLR:ind managed object property"
    ::= { cfprApAaaModLREntry 11 }

cfprApAaaModLRSessionId OBJECT-TYPE
    SYNTAX       SnmpAdminString
    MAX-ACCESS   read-only
    STATUS       current
    DESCRIPTION
        "Cisco Firepower aaa:ModLR:sessionId managed object property"
    ::= { cfprApAaaModLREntry 12 }

cfprApAaaModLRSeverity OBJECT-TYPE
    SYNTAX       CfprApConditionSeverity
    MAX-ACCESS   read-only
    STATUS       current
    DESCRIPTION
        "Cisco Firepower aaa:ModLR:severity managed object property"
    ::= { cfprApAaaModLREntry 13 }

cfprApAaaModLRTrig OBJECT-TYPE
    SYNTAX       Gauge32
    MAX-ACCESS   read-only
    STATUS       current
    DESCRIPTION
        "Cisco Firepower aaa:ModLR:trig managed object property"
    ::= { cfprApAaaModLREntry 14 }

cfprApAaaModLRTxId OBJECT-TYPE
    SYNTAX       Unsigned64
    MAX-ACCESS   read-only
    STATUS       current
    DESCRIPTION
        "Cisco Firepower aaa:ModLR:txId managed object property"
    ::= { cfprApAaaModLREntry 15 }

cfprApAaaModLRUser OBJECT-TYPE
    SYNTAX       SnmpAdminString
    MAX-ACCESS   read-only
    STATUS       current
    DESCRIPTION
        "Cisco Firepower aaa:ModLR:user managed object property"
    ::= { cfprApAaaModLREntry 16 }

cfprApAaaOrgTable OBJECT-TYPE
    SYNTAX           SEQUENCE OF CfprApAaaOrgEntry
    MAX-ACCESS       not-accessible
    STATUS           current
    DESCRIPTION
        "Cisco Firepower aaa:Org managed object table"
    ::= { cfprApAaaObjects 25 }

cfprApAaaOrgEntry OBJECT-TYPE
    SYNTAX           CfprApAaaOrgEntry
    MAX-ACCESS       not-accessible
    STATUS           current
    DESCRIPTION
        "Entry for the cfprApAaaOrgTable table."
    INDEX { cfprApAaaOrgInstanceId }
    ::= { cfprApAaaOrgTable 1 }

CfprApAaaOrgEntry ::= SEQUENCE {
    cfprApAaaOrgInstanceId                                           CfprApManagedObjectId,
    cfprApAaaOrgDn                                                   CfprApManagedObjectDn,
    cfprApAaaOrgRn                                                   SnmpAdminString,
    cfprApAaaOrgConfigState                                          CfprApAaaConfigState,
    cfprApAaaOrgConfigStatusMessage                                  SnmpAdminString,
    cfprApAaaOrgDescr                                                SnmpAdminString,
    cfprApAaaOrgName                                                 SnmpAdminString,
    cfprApAaaOrgOrgDn                                                SnmpAdminString
}

cfprApAaaOrgInstanceId OBJECT-TYPE
    SYNTAX       CfprApManagedObjectId
    MAX-ACCESS   not-accessible
    STATUS       current
    DESCRIPTION
        "Instance identifier of the managed object."
    ::= { cfprApAaaOrgEntry 1 }

cfprApAaaOrgDn OBJECT-TYPE
    SYNTAX       CfprApManagedObjectDn
    MAX-ACCESS   read-only
    STATUS       current
    DESCRIPTION
        "Cisco Firepower aaa:Org:dn managed object property"
    ::= { cfprApAaaOrgEntry 2 }

cfprApAaaOrgRn OBJECT-TYPE
    SYNTAX       SnmpAdminString
    MAX-ACCESS   read-only
    STATUS       current
    DESCRIPTION
        "Cisco Firepower aaa:Org:rn managed object property"
    ::= { cfprApAaaOrgEntry 3 }

cfprApAaaOrgConfigState OBJECT-TYPE
    SYNTAX       CfprApAaaConfigState
    MAX-ACCESS   read-only
    STATUS       current
    DESCRIPTION
        "Cisco Firepower aaa:Org:configState managed object property"
    ::= { cfprApAaaOrgEntry 4 }

cfprApAaaOrgConfigStatusMessage OBJECT-TYPE
    SYNTAX       SnmpAdminString
    MAX-ACCESS   read-only
    STATUS       current
    DESCRIPTION
        "Cisco Firepower aaa:Org:configStatusMessage managed
        object property"
    ::= { cfprApAaaOrgEntry 5 }

cfprApAaaOrgDescr OBJECT-TYPE
    SYNTAX       SnmpAdminString
    MAX-ACCESS   read-only
    STATUS       current
    DESCRIPTION
        "Cisco Firepower aaa:Org:descr managed object property"
    ::= { cfprApAaaOrgEntry 6 }

cfprApAaaOrgName OBJECT-TYPE
    SYNTAX       SnmpAdminString
    MAX-ACCESS   read-only
    STATUS       current
    DESCRIPTION
        "Cisco Firepower aaa:Org:name managed object property"
    ::= { cfprApAaaOrgEntry 7 }

cfprApAaaOrgOrgDn OBJECT-TYPE
    SYNTAX       SnmpAdminString
    MAX-ACCESS   read-only
    STATUS       current
    DESCRIPTION
        "Cisco Firepower aaa:Org:orgDn managed object property"
    ::= { cfprApAaaOrgEntry 8 }

cfprApAaaPreLoginBannerTable OBJECT-TYPE
    SYNTAX           SEQUENCE OF CfprApAaaPreLoginBannerEntry
    MAX-ACCESS       not-accessible
    STATUS           current
    DESCRIPTION
        "Cisco Firepower aaa:PreLoginBanner managed object table"
    ::= { cfprApAaaObjects 26 }

cfprApAaaPreLoginBannerEntry OBJECT-TYPE
    SYNTAX           CfprApAaaPreLoginBannerEntry
    MAX-ACCESS       not-accessible
    STATUS           current
    DESCRIPTION
        "Entry for the cfprApAaaPreLoginBannerTable table."
    INDEX { cfprApAaaPreLoginBannerInstanceId }
    ::= { cfprApAaaPreLoginBannerTable 1 }

CfprApAaaPreLoginBannerEntry ::= SEQUENCE {
    cfprApAaaPreLoginBannerInstanceId                                CfprApManagedObjectId,
    cfprApAaaPreLoginBannerDn                                        CfprApManagedObjectDn,
    cfprApAaaPreLoginBannerRn                                        SnmpAdminString,
    cfprApAaaPreLoginBannerDescr                                     SnmpAdminString,
    cfprApAaaPreLoginBannerIntId                                     SnmpAdminString,
    cfprApAaaPreLoginBannerMessage                                   SnmpAdminString,
    cfprApAaaPreLoginBannerName                                      SnmpAdminString,
    cfprApAaaPreLoginBannerPolicyLevel                               Gauge32,
    cfprApAaaPreLoginBannerPolicyOwner                               CfprApPolicyPolicyOwner
}

cfprApAaaPreLoginBannerInstanceId OBJECT-TYPE
    SYNTAX       CfprApManagedObjectId
    MAX-ACCESS   not-accessible
    STATUS       current
    DESCRIPTION
        "Instance identifier of the managed object."
    ::= { cfprApAaaPreLoginBannerEntry 1 }

cfprApAaaPreLoginBannerDn OBJECT-TYPE
    SYNTAX       CfprApManagedObjectDn
    MAX-ACCESS   read-only
    STATUS       current
    DESCRIPTION
        "Cisco Firepower aaa:PreLoginBanner:dn managed object property"
    ::= { cfprApAaaPreLoginBannerEntry 2 }

cfprApAaaPreLoginBannerRn OBJECT-TYPE
    SYNTAX       SnmpAdminString
    MAX-ACCESS   read-only
    STATUS       current
    DESCRIPTION
        "Cisco Firepower aaa:PreLoginBanner:rn managed object property"
    ::= { cfprApAaaPreLoginBannerEntry 3 }

cfprApAaaPreLoginBannerDescr OBJECT-TYPE
    SYNTAX       SnmpAdminString
    MAX-ACCESS   read-only
    STATUS       current
    DESCRIPTION
        "Cisco Firepower aaa:PreLoginBanner:descr managed object property"
    ::= { cfprApAaaPreLoginBannerEntry 4 }

cfprApAaaPreLoginBannerIntId OBJECT-TYPE
    SYNTAX       SnmpAdminString
    MAX-ACCESS   read-only
    STATUS       current
    DESCRIPTION
        "Cisco Firepower aaa:PreLoginBanner:intId managed object property"
    ::= { cfprApAaaPreLoginBannerEntry 5 }

cfprApAaaPreLoginBannerMessage OBJECT-TYPE
    SYNTAX       SnmpAdminString
    MAX-ACCESS   read-only
    STATUS       current
    DESCRIPTION
        "Cisco Firepower aaa:PreLoginBanner:message managed
        object property"
    ::= { cfprApAaaPreLoginBannerEntry 6 }

cfprApAaaPreLoginBannerName OBJECT-TYPE
    SYNTAX       SnmpAdminString
    MAX-ACCESS   read-only
    STATUS       current
    DESCRIPTION
        "Cisco Firepower aaa:PreLoginBanner:name managed object property"
    ::= { cfprApAaaPreLoginBannerEntry 7 }

cfprApAaaPreLoginBannerPolicyLevel OBJECT-TYPE
    SYNTAX       Gauge32
    MAX-ACCESS   read-only
    STATUS       current
    DESCRIPTION
        "Cisco Firepower aaa:PreLoginBanner:policyLevel
        managed object property"
    ::= { cfprApAaaPreLoginBannerEntry 8 }

cfprApAaaPreLoginBannerPolicyOwner OBJECT-TYPE
    SYNTAX       CfprApPolicyPolicyOwner
    MAX-ACCESS   read-only
    STATUS       current
    DESCRIPTION
        "Cisco Firepower aaa:PreLoginBanner:policyOwner
        managed object property"
    ::= { cfprApAaaPreLoginBannerEntry 9 }

cfprApAaaProviderGroupTable OBJECT-TYPE
    SYNTAX           SEQUENCE OF CfprApAaaProviderGroupEntry
    MAX-ACCESS       not-accessible
    STATUS           current
    DESCRIPTION
        "Cisco Firepower aaa:ProviderGroup managed object table"
    ::= { cfprApAaaObjects 27 }

cfprApAaaProviderGroupEntry OBJECT-TYPE
    SYNTAX           CfprApAaaProviderGroupEntry
    MAX-ACCESS       not-accessible
    STATUS           current
    DESCRIPTION
        "Entry for the cfprApAaaProviderGroupTable table."
    INDEX { cfprApAaaProviderGroupInstanceId }
    ::= { cfprApAaaProviderGroupTable 1 }

CfprApAaaProviderGroupEntry ::= SEQUENCE {
    cfprApAaaProviderGroupInstanceId                                 CfprApManagedObjectId,
    cfprApAaaProviderGroupDn                                         CfprApManagedObjectDn,
    cfprApAaaProviderGroupRn                                         SnmpAdminString,
    cfprApAaaProviderGroupConfigState                                CfprApAaaConfigState,
    cfprApAaaProviderGroupDescr                                      SnmpAdminString,
    cfprApAaaProviderGroupName                                       SnmpAdminString,
    cfprApAaaProviderGroupSize                                       Gauge32
}

cfprApAaaProviderGroupInstanceId OBJECT-TYPE
    SYNTAX       CfprApManagedObjectId
    MAX-ACCESS   not-accessible
    STATUS       current
    DESCRIPTION
        "Instance identifier of the managed object."
    ::= { cfprApAaaProviderGroupEntry 1 }

cfprApAaaProviderGroupDn OBJECT-TYPE
    SYNTAX       CfprApManagedObjectDn
    MAX-ACCESS   read-only
    STATUS       current
    DESCRIPTION
        "Cisco Firepower aaa:ProviderGroup:dn managed object property"
    ::= { cfprApAaaProviderGroupEntry 2 }

cfprApAaaProviderGroupRn OBJECT-TYPE
    SYNTAX       SnmpAdminString
    MAX-ACCESS   read-only
    STATUS       current
    DESCRIPTION
        "Cisco Firepower aaa:ProviderGroup:rn managed object property"
    ::= { cfprApAaaProviderGroupEntry 3 }

cfprApAaaProviderGroupConfigState OBJECT-TYPE
    SYNTAX       CfprApAaaConfigState
    MAX-ACCESS   read-only
    STATUS       current
    DESCRIPTION
        "Cisco Firepower aaa:ProviderGroup:configState
        managed object property"
    ::= { cfprApAaaProviderGroupEntry 4 }

cfprApAaaProviderGroupDescr OBJECT-TYPE
    SYNTAX       SnmpAdminString
    MAX-ACCESS   read-only
    STATUS       current
    DESCRIPTION
        "Cisco Firepower aaa:ProviderGroup:descr managed object property"
    ::= { cfprApAaaProviderGroupEntry 5 }

cfprApAaaProviderGroupName OBJECT-TYPE
    SYNTAX       SnmpAdminString
    MAX-ACCESS   read-only
    STATUS       current
    DESCRIPTION
        "Cisco Firepower aaa:ProviderGroup:name managed object property"
    ::= { cfprApAaaProviderGroupEntry 6 }

cfprApAaaProviderGroupSize OBJECT-TYPE
    SYNTAX       Gauge32
    MAX-ACCESS   read-only
    STATUS       current
    DESCRIPTION
        "Cisco Firepower aaa:ProviderGroup:size managed object property"
    ::= { cfprApAaaProviderGroupEntry 7 }

cfprApAaaProviderRefTable OBJECT-TYPE
    SYNTAX           SEQUENCE OF CfprApAaaProviderRefEntry
    MAX-ACCESS       not-accessible
    STATUS           current
    DESCRIPTION
        "Cisco Firepower aaa:ProviderRef managed object table"
    ::= { cfprApAaaObjects 28 }

cfprApAaaProviderRefEntry OBJECT-TYPE
    SYNTAX           CfprApAaaProviderRefEntry
    MAX-ACCESS       not-accessible
    STATUS           current
    DESCRIPTION
        "Entry for the cfprApAaaProviderRefTable table."
    INDEX { cfprApAaaProviderRefInstanceId }
    ::= { cfprApAaaProviderRefTable 1 }

CfprApAaaProviderRefEntry ::= SEQUENCE {
    cfprApAaaProviderRefInstanceId                                   CfprApManagedObjectId,
    cfprApAaaProviderRefDn                                           CfprApManagedObjectDn,
    cfprApAaaProviderRefRn                                           SnmpAdminString,
    cfprApAaaProviderRefDescr                                        SnmpAdminString,
    cfprApAaaProviderRefName                                         SnmpAdminString,
    cfprApAaaProviderRefOrder                                        Gauge32
}

cfprApAaaProviderRefInstanceId OBJECT-TYPE
    SYNTAX       CfprApManagedObjectId
    MAX-ACCESS   not-accessible
    STATUS       current
    DESCRIPTION
        "Instance identifier of the managed object."
    ::= { cfprApAaaProviderRefEntry 1 }

cfprApAaaProviderRefDn OBJECT-TYPE
    SYNTAX       CfprApManagedObjectDn
    MAX-ACCESS   read-only
    STATUS       current
    DESCRIPTION
        "Cisco Firepower aaa:ProviderRef:dn managed object property"
    ::= { cfprApAaaProviderRefEntry 2 }

cfprApAaaProviderRefRn OBJECT-TYPE
    SYNTAX       SnmpAdminString
    MAX-ACCESS   read-only
    STATUS       current
    DESCRIPTION
        "Cisco Firepower aaa:ProviderRef:rn managed object property"
    ::= { cfprApAaaProviderRefEntry 3 }

cfprApAaaProviderRefDescr OBJECT-TYPE
    SYNTAX       SnmpAdminString
    MAX-ACCESS   read-only
    STATUS       current
    DESCRIPTION
        "Cisco Firepower aaa:ProviderRef:descr managed object property"
    ::= { cfprApAaaProviderRefEntry 4 }

cfprApAaaProviderRefName OBJECT-TYPE
    SYNTAX       SnmpAdminString
    MAX-ACCESS   read-only
    STATUS       current
    DESCRIPTION
        "Cisco Firepower aaa:ProviderRef:name managed object property"
    ::= { cfprApAaaProviderRefEntry 5 }

cfprApAaaProviderRefOrder OBJECT-TYPE
    SYNTAX       Gauge32
    MAX-ACCESS   read-only
    STATUS       current
    DESCRIPTION
        "Cisco Firepower aaa:ProviderRef:order managed object property"
    ::= { cfprApAaaProviderRefEntry 6 }

cfprApAaaPwdProfileTable OBJECT-TYPE
    SYNTAX           SEQUENCE OF CfprApAaaPwdProfileEntry
    MAX-ACCESS       not-accessible
    STATUS           current
    DESCRIPTION
        "Cisco Firepower aaa:PwdProfile managed object table"
    ::= { cfprApAaaObjects 29 }

cfprApAaaPwdProfileEntry OBJECT-TYPE
    SYNTAX           CfprApAaaPwdProfileEntry
    MAX-ACCESS       not-accessible
    STATUS           current
    DESCRIPTION
        "Entry for the cfprApAaaPwdProfileTable table."
    INDEX { cfprApAaaPwdProfileInstanceId }
    ::= { cfprApAaaPwdProfileTable 1 }

CfprApAaaPwdProfileEntry ::= SEQUENCE {
    cfprApAaaPwdProfileInstanceId                                    CfprApManagedObjectId,
    cfprApAaaPwdProfileDn                                            CfprApManagedObjectDn,
    cfprApAaaPwdProfileRn                                            SnmpAdminString,
    cfprApAaaPwdProfileChangeCount                                   Gauge32,
    cfprApAaaPwdProfileChangeDuringInterval                          CfprApAaaPwdPolicy,
    cfprApAaaPwdProfileChangeInterval                                Gauge32,
    cfprApAaaPwdProfileExpirationWarnTime                            Gauge32,
    cfprApAaaPwdProfileHistoryCount                                  Gauge32,
    cfprApAaaPwdProfileNoChangeInterval                              Gauge32
}

cfprApAaaPwdProfileInstanceId OBJECT-TYPE
    SYNTAX       CfprApManagedObjectId
    MAX-ACCESS   not-accessible
    STATUS       current
    DESCRIPTION
        "Instance identifier of the managed object."
    ::= { cfprApAaaPwdProfileEntry 1 }

cfprApAaaPwdProfileDn OBJECT-TYPE
    SYNTAX       CfprApManagedObjectDn
    MAX-ACCESS   read-only
    STATUS       current
    DESCRIPTION
        "Cisco Firepower aaa:PwdProfile:dn managed object property"
    ::= { cfprApAaaPwdProfileEntry 2 }

cfprApAaaPwdProfileRn OBJECT-TYPE
    SYNTAX       SnmpAdminString
    MAX-ACCESS   read-only
    STATUS       current
    DESCRIPTION
        "Cisco Firepower aaa:PwdProfile:rn managed object property"
    ::= { cfprApAaaPwdProfileEntry 3 }

cfprApAaaPwdProfileChangeCount OBJECT-TYPE
    SYNTAX       Gauge32
    MAX-ACCESS   read-only
    STATUS       current
    DESCRIPTION
        "Cisco Firepower aaa:PwdProfile:changeCount managed
        object property"
    ::= { cfprApAaaPwdProfileEntry 4 }

cfprApAaaPwdProfileChangeDuringInterval OBJECT-TYPE
    SYNTAX       CfprApAaaPwdPolicy
    MAX-ACCESS   read-only
    STATUS       current
    DESCRIPTION
        "Cisco Firepower aaa:PwdProfile:changeDuringInterval
        managed object property"
    ::= { cfprApAaaPwdProfileEntry 5 }

cfprApAaaPwdProfileChangeInterval OBJECT-TYPE
    SYNTAX       Gauge32
    MAX-ACCESS   read-only
    STATUS       current
    DESCRIPTION
        "Cisco Firepower aaa:PwdProfile:changeInterval
        managed object property"
    ::= { cfprApAaaPwdProfileEntry 6 }

cfprApAaaPwdProfileExpirationWarnTime OBJECT-TYPE
    SYNTAX       Gauge32
    MAX-ACCESS   read-only
    STATUS       current
    DESCRIPTION
        "Cisco Firepower aaa:PwdProfile:expirationWarnTime
        managed object property"
    ::= { cfprApAaaPwdProfileEntry 8 }

cfprApAaaPwdProfileHistoryCount OBJECT-TYPE
    SYNTAX       Gauge32
    MAX-ACCESS   read-only
    STATUS       current
    DESCRIPTION
        "Cisco Firepower aaa:PwdProfile:historyCount managed
        object property"
    ::= { cfprApAaaPwdProfileEntry 9 }

cfprApAaaPwdProfileNoChangeInterval OBJECT-TYPE
    SYNTAX       Gauge32
    MAX-ACCESS   read-only
    STATUS       current
    DESCRIPTION
        "Cisco Firepower aaa:PwdProfile:noChangeInterval
        managed object property"
    ::= { cfprApAaaPwdProfileEntry 12 }

cfprApAaaRadiusEpTable OBJECT-TYPE
    SYNTAX           SEQUENCE OF CfprApAaaRadiusEpEntry
    MAX-ACCESS       not-accessible
    STATUS           current
    DESCRIPTION
        "Cisco Firepower aaa:RadiusEp managed object table"
    ::= { cfprApAaaObjects 30 }

cfprApAaaRadiusEpEntry OBJECT-TYPE
    SYNTAX           CfprApAaaRadiusEpEntry
    MAX-ACCESS       not-accessible
    STATUS           current
    DESCRIPTION
        "Entry for the cfprApAaaRadiusEpTable table."
    INDEX { cfprApAaaRadiusEpInstanceId }
    ::= { cfprApAaaRadiusEpTable 1 }

CfprApAaaRadiusEpEntry ::= SEQUENCE {
    cfprApAaaRadiusEpInstanceId                                      CfprApManagedObjectId,
    cfprApAaaRadiusEpDn                                              CfprApManagedObjectDn,
    cfprApAaaRadiusEpRn                                              SnmpAdminString,
    cfprApAaaRadiusEpDescr                                           SnmpAdminString,
    cfprApAaaRadiusEpFsmDescr                                        SnmpAdminString,
    cfprApAaaRadiusEpFsmPrev                                         SnmpAdminString,
    cfprApAaaRadiusEpFsmProgr                                        Gauge32,
    cfprApAaaRadiusEpFsmRmtInvErrCode                                Gauge32,
    cfprApAaaRadiusEpFsmRmtInvErrDescr                               SnmpAdminString,
    cfprApAaaRadiusEpFsmRmtInvRslt                                   CfprApConditionRemoteInvRslt,
    cfprApAaaRadiusEpFsmStageDescr                                   SnmpAdminString,
    cfprApAaaRadiusEpFsmStamp                                        DateAndTime,
    cfprApAaaRadiusEpFsmStatus                                       SnmpAdminString,
    cfprApAaaRadiusEpFsmTry                                          Gauge32,
    cfprApAaaRadiusEpIntId                                           SnmpAdminString,
    cfprApAaaRadiusEpName                                            SnmpAdminString,
    cfprApAaaRadiusEpPolicyLevel                                     Gauge32,
    cfprApAaaRadiusEpPolicyOwner                                     CfprApPolicyPolicyOwner,
    cfprApAaaRadiusEpRetries                                         Gauge32,
    cfprApAaaRadiusEpTimeout                                         Gauge32
}

cfprApAaaRadiusEpInstanceId OBJECT-TYPE
    SYNTAX       CfprApManagedObjectId
    MAX-ACCESS   not-accessible
    STATUS       current
    DESCRIPTION
        "Instance identifier of the managed object."
    ::= { cfprApAaaRadiusEpEntry 1 }

cfprApAaaRadiusEpDn OBJECT-TYPE
    SYNTAX       CfprApManagedObjectDn
    MAX-ACCESS   read-only
    STATUS       current
    DESCRIPTION
        "Cisco Firepower aaa:RadiusEp:dn managed object property"
    ::= { cfprApAaaRadiusEpEntry 2 }

cfprApAaaRadiusEpRn OBJECT-TYPE
    SYNTAX       SnmpAdminString
    MAX-ACCESS   read-only
    STATUS       current
    DESCRIPTION
        "Cisco Firepower aaa:RadiusEp:rn managed object property"
    ::= { cfprApAaaRadiusEpEntry 3 }

cfprApAaaRadiusEpDescr OBJECT-TYPE
    SYNTAX       SnmpAdminString
    MAX-ACCESS   read-only
    STATUS       current
    DESCRIPTION
        "Cisco Firepower aaa:RadiusEp:descr managed object property"
    ::= { cfprApAaaRadiusEpEntry 4 }

cfprApAaaRadiusEpFsmDescr OBJECT-TYPE
    SYNTAX       SnmpAdminString
    MAX-ACCESS   read-only
    STATUS       current
    DESCRIPTION
        "Cisco Firepower aaa:RadiusEp:fsmDescr managed object property"
    ::= { cfprApAaaRadiusEpEntry 5 }

cfprApAaaRadiusEpFsmPrev OBJECT-TYPE
    SYNTAX       SnmpAdminString
    MAX-ACCESS   read-only
    STATUS       current
    DESCRIPTION
        "Cisco Firepower aaa:RadiusEp:fsmPrev managed object property"
    ::= { cfprApAaaRadiusEpEntry 6 }

cfprApAaaRadiusEpFsmProgr OBJECT-TYPE
    SYNTAX       Gauge32
    MAX-ACCESS   read-only
    STATUS       current
    DESCRIPTION
        "Cisco Firepower aaa:RadiusEp:fsmProgr managed object property"
    ::= { cfprApAaaRadiusEpEntry 7 }

cfprApAaaRadiusEpFsmRmtInvErrCode OBJECT-TYPE
    SYNTAX       Gauge32
    MAX-ACCESS   read-only
    STATUS       current
    DESCRIPTION
        "Cisco Firepower aaa:RadiusEp:fsmRmtInvErrCode
        managed object property"
    ::= { cfprApAaaRadiusEpEntry 8 }

cfprApAaaRadiusEpFsmRmtInvErrDescr OBJECT-TYPE
    SYNTAX       SnmpAdminString
    MAX-ACCESS   read-only
    STATUS       current
    DESCRIPTION
        "Cisco Firepower aaa:RadiusEp:fsmRmtInvErrDescr
        managed object property"
    ::= { cfprApAaaRadiusEpEntry 9 }

cfprApAaaRadiusEpFsmRmtInvRslt OBJECT-TYPE
    SYNTAX       CfprApConditionRemoteInvRslt
    MAX-ACCESS   read-only
    STATUS       current
    DESCRIPTION
        "Cisco Firepower aaa:RadiusEp:fsmRmtInvRslt managed
        object property"
    ::= { cfprApAaaRadiusEpEntry 10 }

cfprApAaaRadiusEpFsmStageDescr OBJECT-TYPE
    SYNTAX       SnmpAdminString
    MAX-ACCESS   read-only
    STATUS       current
    DESCRIPTION
        "Cisco Firepower aaa:RadiusEp:fsmStageDescr managed
        object property"
    ::= { cfprApAaaRadiusEpEntry 11 }

cfprApAaaRadiusEpFsmStamp OBJECT-TYPE
    SYNTAX       DateAndTime
    MAX-ACCESS   read-only
    STATUS       current
    DESCRIPTION
        "Cisco Firepower aaa:RadiusEp:fsmStamp managed object property"
    ::= { cfprApAaaRadiusEpEntry 12 }

cfprApAaaRadiusEpFsmStatus OBJECT-TYPE
    SYNTAX       SnmpAdminString
    MAX-ACCESS   read-only
    STATUS       current
    DESCRIPTION
        "Cisco Firepower aaa:RadiusEp:fsmStatus managed object property"
    ::= { cfprApAaaRadiusEpEntry 13 }

cfprApAaaRadiusEpFsmTry OBJECT-TYPE
    SYNTAX       Gauge32
    MAX-ACCESS   read-only
    STATUS       current
    DESCRIPTION
        "Cisco Firepower aaa:RadiusEp:fsmTry managed object property"
    ::= { cfprApAaaRadiusEpEntry 14 }

cfprApAaaRadiusEpIntId OBJECT-TYPE
    SYNTAX       SnmpAdminString
    MAX-ACCESS   read-only
    STATUS       current
    DESCRIPTION
        "Cisco Firepower aaa:RadiusEp:intId managed object property"
    ::= { cfprApAaaRadiusEpEntry 15 }

cfprApAaaRadiusEpName OBJECT-TYPE
    SYNTAX       SnmpAdminString
    MAX-ACCESS   read-only
    STATUS       current
    DESCRIPTION
        "Cisco Firepower aaa:RadiusEp:name managed object property"
    ::= { cfprApAaaRadiusEpEntry 16 }

cfprApAaaRadiusEpPolicyLevel OBJECT-TYPE
    SYNTAX       Gauge32
    MAX-ACCESS   read-only
    STATUS       current
    DESCRIPTION
        "Cisco Firepower aaa:RadiusEp:policyLevel managed object property"
    ::= { cfprApAaaRadiusEpEntry 17 }

cfprApAaaRadiusEpPolicyOwner OBJECT-TYPE
    SYNTAX       CfprApPolicyPolicyOwner
    MAX-ACCESS   read-only
    STATUS       current
    DESCRIPTION
        "Cisco Firepower aaa:RadiusEp:policyOwner managed object property"
    ::= { cfprApAaaRadiusEpEntry 18 }

cfprApAaaRadiusEpRetries OBJECT-TYPE
    SYNTAX       Gauge32
    MAX-ACCESS   read-only
    STATUS       current
    DESCRIPTION
        "Cisco Firepower aaa:RadiusEp:retries managed object property"
    ::= { cfprApAaaRadiusEpEntry 19 }

cfprApAaaRadiusEpTimeout OBJECT-TYPE
    SYNTAX       Gauge32
    MAX-ACCESS   read-only
    STATUS       current
    DESCRIPTION
        "Cisco Firepower aaa:RadiusEp:timeout managed object property"
    ::= { cfprApAaaRadiusEpEntry 20 }

cfprApAaaRadiusEpFsmTable OBJECT-TYPE
    SYNTAX           SEQUENCE OF CfprApAaaRadiusEpFsmEntry
    MAX-ACCESS       not-accessible
    STATUS           current
    DESCRIPTION
        "Cisco Firepower aaa:RadiusEpFsm managed object table"
    ::= { cfprApAaaObjects 31 }

cfprApAaaRadiusEpFsmEntry OBJECT-TYPE
    SYNTAX           CfprApAaaRadiusEpFsmEntry
    MAX-ACCESS       not-accessible
    STATUS           current
    DESCRIPTION
        "Entry for the cfprApAaaRadiusEpFsmTable table."
    INDEX { cfprApAaaRadiusEpFsmInstanceId }
    ::= { cfprApAaaRadiusEpFsmTable 1 }

CfprApAaaRadiusEpFsmEntry ::= SEQUENCE {
    cfprApAaaRadiusEpFsmInstanceId                                   CfprApManagedObjectId,
    cfprApAaaRadiusEpFsmDn                                           CfprApManagedObjectDn,
    cfprApAaaRadiusEpFsmRn                                           SnmpAdminString,
    cfprApAaaRadiusEpFsmCompletionTime                               DateAndTime,
    cfprApAaaRadiusEpFsmCurrentFsm                                   CfprApAaaRadiusEpFsmCurrentFsm,
    cfprApAaaRadiusEpFsmDescrData                                    SnmpAdminString,
    cfprApAaaRadiusEpFsmFsmStatus                                    CfprApFsmFsmStageStatus,
    cfprApAaaRadiusEpFsmProgress                                     Gauge32,
    cfprApAaaRadiusEpFsmRmtErrCode                                   Gauge32,
    cfprApAaaRadiusEpFsmRmtErrDescr                                  SnmpAdminString,
    cfprApAaaRadiusEpFsmRmtRslt                                      CfprApConditionRemoteInvRslt
}

cfprApAaaRadiusEpFsmInstanceId OBJECT-TYPE
    SYNTAX       CfprApManagedObjectId
    MAX-ACCESS   not-accessible
    STATUS       current
    DESCRIPTION
        "Instance identifier of the managed object."
    ::= { cfprApAaaRadiusEpFsmEntry 1 }

cfprApAaaRadiusEpFsmDn OBJECT-TYPE
    SYNTAX       CfprApManagedObjectDn
    MAX-ACCESS   read-only
    STATUS       current
    DESCRIPTION
        "Cisco Firepower aaa:RadiusEpFsm:dn managed object property"
    ::= { cfprApAaaRadiusEpFsmEntry 2 }

cfprApAaaRadiusEpFsmRn OBJECT-TYPE
    SYNTAX       SnmpAdminString
    MAX-ACCESS   read-only
    STATUS       current
    DESCRIPTION
        "Cisco Firepower aaa:RadiusEpFsm:rn managed object property"
    ::= { cfprApAaaRadiusEpFsmEntry 3 }

cfprApAaaRadiusEpFsmCompletionTime OBJECT-TYPE
    SYNTAX       DateAndTime
    MAX-ACCESS   read-only
    STATUS       current
    DESCRIPTION
        "Cisco Firepower aaa:RadiusEpFsm:completionTime
        managed object property"
    ::= { cfprApAaaRadiusEpFsmEntry 4 }

cfprApAaaRadiusEpFsmCurrentFsm OBJECT-TYPE
    SYNTAX       CfprApAaaRadiusEpFsmCurrentFsm
    MAX-ACCESS   read-only
    STATUS       current
    DESCRIPTION
        "Cisco Firepower aaa:RadiusEpFsm:currentFsm managed
        object property"
    ::= { cfprApAaaRadiusEpFsmEntry 5 }

cfprApAaaRadiusEpFsmDescrData OBJECT-TYPE
    SYNTAX       SnmpAdminString
    MAX-ACCESS   read-only
    STATUS       current
    DESCRIPTION
        "Cisco Firepower aaa:RadiusEpFsm:descr managed object property"
    ::= { cfprApAaaRadiusEpFsmEntry 6 }

cfprApAaaRadiusEpFsmFsmStatus OBJECT-TYPE
    SYNTAX       CfprApFsmFsmStageStatus
    MAX-ACCESS   read-only
    STATUS       current
    DESCRIPTION
        "Cisco Firepower aaa:RadiusEpFsm:fsmStatus managed
        object property"
    ::= { cfprApAaaRadiusEpFsmEntry 7 }

cfprApAaaRadiusEpFsmProgress OBJECT-TYPE
    SYNTAX       Gauge32
    MAX-ACCESS   read-only
    STATUS       current
    DESCRIPTION
        "Cisco Firepower aaa:RadiusEpFsm:progress managed object property"
    ::= { cfprApAaaRadiusEpFsmEntry 8 }

cfprApAaaRadiusEpFsmRmtErrCode OBJECT-TYPE
    SYNTAX       Gauge32
    MAX-ACCESS   read-only
    STATUS       current
    DESCRIPTION
        "Cisco Firepower aaa:RadiusEpFsm:rmtErrCode managed
        object property"
    ::= { cfprApAaaRadiusEpFsmEntry 9 }

cfprApAaaRadiusEpFsmRmtErrDescr OBJECT-TYPE
    SYNTAX       SnmpAdminString
    MAX-ACCESS   read-only
    STATUS       current
    DESCRIPTION
        "Cisco Firepower aaa:RadiusEpFsm:rmtErrDescr managed
        object property"
    ::= { cfprApAaaRadiusEpFsmEntry 10 }

cfprApAaaRadiusEpFsmRmtRslt OBJECT-TYPE
    SYNTAX       CfprApConditionRemoteInvRslt
    MAX-ACCESS   read-only
    STATUS       current
    DESCRIPTION
        "Cisco Firepower aaa:RadiusEpFsm:rmtRslt managed object property"
    ::= { cfprApAaaRadiusEpFsmEntry 11 }

cfprApAaaRadiusEpFsmStageTable OBJECT-TYPE
    SYNTAX           SEQUENCE OF CfprApAaaRadiusEpFsmStageEntry
    MAX-ACCESS       not-accessible
    STATUS           current
    DESCRIPTION
        "Cisco Firepower aaa:RadiusEpFsmStage managed object table"
    ::= { cfprApAaaObjects 32 }

cfprApAaaRadiusEpFsmStageEntry OBJECT-TYPE
    SYNTAX           CfprApAaaRadiusEpFsmStageEntry
    MAX-ACCESS       not-accessible
    STATUS           current
    DESCRIPTION
        "Entry for the cfprApAaaRadiusEpFsmStageTable table."
    INDEX { cfprApAaaRadiusEpFsmStageInstanceId }
    ::= { cfprApAaaRadiusEpFsmStageTable 1 }

CfprApAaaRadiusEpFsmStageEntry ::= SEQUENCE {
    cfprApAaaRadiusEpFsmStageInstanceId                              CfprApManagedObjectId,
    cfprApAaaRadiusEpFsmStageDn                                      CfprApManagedObjectDn,
    cfprApAaaRadiusEpFsmStageRn                                      SnmpAdminString,
    cfprApAaaRadiusEpFsmStageDescrData                               SnmpAdminString,
    cfprApAaaRadiusEpFsmStageLastUpdateTime                          DateAndTime,
    cfprApAaaRadiusEpFsmStageName                                    CfprApAaaRadiusEpFsmStageName,
    cfprApAaaRadiusEpFsmStageOrder                                   Gauge32,
    cfprApAaaRadiusEpFsmStageRetry                                   Gauge32,
    cfprApAaaRadiusEpFsmStageStageStatus                             CfprApFsmFsmStageStatus
}

cfprApAaaRadiusEpFsmStageInstanceId OBJECT-TYPE
    SYNTAX       CfprApManagedObjectId
    MAX-ACCESS   not-accessible
    STATUS       current
    DESCRIPTION
        "Instance identifier of the managed object."
    ::= { cfprApAaaRadiusEpFsmStageEntry 1 }

cfprApAaaRadiusEpFsmStageDn OBJECT-TYPE
    SYNTAX       CfprApManagedObjectDn
    MAX-ACCESS   read-only
    STATUS       current
    DESCRIPTION
        "Cisco Firepower aaa:RadiusEpFsmStage:dn managed object property"
    ::= { cfprApAaaRadiusEpFsmStageEntry 2 }

cfprApAaaRadiusEpFsmStageRn OBJECT-TYPE
    SYNTAX       SnmpAdminString
    MAX-ACCESS   read-only
    STATUS       current
    DESCRIPTION
        "Cisco Firepower aaa:RadiusEpFsmStage:rn managed object property"
    ::= { cfprApAaaRadiusEpFsmStageEntry 3 }

cfprApAaaRadiusEpFsmStageDescrData OBJECT-TYPE
    SYNTAX       SnmpAdminString
    MAX-ACCESS   read-only
    STATUS       current
    DESCRIPTION
        "Cisco Firepower aaa:RadiusEpFsmStage:descr managed
        object property"
    ::= { cfprApAaaRadiusEpFsmStageEntry 4 }

cfprApAaaRadiusEpFsmStageLastUpdateTime OBJECT-TYPE
    SYNTAX       DateAndTime
    MAX-ACCESS   read-only
    STATUS       current
    DESCRIPTION
        "Cisco Firepower aaa:RadiusEpFsmStage:lastUpdateTime
        managed object property"
    ::= { cfprApAaaRadiusEpFsmStageEntry 5 }

cfprApAaaRadiusEpFsmStageName OBJECT-TYPE
    SYNTAX       CfprApAaaRadiusEpFsmStageName
    MAX-ACCESS   read-only
    STATUS       current
    DESCRIPTION
        "Cisco Firepower aaa:RadiusEpFsmStage:name managed
        object property"
    ::= { cfprApAaaRadiusEpFsmStageEntry 6 }

cfprApAaaRadiusEpFsmStageOrder OBJECT-TYPE
    SYNTAX       Gauge32
    MAX-ACCESS   read-only
    STATUS       current
    DESCRIPTION
        "Cisco Firepower aaa:RadiusEpFsmStage:order managed
        object property"
    ::= { cfprApAaaRadiusEpFsmStageEntry 7 }

cfprApAaaRadiusEpFsmStageRetry OBJECT-TYPE
    SYNTAX       Gauge32
    MAX-ACCESS   read-only
    STATUS       current
    DESCRIPTION
        "Cisco Firepower aaa:RadiusEpFsmStage:retry managed
        object property"
    ::= { cfprApAaaRadiusEpFsmStageEntry 8 }

cfprApAaaRadiusEpFsmStageStageStatus OBJECT-TYPE
    SYNTAX       CfprApFsmFsmStageStatus
    MAX-ACCESS   read-only
    STATUS       current
    DESCRIPTION
        "Cisco Firepower aaa:RadiusEpFsmStage:stageStatus
        managed object property"
    ::= { cfprApAaaRadiusEpFsmStageEntry 9 }

cfprApAaaRadiusProviderTable OBJECT-TYPE
    SYNTAX           SEQUENCE OF CfprApAaaRadiusProviderEntry
    MAX-ACCESS       not-accessible
    STATUS           current
    DESCRIPTION
        "Cisco Firepower aaa:RadiusProvider managed object table"
    ::= { cfprApAaaObjects 33 }

cfprApAaaRadiusProviderEntry OBJECT-TYPE
    SYNTAX           CfprApAaaRadiusProviderEntry
    MAX-ACCESS       not-accessible
    STATUS           current
    DESCRIPTION
        "Entry for the cfprApAaaRadiusProviderTable table."
    INDEX { cfprApAaaRadiusProviderInstanceId }
    ::= { cfprApAaaRadiusProviderTable 1 }

CfprApAaaRadiusProviderEntry ::= SEQUENCE {
    cfprApAaaRadiusProviderInstanceId                                CfprApManagedObjectId,
    cfprApAaaRadiusProviderDn                                        CfprApManagedObjectDn,
    cfprApAaaRadiusProviderRn                                        SnmpAdminString,
    cfprApAaaRadiusProviderAuthPort                                  Gauge32,
    cfprApAaaRadiusProviderDescr                                     SnmpAdminString,
    cfprApAaaRadiusProviderEncKey                                    SnmpAdminString,
    cfprApAaaRadiusProviderKey                                       SnmpAdminString,
    cfprApAaaRadiusProviderKeySet                                    TruthValue,
    cfprApAaaRadiusProviderName                                      SnmpAdminString,
    cfprApAaaRadiusProviderOrder                                     Gauge32,
    cfprApAaaRadiusProviderRetries                                   Gauge32,
    cfprApAaaRadiusProviderService                                   CfprApAaaRadiusService,
    cfprApAaaRadiusProviderTimeout                                   Gauge32
}

cfprApAaaRadiusProviderInstanceId OBJECT-TYPE
    SYNTAX       CfprApManagedObjectId
    MAX-ACCESS   not-accessible
    STATUS       current
    DESCRIPTION
        "Instance identifier of the managed object."
    ::= { cfprApAaaRadiusProviderEntry 1 }

cfprApAaaRadiusProviderDn OBJECT-TYPE
    SYNTAX       CfprApManagedObjectDn
    MAX-ACCESS   read-only
    STATUS       current
    DESCRIPTION
        "Cisco Firepower aaa:RadiusProvider:dn managed object property"
    ::= { cfprApAaaRadiusProviderEntry 2 }

cfprApAaaRadiusProviderRn OBJECT-TYPE
    SYNTAX       SnmpAdminString
    MAX-ACCESS   read-only
    STATUS       current
    DESCRIPTION
        "Cisco Firepower aaa:RadiusProvider:rn managed object property"
    ::= { cfprApAaaRadiusProviderEntry 3 }

cfprApAaaRadiusProviderAuthPort OBJECT-TYPE
    SYNTAX       Gauge32
    MAX-ACCESS   read-only
    STATUS       current
    DESCRIPTION
        "Cisco Firepower aaa:RadiusProvider:authPort managed
        object property"
    ::= { cfprApAaaRadiusProviderEntry 4 }

cfprApAaaRadiusProviderDescr OBJECT-TYPE
    SYNTAX       SnmpAdminString
    MAX-ACCESS   read-only
    STATUS       current
    DESCRIPTION
        "Cisco Firepower aaa:RadiusProvider:descr managed object property"
    ::= { cfprApAaaRadiusProviderEntry 5 }

cfprApAaaRadiusProviderEncKey OBJECT-TYPE
    SYNTAX       SnmpAdminString
    MAX-ACCESS   read-only
    STATUS       current
    DESCRIPTION
        "Cisco Firepower aaa:RadiusProvider:encKey managed
        object property"
    ::= { cfprApAaaRadiusProviderEntry 6 }

cfprApAaaRadiusProviderKey OBJECT-TYPE
    SYNTAX       SnmpAdminString
    MAX-ACCESS   read-only
    STATUS       current
    DESCRIPTION
        "Cisco Firepower aaa:RadiusProvider:key managed object property"
    ::= { cfprApAaaRadiusProviderEntry 7 }

cfprApAaaRadiusProviderKeySet OBJECT-TYPE
    SYNTAX       TruthValue
    MAX-ACCESS   read-only
    STATUS       current
    DESCRIPTION
        "Cisco Firepower aaa:RadiusProvider:keySet managed
        object property"
    ::= { cfprApAaaRadiusProviderEntry 8 }

cfprApAaaRadiusProviderName OBJECT-TYPE
    SYNTAX       SnmpAdminString
    MAX-ACCESS   read-only
    STATUS       current
    DESCRIPTION
        "Cisco Firepower aaa:RadiusProvider:name managed object property"
    ::= { cfprApAaaRadiusProviderEntry 9 }

cfprApAaaRadiusProviderOrder OBJECT-TYPE
    SYNTAX       Gauge32
    MAX-ACCESS   read-only
    STATUS       current
    DESCRIPTION
        "Cisco Firepower aaa:RadiusProvider:order managed object property"
    ::= { cfprApAaaRadiusProviderEntry 10 }

cfprApAaaRadiusProviderRetries OBJECT-TYPE
    SYNTAX       Gauge32
    MAX-ACCESS   read-only
    STATUS       current
    DESCRIPTION
        "Cisco Firepower aaa:RadiusProvider:retries managed
        object property"
    ::= { cfprApAaaRadiusProviderEntry 11 }

cfprApAaaRadiusProviderService OBJECT-TYPE
    SYNTAX       CfprApAaaRadiusService
    MAX-ACCESS   read-only
    STATUS       current
    DESCRIPTION
        "Cisco Firepower aaa:RadiusProvider:service managed
        object property"
    ::= { cfprApAaaRadiusProviderEntry 12 }

cfprApAaaRadiusProviderTimeout OBJECT-TYPE
    SYNTAX       Gauge32
    MAX-ACCESS   read-only
    STATUS       current
    DESCRIPTION
        "Cisco Firepower aaa:RadiusProvider:timeout managed
        object property"
    ::= { cfprApAaaRadiusProviderEntry 13 }

cfprApAaaRealmFsmTable OBJECT-TYPE
    SYNTAX           SEQUENCE OF CfprApAaaRealmFsmEntry
    MAX-ACCESS       not-accessible
    STATUS           current
    DESCRIPTION
        "Cisco Firepower aaa:RealmFsm managed object table"
    ::= { cfprApAaaObjects 34 }

cfprApAaaRealmFsmEntry OBJECT-TYPE
    SYNTAX           CfprApAaaRealmFsmEntry
    MAX-ACCESS       not-accessible
    STATUS           current
    DESCRIPTION
        "Entry for the cfprApAaaRealmFsmTable table."
    INDEX { cfprApAaaRealmFsmInstanceId }
    ::= { cfprApAaaRealmFsmTable 1 }

CfprApAaaRealmFsmEntry ::= SEQUENCE {
    cfprApAaaRealmFsmInstanceId                                      CfprApManagedObjectId,
    cfprApAaaRealmFsmDn                                              CfprApManagedObjectDn,
    cfprApAaaRealmFsmRn                                              SnmpAdminString,
    cfprApAaaRealmFsmCompletionTime                                  DateAndTime,
    cfprApAaaRealmFsmCurrentFsm                                      CfprApAaaRealmFsmCurrentFsm,
    cfprApAaaRealmFsmDescr                                           SnmpAdminString,
    cfprApAaaRealmFsmFsmStatus                                       CfprApFsmFsmStageStatus,
    cfprApAaaRealmFsmProgress                                        Gauge32,
    cfprApAaaRealmFsmRmtErrCode                                      Gauge32,
    cfprApAaaRealmFsmRmtErrDescr                                     SnmpAdminString,
    cfprApAaaRealmFsmRmtRslt                                         CfprApConditionRemoteInvRslt
}

cfprApAaaRealmFsmInstanceId OBJECT-TYPE
    SYNTAX       CfprApManagedObjectId
    MAX-ACCESS   not-accessible
    STATUS       current
    DESCRIPTION
        "Instance identifier of the managed object."
    ::= { cfprApAaaRealmFsmEntry 1 }

cfprApAaaRealmFsmDn OBJECT-TYPE
    SYNTAX       CfprApManagedObjectDn
    MAX-ACCESS   read-only
    STATUS       current
    DESCRIPTION
        "Cisco Firepower aaa:RealmFsm:dn managed object property"
    ::= { cfprApAaaRealmFsmEntry 2 }

cfprApAaaRealmFsmRn OBJECT-TYPE
    SYNTAX       SnmpAdminString
    MAX-ACCESS   read-only
    STATUS       current
    DESCRIPTION
        "Cisco Firepower aaa:RealmFsm:rn managed object property"
    ::= { cfprApAaaRealmFsmEntry 3 }

cfprApAaaRealmFsmCompletionTime OBJECT-TYPE
    SYNTAX       DateAndTime
    MAX-ACCESS   read-only
    STATUS       current
    DESCRIPTION
        "Cisco Firepower aaa:RealmFsm:completionTime managed
        object property"
    ::= { cfprApAaaRealmFsmEntry 4 }

cfprApAaaRealmFsmCurrentFsm OBJECT-TYPE
    SYNTAX       CfprApAaaRealmFsmCurrentFsm
    MAX-ACCESS   read-only
    STATUS       current
    DESCRIPTION
        "Cisco Firepower aaa:RealmFsm:currentFsm managed object property"
    ::= { cfprApAaaRealmFsmEntry 5 }

cfprApAaaRealmFsmDescr OBJECT-TYPE
    SYNTAX       SnmpAdminString
    MAX-ACCESS   read-only
    STATUS       current
    DESCRIPTION
        "Cisco Firepower aaa:RealmFsm:descr managed object property"
    ::= { cfprApAaaRealmFsmEntry 6 }

cfprApAaaRealmFsmFsmStatus OBJECT-TYPE
    SYNTAX       CfprApFsmFsmStageStatus
    MAX-ACCESS   read-only
    STATUS       current
    DESCRIPTION
        "Cisco Firepower aaa:RealmFsm:fsmStatus managed object property"
    ::= { cfprApAaaRealmFsmEntry 7 }

cfprApAaaRealmFsmProgress OBJECT-TYPE
    SYNTAX       Gauge32
    MAX-ACCESS   read-only
    STATUS       current
    DESCRIPTION
        "Cisco Firepower aaa:RealmFsm:progress managed object property"
    ::= { cfprApAaaRealmFsmEntry 8 }

cfprApAaaRealmFsmRmtErrCode OBJECT-TYPE
    SYNTAX       Gauge32
    MAX-ACCESS   read-only
    STATUS       current
    DESCRIPTION
        "Cisco Firepower aaa:RealmFsm:rmtErrCode managed object property"
    ::= { cfprApAaaRealmFsmEntry 9 }

cfprApAaaRealmFsmRmtErrDescr OBJECT-TYPE
    SYNTAX       SnmpAdminString
    MAX-ACCESS   read-only
    STATUS       current
    DESCRIPTION
        "Cisco Firepower aaa:RealmFsm:rmtErrDescr managed object property"
    ::= { cfprApAaaRealmFsmEntry 10 }

cfprApAaaRealmFsmRmtRslt OBJECT-TYPE
    SYNTAX       CfprApConditionRemoteInvRslt
    MAX-ACCESS   read-only
    STATUS       current
    DESCRIPTION
        "Cisco Firepower aaa:RealmFsm:rmtRslt managed object property"
    ::= { cfprApAaaRealmFsmEntry 11 }

cfprApAaaRealmFsmStageTable OBJECT-TYPE
    SYNTAX           SEQUENCE OF CfprApAaaRealmFsmStageEntry
    MAX-ACCESS       not-accessible
    STATUS           current
    DESCRIPTION
        "Cisco Firepower aaa:RealmFsmStage managed object table"
    ::= { cfprApAaaObjects 35 }

cfprApAaaRealmFsmStageEntry OBJECT-TYPE
    SYNTAX           CfprApAaaRealmFsmStageEntry
    MAX-ACCESS       not-accessible
    STATUS           current
    DESCRIPTION
        "Entry for the cfprApAaaRealmFsmStageTable table."
    INDEX { cfprApAaaRealmFsmStageInstanceId }
    ::= { cfprApAaaRealmFsmStageTable 1 }

CfprApAaaRealmFsmStageEntry ::= SEQUENCE {
    cfprApAaaRealmFsmStageInstanceId                                 CfprApManagedObjectId,
    cfprApAaaRealmFsmStageDn                                         CfprApManagedObjectDn,
    cfprApAaaRealmFsmStageRn                                         SnmpAdminString,
    cfprApAaaRealmFsmStageDescr                                      SnmpAdminString,
    cfprApAaaRealmFsmStageLastUpdateTime                             DateAndTime,
    cfprApAaaRealmFsmStageName                                       CfprApAaaRealmFsmStageName,
    cfprApAaaRealmFsmStageOrder                                      Gauge32,
    cfprApAaaRealmFsmStageRetry                                      Gauge32,
    cfprApAaaRealmFsmStageStageStatus                                CfprApFsmFsmStageStatus
}

cfprApAaaRealmFsmStageInstanceId OBJECT-TYPE
    SYNTAX       CfprApManagedObjectId
    MAX-ACCESS   not-accessible
    STATUS       current
    DESCRIPTION
        "Instance identifier of the managed object."
    ::= { cfprApAaaRealmFsmStageEntry 1 }

cfprApAaaRealmFsmStageDn OBJECT-TYPE
    SYNTAX       CfprApManagedObjectDn
    MAX-ACCESS   read-only
    STATUS       current
    DESCRIPTION
        "Cisco Firepower aaa:RealmFsmStage:dn managed object property"
    ::= { cfprApAaaRealmFsmStageEntry 2 }

cfprApAaaRealmFsmStageRn OBJECT-TYPE
    SYNTAX       SnmpAdminString
    MAX-ACCESS   read-only
    STATUS       current
    DESCRIPTION
        "Cisco Firepower aaa:RealmFsmStage:rn managed object property"
    ::= { cfprApAaaRealmFsmStageEntry 3 }

cfprApAaaRealmFsmStageDescr OBJECT-TYPE
    SYNTAX       SnmpAdminString
    MAX-ACCESS   read-only
    STATUS       current
    DESCRIPTION
        "Cisco Firepower aaa:RealmFsmStage:descr managed object property"
    ::= { cfprApAaaRealmFsmStageEntry 4 }

cfprApAaaRealmFsmStageLastUpdateTime OBJECT-TYPE
    SYNTAX       DateAndTime
    MAX-ACCESS   read-only
    STATUS       current
    DESCRIPTION
        "Cisco Firepower aaa:RealmFsmStage:lastUpdateTime
        managed object property"
    ::= { cfprApAaaRealmFsmStageEntry 5 }

cfprApAaaRealmFsmStageName OBJECT-TYPE
    SYNTAX       CfprApAaaRealmFsmStageName
    MAX-ACCESS   read-only
    STATUS       current
    DESCRIPTION
        "Cisco Firepower aaa:RealmFsmStage:name managed object property"
    ::= { cfprApAaaRealmFsmStageEntry 6 }

cfprApAaaRealmFsmStageOrder OBJECT-TYPE
    SYNTAX       Gauge32
    MAX-ACCESS   read-only
    STATUS       current
    DESCRIPTION
        "Cisco Firepower aaa:RealmFsmStage:order managed object property"
    ::= { cfprApAaaRealmFsmStageEntry 7 }

cfprApAaaRealmFsmStageRetry OBJECT-TYPE
    SYNTAX       Gauge32
    MAX-ACCESS   read-only
    STATUS       current
    DESCRIPTION
        "Cisco Firepower aaa:RealmFsmStage:retry managed object property"
    ::= { cfprApAaaRealmFsmStageEntry 8 }

cfprApAaaRealmFsmStageStageStatus OBJECT-TYPE
    SYNTAX       CfprApFsmFsmStageStatus
    MAX-ACCESS   read-only
    STATUS       current
    DESCRIPTION
        "Cisco Firepower aaa:RealmFsmStage:stageStatus
        managed object property"
    ::= { cfprApAaaRealmFsmStageEntry 9 }

cfprApAaaRealmFsmTaskTable OBJECT-TYPE
    SYNTAX           SEQUENCE OF CfprApAaaRealmFsmTaskEntry
    MAX-ACCESS       not-accessible
    STATUS           current
    DESCRIPTION
        "Cisco Firepower aaa:RealmFsmTask managed object table"
    ::= { cfprApAaaObjects 36 }

cfprApAaaRealmFsmTaskEntry OBJECT-TYPE
    SYNTAX           CfprApAaaRealmFsmTaskEntry
    MAX-ACCESS       not-accessible
    STATUS           current
    DESCRIPTION
        "Entry for the cfprApAaaRealmFsmTaskTable table."
    INDEX { cfprApAaaRealmFsmTaskInstanceId }
    ::= { cfprApAaaRealmFsmTaskTable 1 }

CfprApAaaRealmFsmTaskEntry ::= SEQUENCE {
    cfprApAaaRealmFsmTaskInstanceId                                  CfprApManagedObjectId,
    cfprApAaaRealmFsmTaskDn                                          CfprApManagedObjectDn,
    cfprApAaaRealmFsmTaskRn                                          SnmpAdminString,
    cfprApAaaRealmFsmTaskCompletion                                  CfprApFsmCompletion,
    cfprApAaaRealmFsmTaskFlags                                       CfprApFsmFlags,
    cfprApAaaRealmFsmTaskItem                                        CfprApAaaRealmFsmTaskItem,
    cfprApAaaRealmFsmTaskSeqId                                       Gauge32
}

cfprApAaaRealmFsmTaskInstanceId OBJECT-TYPE
    SYNTAX       CfprApManagedObjectId
    MAX-ACCESS   not-accessible
    STATUS       current
    DESCRIPTION
        "Instance identifier of the managed object."
    ::= { cfprApAaaRealmFsmTaskEntry 1 }

cfprApAaaRealmFsmTaskDn OBJECT-TYPE
    SYNTAX       CfprApManagedObjectDn
    MAX-ACCESS   read-only
    STATUS       current
    DESCRIPTION
        "Cisco Firepower aaa:RealmFsmTask:dn managed object property"
    ::= { cfprApAaaRealmFsmTaskEntry 2 }

cfprApAaaRealmFsmTaskRn OBJECT-TYPE
    SYNTAX       SnmpAdminString
    MAX-ACCESS   read-only
    STATUS       current
    DESCRIPTION
        "Cisco Firepower aaa:RealmFsmTask:rn managed object property"
    ::= { cfprApAaaRealmFsmTaskEntry 3 }

cfprApAaaRealmFsmTaskCompletion OBJECT-TYPE
    SYNTAX       CfprApFsmCompletion
    MAX-ACCESS   read-only
    STATUS       current
    DESCRIPTION
        "Cisco Firepower aaa:RealmFsmTask:completion managed
        object property"
    ::= { cfprApAaaRealmFsmTaskEntry 4 }

cfprApAaaRealmFsmTaskFlags OBJECT-TYPE
    SYNTAX       CfprApFsmFlags
    MAX-ACCESS   read-only
    STATUS       current
    DESCRIPTION
        "Cisco Firepower aaa:RealmFsmTask:flags managed object property"
    ::= { cfprApAaaRealmFsmTaskEntry 5 }

cfprApAaaRealmFsmTaskItem OBJECT-TYPE
    SYNTAX       CfprApAaaRealmFsmTaskItem
    MAX-ACCESS   read-only
    STATUS       current
    DESCRIPTION
        "Cisco Firepower aaa:RealmFsmTask:item managed object property"
    ::= { cfprApAaaRealmFsmTaskEntry 6 }

cfprApAaaRealmFsmTaskSeqId OBJECT-TYPE
    SYNTAX       Gauge32
    MAX-ACCESS   read-only
    STATUS       current
    DESCRIPTION
        "Cisco Firepower aaa:RealmFsmTask:seqId managed object property"
    ::= { cfprApAaaRealmFsmTaskEntry 7 }

cfprApAaaRemoteUserTable OBJECT-TYPE
    SYNTAX           SEQUENCE OF CfprApAaaRemoteUserEntry
    MAX-ACCESS       not-accessible
    STATUS           current
    DESCRIPTION
        "Cisco Firepower aaa:RemoteUser managed object table"
    ::= { cfprApAaaObjects 37 }

cfprApAaaRemoteUserEntry OBJECT-TYPE
    SYNTAX           CfprApAaaRemoteUserEntry
    MAX-ACCESS       not-accessible
    STATUS           current
    DESCRIPTION
        "Entry for the cfprApAaaRemoteUserTable table."
    INDEX { cfprApAaaRemoteUserInstanceId }
    ::= { cfprApAaaRemoteUserTable 1 }

CfprApAaaRemoteUserEntry ::= SEQUENCE {
    cfprApAaaRemoteUserInstanceId                                    CfprApManagedObjectId,
    cfprApAaaRemoteUserDn                                            CfprApManagedObjectDn,
    cfprApAaaRemoteUserRn                                            SnmpAdminString,
    cfprApAaaRemoteUserConfigState                                   CfprApAaaConfigState,
    cfprApAaaRemoteUserConfigStatusMessage                           SnmpAdminString,
    cfprApAaaRemoteUserDescr                                         SnmpAdminString,
    cfprApAaaRemoteUserName                                          SnmpAdminString,
    cfprApAaaRemoteUserPwd                                           SnmpAdminString,
    cfprApAaaRemoteUserPwdSet                                        TruthValue
}

cfprApAaaRemoteUserInstanceId OBJECT-TYPE
    SYNTAX       CfprApManagedObjectId
    MAX-ACCESS   not-accessible
    STATUS       current
    DESCRIPTION
        "Instance identifier of the managed object."
    ::= { cfprApAaaRemoteUserEntry 1 }

cfprApAaaRemoteUserDn OBJECT-TYPE
    SYNTAX       CfprApManagedObjectDn
    MAX-ACCESS   read-only
    STATUS       current
    DESCRIPTION
        "Cisco Firepower aaa:RemoteUser:dn managed object property"
    ::= { cfprApAaaRemoteUserEntry 2 }

cfprApAaaRemoteUserRn OBJECT-TYPE
    SYNTAX       SnmpAdminString
    MAX-ACCESS   read-only
    STATUS       current
    DESCRIPTION
        "Cisco Firepower aaa:RemoteUser:rn managed object property"
    ::= { cfprApAaaRemoteUserEntry 3 }

cfprApAaaRemoteUserConfigState OBJECT-TYPE
    SYNTAX       CfprApAaaConfigState
    MAX-ACCESS   read-only
    STATUS       current
    DESCRIPTION
        "Cisco Firepower aaa:RemoteUser:configState managed
        object property"
    ::= { cfprApAaaRemoteUserEntry 4 }

cfprApAaaRemoteUserConfigStatusMessage OBJECT-TYPE
    SYNTAX       SnmpAdminString
    MAX-ACCESS   read-only
    STATUS       current
    DESCRIPTION
        "Cisco Firepower aaa:RemoteUser:configStatusMessage
        managed object property"
    ::= { cfprApAaaRemoteUserEntry 5 }

cfprApAaaRemoteUserDescr OBJECT-TYPE
    SYNTAX       SnmpAdminString
    MAX-ACCESS   read-only
    STATUS       current
    DESCRIPTION
        "Cisco Firepower aaa:RemoteUser:descr managed object property"
    ::= { cfprApAaaRemoteUserEntry 6 }

cfprApAaaRemoteUserName OBJECT-TYPE
    SYNTAX       SnmpAdminString
    MAX-ACCESS   read-only
    STATUS       current
    DESCRIPTION
        "Cisco Firepower aaa:RemoteUser:name managed object property"
    ::= { cfprApAaaRemoteUserEntry 7 }

cfprApAaaRemoteUserPwd OBJECT-TYPE
    SYNTAX       SnmpAdminString
    MAX-ACCESS   read-only
    STATUS       current
    DESCRIPTION
        "Cisco Firepower aaa:RemoteUser:pwd managed object property"
    ::= { cfprApAaaRemoteUserEntry 8 }

cfprApAaaRemoteUserPwdSet OBJECT-TYPE
    SYNTAX       TruthValue
    MAX-ACCESS   read-only
    STATUS       current
    DESCRIPTION
        "Cisco Firepower aaa:RemoteUser:pwdSet managed object property"
    ::= { cfprApAaaRemoteUserEntry 9 }

cfprApAaaRoleTable OBJECT-TYPE
    SYNTAX           SEQUENCE OF CfprApAaaRoleEntry
    MAX-ACCESS       not-accessible
    STATUS           current
    DESCRIPTION
        "Cisco Firepower aaa:Role managed object table"
    ::= { cfprApAaaObjects 38 }

cfprApAaaRoleEntry OBJECT-TYPE
    SYNTAX           CfprApAaaRoleEntry
    MAX-ACCESS       not-accessible
    STATUS           current
    DESCRIPTION
        "Entry for the cfprApAaaRoleTable table."
    INDEX { cfprApAaaRoleInstanceId }
    ::= { cfprApAaaRoleTable 1 }

CfprApAaaRoleEntry ::= SEQUENCE {
    cfprApAaaRoleInstanceId                                          CfprApManagedObjectId,
    cfprApAaaRoleDn                                                  CfprApManagedObjectDn,
    cfprApAaaRoleRn                                                  SnmpAdminString,
    cfprApAaaRoleConfigState                                         CfprApAaaConfigState,
    cfprApAaaRoleConfigStatusMessage                                 SnmpAdminString,
    cfprApAaaRoleDescr                                               SnmpAdminString,
    cfprApAaaRoleIntId                                               SnmpAdminString,
    cfprApAaaRoleName                                                SnmpAdminString,
    cfprApAaaRolePolicyLevel                                         Gauge32,
    cfprApAaaRolePolicyOwner                                         CfprApPolicyPolicyOwner,
    cfprApAaaRolePriv                                                CfprApAaaAccess
}

cfprApAaaRoleInstanceId OBJECT-TYPE
    SYNTAX       CfprApManagedObjectId
    MAX-ACCESS   not-accessible
    STATUS       current
    DESCRIPTION
        "Instance identifier of the managed object."
    ::= { cfprApAaaRoleEntry 1 }

cfprApAaaRoleDn OBJECT-TYPE
    SYNTAX       CfprApManagedObjectDn
    MAX-ACCESS   read-only
    STATUS       current
    DESCRIPTION
        "Cisco Firepower aaa:Role:dn managed object property"
    ::= { cfprApAaaRoleEntry 2 }

cfprApAaaRoleRn OBJECT-TYPE
    SYNTAX       SnmpAdminString
    MAX-ACCESS   read-only
    STATUS       current
    DESCRIPTION
        "Cisco Firepower aaa:Role:rn managed object property"
    ::= { cfprApAaaRoleEntry 3 }

cfprApAaaRoleConfigState OBJECT-TYPE
    SYNTAX       CfprApAaaConfigState
    MAX-ACCESS   read-only
    STATUS       current
    DESCRIPTION
        "Cisco Firepower aaa:Role:configState managed object property"
    ::= { cfprApAaaRoleEntry 4 }

cfprApAaaRoleConfigStatusMessage OBJECT-TYPE
    SYNTAX       SnmpAdminString
    MAX-ACCESS   read-only
    STATUS       current
    DESCRIPTION
        "Cisco Firepower aaa:Role:configStatusMessage managed
        object property"
    ::= { cfprApAaaRoleEntry 5 }

cfprApAaaRoleDescr OBJECT-TYPE
    SYNTAX       SnmpAdminString
    MAX-ACCESS   read-only
    STATUS       current
    DESCRIPTION
        "Cisco Firepower aaa:Role:descr managed object property"
    ::= { cfprApAaaRoleEntry 6 }

cfprApAaaRoleIntId OBJECT-TYPE
    SYNTAX       SnmpAdminString
    MAX-ACCESS   read-only
    STATUS       current
    DESCRIPTION
        "Cisco Firepower aaa:Role:intId managed object property"
    ::= { cfprApAaaRoleEntry 7 }

cfprApAaaRoleName OBJECT-TYPE
    SYNTAX       SnmpAdminString
    MAX-ACCESS   read-only
    STATUS       current
    DESCRIPTION
        "Cisco Firepower aaa:Role:name managed object property"
    ::= { cfprApAaaRoleEntry 8 }

cfprApAaaRolePolicyLevel OBJECT-TYPE
    SYNTAX       Gauge32
    MAX-ACCESS   read-only
    STATUS       current
    DESCRIPTION
        "Cisco Firepower aaa:Role:policyLevel managed object property"
    ::= { cfprApAaaRoleEntry 9 }

cfprApAaaRolePolicyOwner OBJECT-TYPE
    SYNTAX       CfprApPolicyPolicyOwner
    MAX-ACCESS   read-only
    STATUS       current
    DESCRIPTION
        "Cisco Firepower aaa:Role:policyOwner managed object property"
    ::= { cfprApAaaRoleEntry 10 }

cfprApAaaRolePriv OBJECT-TYPE
    SYNTAX       CfprApAaaAccess
    MAX-ACCESS   read-only
    STATUS       current
    DESCRIPTION
        "Cisco Firepower aaa:Role:priv managed object property"
    ::= { cfprApAaaRoleEntry 11 }

cfprApAaaSessionTable OBJECT-TYPE
    SYNTAX           SEQUENCE OF CfprApAaaSessionEntry
    MAX-ACCESS       not-accessible
    STATUS           current
    DESCRIPTION
        "Cisco Firepower aaa:Session managed object table"
    ::= { cfprApAaaObjects 39 }

cfprApAaaSessionEntry OBJECT-TYPE
    SYNTAX           CfprApAaaSessionEntry
    MAX-ACCESS       not-accessible
    STATUS           current
    DESCRIPTION
        "Entry for the cfprApAaaSessionTable table."
    INDEX { cfprApAaaSessionInstanceId }
    ::= { cfprApAaaSessionTable 1 }

CfprApAaaSessionEntry ::= SEQUENCE {
    cfprApAaaSessionInstanceId                                       CfprApManagedObjectId,
    cfprApAaaSessionDn                                               CfprApManagedObjectDn,
    cfprApAaaSessionRn                                               SnmpAdminString,
    cfprApAaaSessionHost                                             SnmpAdminString,
    cfprApAaaSessionId                                               SnmpAdminString,
    cfprApAaaSessionIntDel                                           TruthValue,
    cfprApAaaSessionLoginTime                                        DateAndTime,
    cfprApAaaSessionPid                                              Gauge32,
    cfprApAaaSessionRefreshPeriod                                    Gauge32,
    cfprApAaaSessionSessionTimeout                                   Gauge32,
    cfprApAaaSessionSwitchId                                         CfprApNetworkSwitchId,
    cfprApAaaSessionTerm                                             SnmpAdminString,
    cfprApAaaSessionUi                                               CfprApAaaUserInterface,
    cfprApAaaSessionUser                                             SnmpAdminString
}

cfprApAaaSessionInstanceId OBJECT-TYPE
    SYNTAX       CfprApManagedObjectId
    MAX-ACCESS   not-accessible
    STATUS       current
    DESCRIPTION
        "Instance identifier of the managed object."
    ::= { cfprApAaaSessionEntry 1 }

cfprApAaaSessionDn OBJECT-TYPE
    SYNTAX       CfprApManagedObjectDn
    MAX-ACCESS   read-only
    STATUS       current
    DESCRIPTION
        "Cisco Firepower aaa:Session:dn managed object property"
    ::= { cfprApAaaSessionEntry 2 }

cfprApAaaSessionRn OBJECT-TYPE
    SYNTAX       SnmpAdminString
    MAX-ACCESS   read-only
    STATUS       current
    DESCRIPTION
        "Cisco Firepower aaa:Session:rn managed object property"
    ::= { cfprApAaaSessionEntry 3 }

cfprApAaaSessionHost OBJECT-TYPE
    SYNTAX       SnmpAdminString
    MAX-ACCESS   read-only
    STATUS       current
    DESCRIPTION
        "Cisco Firepower aaa:Session:host managed object property"
    ::= { cfprApAaaSessionEntry 4 }

cfprApAaaSessionId OBJECT-TYPE
    SYNTAX       SnmpAdminString
    MAX-ACCESS   read-only
    STATUS       current
    DESCRIPTION
        "Cisco Firepower aaa:Session:id managed object property"
    ::= { cfprApAaaSessionEntry 5 }

cfprApAaaSessionIntDel OBJECT-TYPE
    SYNTAX       TruthValue
    MAX-ACCESS   read-only
    STATUS       current
    DESCRIPTION
        "Cisco Firepower aaa:Session:intDel managed object property"
    ::= { cfprApAaaSessionEntry 6 }

cfprApAaaSessionLoginTime OBJECT-TYPE
    SYNTAX       DateAndTime
    MAX-ACCESS   read-only
    STATUS       current
    DESCRIPTION
        "Cisco Firepower aaa:Session:loginTime managed object property"
    ::= { cfprApAaaSessionEntry 7 }

cfprApAaaSessionPid OBJECT-TYPE
    SYNTAX       Gauge32
    MAX-ACCESS   read-only
    STATUS       current
    DESCRIPTION
        "Cisco Firepower aaa:Session:pid managed object property"
    ::= { cfprApAaaSessionEntry 8 }

cfprApAaaSessionRefreshPeriod OBJECT-TYPE
    SYNTAX       Gauge32
    MAX-ACCESS   read-only
    STATUS       current
    DESCRIPTION
        "Cisco Firepower aaa:Session:refreshPeriod managed
        object property"
    ::= { cfprApAaaSessionEntry 9 }

cfprApAaaSessionSessionTimeout OBJECT-TYPE
    SYNTAX       Gauge32
    MAX-ACCESS   read-only
    STATUS       current
    DESCRIPTION
        "Cisco Firepower aaa:Session:sessionTimeout managed
        object property"
    ::= { cfprApAaaSessionEntry 10 }

cfprApAaaSessionSwitchId OBJECT-TYPE
    SYNTAX       CfprApNetworkSwitchId
    MAX-ACCESS   read-only
    STATUS       current
    DESCRIPTION
        "Cisco Firepower aaa:Session:switchId managed object property"
    ::= { cfprApAaaSessionEntry 11 }

cfprApAaaSessionTerm OBJECT-TYPE
    SYNTAX       SnmpAdminString
    MAX-ACCESS   read-only
    STATUS       current
    DESCRIPTION
        "Cisco Firepower aaa:Session:term managed object property"
    ::= { cfprApAaaSessionEntry 12 }

cfprApAaaSessionUi OBJECT-TYPE
    SYNTAX       CfprApAaaUserInterface
    MAX-ACCESS   read-only
    STATUS       current
    DESCRIPTION
        "Cisco Firepower aaa:Session:ui managed object property"
    ::= { cfprApAaaSessionEntry 13 }

cfprApAaaSessionUser OBJECT-TYPE
    SYNTAX       SnmpAdminString
    MAX-ACCESS   read-only
    STATUS       current
    DESCRIPTION
        "Cisco Firepower aaa:Session:user managed object property"
    ::= { cfprApAaaSessionEntry 14 }

cfprApAaaSessionInfoTable OBJECT-TYPE
    SYNTAX           SEQUENCE OF CfprApAaaSessionInfoEntry
    MAX-ACCESS       not-accessible
    STATUS           current
    DESCRIPTION
        "Cisco Firepower aaa:SessionInfo managed object table"
    ::= { cfprApAaaObjects 40 }

cfprApAaaSessionInfoEntry OBJECT-TYPE
    SYNTAX           CfprApAaaSessionInfoEntry
    MAX-ACCESS       not-accessible
    STATUS           current
    DESCRIPTION
        "Entry for the cfprApAaaSessionInfoTable table."
    INDEX { cfprApAaaSessionInfoInstanceId }
    ::= { cfprApAaaSessionInfoTable 1 }

CfprApAaaSessionInfoEntry ::= SEQUENCE {
    cfprApAaaSessionInfoInstanceId                                   CfprApManagedObjectId,
    cfprApAaaSessionInfoDn                                           CfprApManagedObjectDn,
    cfprApAaaSessionInfoRn                                           SnmpAdminString,
    cfprApAaaSessionInfoAddress                                      SnmpAdminString,
    cfprApAaaSessionInfoDestIp                                       SnmpAdminString,
    cfprApAaaSessionInfoEtime                                        DateAndTime,
    cfprApAaaSessionInfoId                                           SnmpAdminString,
    cfprApAaaSessionInfoPriv                                         SnmpAdminString,
    cfprApAaaSessionInfoType                                         CfprApAaaCimcSessionType,
    cfprApAaaSessionInfoUser                                         SnmpAdminString,
    cfprApAaaSessionInfoUserType                                     CfprApAaaSession
}

cfprApAaaSessionInfoInstanceId OBJECT-TYPE
    SYNTAX       CfprApManagedObjectId
    MAX-ACCESS   not-accessible
    STATUS       current
    DESCRIPTION
        "Instance identifier of the managed object."
    ::= { cfprApAaaSessionInfoEntry 1 }

cfprApAaaSessionInfoDn OBJECT-TYPE
    SYNTAX       CfprApManagedObjectDn
    MAX-ACCESS   read-only
    STATUS       current
    DESCRIPTION
        "Cisco Firepower aaa:SessionInfo:dn managed object property"
    ::= { cfprApAaaSessionInfoEntry 2 }

cfprApAaaSessionInfoRn OBJECT-TYPE
    SYNTAX       SnmpAdminString
    MAX-ACCESS   read-only
    STATUS       current
    DESCRIPTION
        "Cisco Firepower aaa:SessionInfo:rn managed object property"
    ::= { cfprApAaaSessionInfoEntry 3 }

cfprApAaaSessionInfoAddress OBJECT-TYPE
    SYNTAX       SnmpAdminString
    MAX-ACCESS   read-only
    STATUS       current
    DESCRIPTION
        "Cisco Firepower aaa:SessionInfo:address managed object property"
    ::= { cfprApAaaSessionInfoEntry 4 }

cfprApAaaSessionInfoDestIp OBJECT-TYPE
    SYNTAX       SnmpAdminString
    MAX-ACCESS   read-only
    STATUS       current
    DESCRIPTION
        "Cisco Firepower aaa:SessionInfo:destIp managed object property"
    ::= { cfprApAaaSessionInfoEntry 5 }

cfprApAaaSessionInfoEtime OBJECT-TYPE
    SYNTAX       DateAndTime
    MAX-ACCESS   read-only
    STATUS       current
    DESCRIPTION
        "Cisco Firepower aaa:SessionInfo:etime managed object property"
    ::= { cfprApAaaSessionInfoEntry 6 }

cfprApAaaSessionInfoId OBJECT-TYPE
    SYNTAX       SnmpAdminString
    MAX-ACCESS   read-only
    STATUS       current
    DESCRIPTION
        "Cisco Firepower aaa:SessionInfo:id managed object property"
    ::= { cfprApAaaSessionInfoEntry 7 }

cfprApAaaSessionInfoPriv OBJECT-TYPE
    SYNTAX       SnmpAdminString
    MAX-ACCESS   read-only
    STATUS       current
    DESCRIPTION
        "Cisco Firepower aaa:SessionInfo:priv managed object property"
    ::= { cfprApAaaSessionInfoEntry 8 }

cfprApAaaSessionInfoType OBJECT-TYPE
    SYNTAX       CfprApAaaCimcSessionType
    MAX-ACCESS   read-only
    STATUS       current
    DESCRIPTION
        "Cisco Firepower aaa:SessionInfo:type managed object property"
    ::= { cfprApAaaSessionInfoEntry 9 }

cfprApAaaSessionInfoUser OBJECT-TYPE
    SYNTAX       SnmpAdminString
    MAX-ACCESS   read-only
    STATUS       current
    DESCRIPTION
        "Cisco Firepower aaa:SessionInfo:user managed object property"
    ::= { cfprApAaaSessionInfoEntry 10 }

cfprApAaaSessionInfoUserType OBJECT-TYPE
    SYNTAX       CfprApAaaSession
    MAX-ACCESS   read-only
    STATUS       current
    DESCRIPTION
        "Cisco Firepower aaa:SessionInfo:userType managed object property"
    ::= { cfprApAaaSessionInfoEntry 11 }

cfprApAaaSessionInfoTableTable OBJECT-TYPE
    SYNTAX           SEQUENCE OF CfprApAaaSessionInfoTableEntry
    MAX-ACCESS       not-accessible
    STATUS           current
    DESCRIPTION
        "Cisco Firepower aaa:SessionInfoTable managed object table"
    ::= { cfprApAaaObjects 41 }

cfprApAaaSessionInfoTableEntry OBJECT-TYPE
    SYNTAX           CfprApAaaSessionInfoTableEntry
    MAX-ACCESS       not-accessible
    STATUS           current
    DESCRIPTION
        "Entry for the cfprApAaaSessionInfoTableTable table."
    INDEX { cfprApAaaSessionInfoTableInstanceId }
    ::= { cfprApAaaSessionInfoTableTable 1 }

CfprApAaaSessionInfoTableEntry ::= SEQUENCE {
    cfprApAaaSessionInfoTableInstanceId                              CfprApManagedObjectId,
    cfprApAaaSessionInfoTableDn                                      CfprApManagedObjectDn,
    cfprApAaaSessionInfoTableRn                                      SnmpAdminString
}

cfprApAaaSessionInfoTableInstanceId OBJECT-TYPE
    SYNTAX       CfprApManagedObjectId
    MAX-ACCESS   not-accessible
    STATUS       current
    DESCRIPTION
        "Instance identifier of the managed object."
    ::= { cfprApAaaSessionInfoTableEntry 1 }

cfprApAaaSessionInfoTableDn OBJECT-TYPE
    SYNTAX       CfprApManagedObjectDn
    MAX-ACCESS   read-only
    STATUS       current
    DESCRIPTION
        "Cisco Firepower aaa:SessionInfoTable:dn managed object property"
    ::= { cfprApAaaSessionInfoTableEntry 2 }

cfprApAaaSessionInfoTableRn OBJECT-TYPE
    SYNTAX       SnmpAdminString
    MAX-ACCESS   read-only
    STATUS       current
    DESCRIPTION
        "Cisco Firepower aaa:SessionInfoTable:rn managed object property"
    ::= { cfprApAaaSessionInfoTableEntry 3 }

cfprApAaaSessionLRTable OBJECT-TYPE
    SYNTAX           SEQUENCE OF CfprApAaaSessionLREntry
    MAX-ACCESS       not-accessible
    STATUS           current
    DESCRIPTION
        "Cisco Firepower aaa:SessionLR managed object table"
    ::= { cfprApAaaObjects 42 }

cfprApAaaSessionLREntry OBJECT-TYPE
    SYNTAX           CfprApAaaSessionLREntry
    MAX-ACCESS       not-accessible
    STATUS           current
    DESCRIPTION
        "Entry for the cfprApAaaSessionLRTable table."
    INDEX { cfprApAaaSessionLRInstanceId }
    ::= { cfprApAaaSessionLRTable 1 }

CfprApAaaSessionLREntry ::= SEQUENCE {
    cfprApAaaSessionLRInstanceId                                     CfprApManagedObjectId,
    cfprApAaaSessionLRDn                                             CfprApManagedObjectDn,
    cfprApAaaSessionLRRn                                             SnmpAdminString,
    cfprApAaaSessionLRAffected                                       SnmpAdminString,
    cfprApAaaSessionLRCause                                          CfprApConditionCause,
    cfprApAaaSessionLRChangeSet                                      SnmpAdminString,
    cfprApAaaSessionLRCode                                           CfprApConditionCode,
    cfprApAaaSessionLRCreated                                        DateAndTime,
    cfprApAaaSessionLRDescr                                          SnmpAdminString,
    cfprApAaaSessionLRId                                             Gauge32,
    cfprApAaaSessionLRInd                                            CfprApConditionActionIndicator,
    cfprApAaaSessionLRSessionId                                      SnmpAdminString,
    cfprApAaaSessionLRSeverity                                       CfprApConditionSeverity,
    cfprApAaaSessionLRTrig                                           Gauge32,
    cfprApAaaSessionLRTxId                                           Unsigned64,
    cfprApAaaSessionLRUser                                           SnmpAdminString
}

cfprApAaaSessionLRInstanceId OBJECT-TYPE
    SYNTAX       CfprApManagedObjectId
    MAX-ACCESS   not-accessible
    STATUS       current
    DESCRIPTION
        "Instance identifier of the managed object."
    ::= { cfprApAaaSessionLREntry 1 }

cfprApAaaSessionLRDn OBJECT-TYPE
    SYNTAX       CfprApManagedObjectDn
    MAX-ACCESS   read-only
    STATUS       current
    DESCRIPTION
        "Cisco Firepower aaa:SessionLR:dn managed object property"
    ::= { cfprApAaaSessionLREntry 2 }

cfprApAaaSessionLRRn OBJECT-TYPE
    SYNTAX       SnmpAdminString
    MAX-ACCESS   read-only
    STATUS       current
    DESCRIPTION
        "Cisco Firepower aaa:SessionLR:rn managed object property"
    ::= { cfprApAaaSessionLREntry 3 }

cfprApAaaSessionLRAffected OBJECT-TYPE
    SYNTAX       SnmpAdminString
    MAX-ACCESS   read-only
    STATUS       current
    DESCRIPTION
        "Cisco Firepower aaa:SessionLR:affected managed object property"
    ::= { cfprApAaaSessionLREntry 4 }

cfprApAaaSessionLRCause OBJECT-TYPE
    SYNTAX       CfprApConditionCause
    MAX-ACCESS   read-only
    STATUS       current
    DESCRIPTION
        "Cisco Firepower aaa:SessionLR:cause managed object property"
    ::= { cfprApAaaSessionLREntry 5 }

cfprApAaaSessionLRChangeSet OBJECT-TYPE
    SYNTAX       SnmpAdminString
    MAX-ACCESS   read-only
    STATUS       current
    DESCRIPTION
        "Cisco Firepower aaa:SessionLR:changeSet managed object property"
    ::= { cfprApAaaSessionLREntry 6 }

cfprApAaaSessionLRCode OBJECT-TYPE
    SYNTAX       CfprApConditionCode
    MAX-ACCESS   read-only
    STATUS       current
    DESCRIPTION
        "Cisco Firepower aaa:SessionLR:code managed object property"
    ::= { cfprApAaaSessionLREntry 7 }

cfprApAaaSessionLRCreated OBJECT-TYPE
    SYNTAX       DateAndTime
    MAX-ACCESS   read-only
    STATUS       current
    DESCRIPTION
        "Cisco Firepower aaa:SessionLR:created managed object property"
    ::= { cfprApAaaSessionLREntry 8 }

cfprApAaaSessionLRDescr OBJECT-TYPE
    SYNTAX       SnmpAdminString
    MAX-ACCESS   read-only
    STATUS       current
    DESCRIPTION
        "Cisco Firepower aaa:SessionLR:descr managed object property"
    ::= { cfprApAaaSessionLREntry 9 }

cfprApAaaSessionLRId OBJECT-TYPE
    SYNTAX       Gauge32
    MAX-ACCESS   read-only
    STATUS       current
    DESCRIPTION
        "Cisco Firepower aaa:SessionLR:id managed object property"
    ::= { cfprApAaaSessionLREntry 10 }

cfprApAaaSessionLRInd OBJECT-TYPE
    SYNTAX       CfprApConditionActionIndicator
    MAX-ACCESS   read-only
    STATUS       current
    DESCRIPTION
        "Cisco Firepower aaa:SessionLR:ind managed object property"
    ::= { cfprApAaaSessionLREntry 11 }

cfprApAaaSessionLRSessionId OBJECT-TYPE
    SYNTAX       SnmpAdminString
    MAX-ACCESS   read-only
    STATUS       current
    DESCRIPTION
        "Cisco Firepower aaa:SessionLR:sessionId managed object property"
    ::= { cfprApAaaSessionLREntry 12 }

cfprApAaaSessionLRSeverity OBJECT-TYPE
    SYNTAX       CfprApConditionSeverity
    MAX-ACCESS   read-only
    STATUS       current
    DESCRIPTION
        "Cisco Firepower aaa:SessionLR:severity managed object property"
    ::= { cfprApAaaSessionLREntry 13 }

cfprApAaaSessionLRTrig OBJECT-TYPE
    SYNTAX       Gauge32
    MAX-ACCESS   read-only
    STATUS       current
    DESCRIPTION
        "Cisco Firepower aaa:SessionLR:trig managed object property"
    ::= { cfprApAaaSessionLREntry 14 }

cfprApAaaSessionLRTxId OBJECT-TYPE
    SYNTAX       Unsigned64
    MAX-ACCESS   read-only
    STATUS       current
    DESCRIPTION
        "Cisco Firepower aaa:SessionLR:txId managed object property"
    ::= { cfprApAaaSessionLREntry 15 }

cfprApAaaSessionLRUser OBJECT-TYPE
    SYNTAX       SnmpAdminString
    MAX-ACCESS   read-only
    STATUS       current
    DESCRIPTION
        "Cisco Firepower aaa:SessionLR:user managed object property"
    ::= { cfprApAaaSessionLREntry 16 }

cfprApAaaShellLoginTable OBJECT-TYPE
    SYNTAX           SEQUENCE OF CfprApAaaShellLoginEntry
    MAX-ACCESS       not-accessible
    STATUS           current
    DESCRIPTION
        "Cisco Firepower aaa:ShellLogin managed object table"
    ::= { cfprApAaaObjects 43 }

cfprApAaaShellLoginEntry OBJECT-TYPE
    SYNTAX           CfprApAaaShellLoginEntry
    MAX-ACCESS       not-accessible
    STATUS           current
    DESCRIPTION
        "Entry for the cfprApAaaShellLoginTable table."
    INDEX { cfprApAaaShellLoginInstanceId }
    ::= { cfprApAaaShellLoginTable 1 }

CfprApAaaShellLoginEntry ::= SEQUENCE {
    cfprApAaaShellLoginInstanceId                                    CfprApManagedObjectId,
    cfprApAaaShellLoginDn                                            CfprApManagedObjectDn,
    cfprApAaaShellLoginRn                                            SnmpAdminString,
    cfprApAaaShellLoginDescr                                         SnmpAdminString,
    cfprApAaaShellLoginId                                            SnmpAdminString,
    cfprApAaaShellLoginIntId                                         SnmpAdminString,
    cfprApAaaShellLoginLocalHost                                     SnmpAdminString,
    cfprApAaaShellLoginName                                          SnmpAdminString,
    cfprApAaaShellLoginPolicyLevel                                   Gauge32,
    cfprApAaaShellLoginPolicyOwner                                   CfprApPolicyPolicyOwner,
    cfprApAaaShellLoginRemoteHost                                    SnmpAdminString,
    cfprApAaaShellLoginSession                                       CfprApAaaSession,
    cfprApAaaShellLoginSwitchId                                      CfprApNetworkSwitchId
}

cfprApAaaShellLoginInstanceId OBJECT-TYPE
    SYNTAX       CfprApManagedObjectId
    MAX-ACCESS   not-accessible
    STATUS       current
    DESCRIPTION
        "Instance identifier of the managed object."
    ::= { cfprApAaaShellLoginEntry 1 }

cfprApAaaShellLoginDn OBJECT-TYPE
    SYNTAX       CfprApManagedObjectDn
    MAX-ACCESS   read-only
    STATUS       current
    DESCRIPTION
        "Cisco Firepower aaa:ShellLogin:dn managed object property"
    ::= { cfprApAaaShellLoginEntry 2 }

cfprApAaaShellLoginRn OBJECT-TYPE
    SYNTAX       SnmpAdminString
    MAX-ACCESS   read-only
    STATUS       current
    DESCRIPTION
        "Cisco Firepower aaa:ShellLogin:rn managed object property"
    ::= { cfprApAaaShellLoginEntry 3 }

cfprApAaaShellLoginDescr OBJECT-TYPE
    SYNTAX       SnmpAdminString
    MAX-ACCESS   read-only
    STATUS       current
    DESCRIPTION
        "Cisco Firepower aaa:ShellLogin:descr managed object property"
    ::= { cfprApAaaShellLoginEntry 4 }

cfprApAaaShellLoginId OBJECT-TYPE
    SYNTAX       SnmpAdminString
    MAX-ACCESS   read-only
    STATUS       current
    DESCRIPTION
        "Cisco Firepower aaa:ShellLogin:id managed object property"
    ::= { cfprApAaaShellLoginEntry 5 }

cfprApAaaShellLoginIntId OBJECT-TYPE
    SYNTAX       SnmpAdminString
    MAX-ACCESS   read-only
    STATUS       current
    DESCRIPTION
        "Cisco Firepower aaa:ShellLogin:intId managed object property"
    ::= { cfprApAaaShellLoginEntry 6 }

cfprApAaaShellLoginLocalHost OBJECT-TYPE
    SYNTAX       SnmpAdminString
    MAX-ACCESS   read-only
    STATUS       current
    DESCRIPTION
        "Cisco Firepower aaa:ShellLogin:localHost managed object property"
    ::= { cfprApAaaShellLoginEntry 7 }

cfprApAaaShellLoginName OBJECT-TYPE
    SYNTAX       SnmpAdminString
    MAX-ACCESS   read-only
    STATUS       current
    DESCRIPTION
        "Cisco Firepower aaa:ShellLogin:name managed object property"
    ::= { cfprApAaaShellLoginEntry 8 }

cfprApAaaShellLoginPolicyLevel OBJECT-TYPE
    SYNTAX       Gauge32
    MAX-ACCESS   read-only
    STATUS       current
    DESCRIPTION
        "Cisco Firepower aaa:ShellLogin:policyLevel managed
        object property"
    ::= { cfprApAaaShellLoginEntry 9 }

cfprApAaaShellLoginPolicyOwner OBJECT-TYPE
    SYNTAX       CfprApPolicyPolicyOwner
    MAX-ACCESS   read-only
    STATUS       current
    DESCRIPTION
        "Cisco Firepower aaa:ShellLogin:policyOwner managed
        object property"
    ::= { cfprApAaaShellLoginEntry 10 }

cfprApAaaShellLoginRemoteHost OBJECT-TYPE
    SYNTAX       SnmpAdminString
    MAX-ACCESS   read-only
    STATUS       current
    DESCRIPTION
        "Cisco Firepower aaa:ShellLogin:remoteHost managed
        object property"
    ::= { cfprApAaaShellLoginEntry 11 }

cfprApAaaShellLoginSession OBJECT-TYPE
    SYNTAX       CfprApAaaSession
    MAX-ACCESS   read-only
    STATUS       current
    DESCRIPTION
        "Cisco Firepower aaa:ShellLogin:session managed object property"
    ::= { cfprApAaaShellLoginEntry 12 }

cfprApAaaShellLoginSwitchId OBJECT-TYPE
    SYNTAX       CfprApNetworkSwitchId
    MAX-ACCESS   read-only
    STATUS       current
    DESCRIPTION
        "Cisco Firepower aaa:ShellLogin:switchId managed object property"
    ::= { cfprApAaaShellLoginEntry 13 }

cfprApAaaSshAuthTable OBJECT-TYPE
    SYNTAX           SEQUENCE OF CfprApAaaSshAuthEntry
    MAX-ACCESS       not-accessible
    STATUS           current
    DESCRIPTION
        "Cisco Firepower aaa:SshAuth managed object table"
    ::= { cfprApAaaObjects 44 }

cfprApAaaSshAuthEntry OBJECT-TYPE
    SYNTAX           CfprApAaaSshAuthEntry
    MAX-ACCESS       not-accessible
    STATUS           current
    DESCRIPTION
        "Entry for the cfprApAaaSshAuthTable table."
    INDEX { cfprApAaaSshAuthInstanceId }
    ::= { cfprApAaaSshAuthTable 1 }

CfprApAaaSshAuthEntry ::= SEQUENCE {
    cfprApAaaSshAuthInstanceId                                       CfprApManagedObjectId,
    cfprApAaaSshAuthDn                                               CfprApManagedObjectDn,
    cfprApAaaSshAuthRn                                               SnmpAdminString,
    cfprApAaaSshAuthData                                             SnmpAdminString,
    cfprApAaaSshAuthOldStrType                                       CfprApAaaSshStr,
    cfprApAaaSshAuthStrType                                          CfprApAaaSshStr
}

cfprApAaaSshAuthInstanceId OBJECT-TYPE
    SYNTAX       CfprApManagedObjectId
    MAX-ACCESS   not-accessible
    STATUS       current
    DESCRIPTION
        "Instance identifier of the managed object."
    ::= { cfprApAaaSshAuthEntry 1 }

cfprApAaaSshAuthDn OBJECT-TYPE
    SYNTAX       CfprApManagedObjectDn
    MAX-ACCESS   read-only
    STATUS       current
    DESCRIPTION
        "Cisco Firepower aaa:SshAuth:dn managed object property"
    ::= { cfprApAaaSshAuthEntry 2 }

cfprApAaaSshAuthRn OBJECT-TYPE
    SYNTAX       SnmpAdminString
    MAX-ACCESS   read-only
    STATUS       current
    DESCRIPTION
        "Cisco Firepower aaa:SshAuth:rn managed object property"
    ::= { cfprApAaaSshAuthEntry 3 }

cfprApAaaSshAuthData OBJECT-TYPE
    SYNTAX       SnmpAdminString
    MAX-ACCESS   read-only
    STATUS       current
    DESCRIPTION
        "Cisco Firepower aaa:SshAuth:data managed object property"
    ::= { cfprApAaaSshAuthEntry 4 }

cfprApAaaSshAuthOldStrType OBJECT-TYPE
    SYNTAX       CfprApAaaSshStr
    MAX-ACCESS   read-only
    STATUS       current
    DESCRIPTION
        "Cisco Firepower aaa:SshAuth:oldStrType managed object property"
    ::= { cfprApAaaSshAuthEntry 5 }

cfprApAaaSshAuthStrType OBJECT-TYPE
    SYNTAX       CfprApAaaSshStr
    MAX-ACCESS   read-only
    STATUS       current
    DESCRIPTION
        "Cisco Firepower aaa:SshAuth:strType managed object property"
    ::= { cfprApAaaSshAuthEntry 6 }

cfprApAaaTacacsPlusEpTable OBJECT-TYPE
    SYNTAX           SEQUENCE OF CfprApAaaTacacsPlusEpEntry
    MAX-ACCESS       not-accessible
    STATUS           current
    DESCRIPTION
        "Cisco Firepower aaa:TacacsPlusEp managed object table"
    ::= { cfprApAaaObjects 45 }

cfprApAaaTacacsPlusEpEntry OBJECT-TYPE
    SYNTAX           CfprApAaaTacacsPlusEpEntry
    MAX-ACCESS       not-accessible
    STATUS           current
    DESCRIPTION
        "Entry for the cfprApAaaTacacsPlusEpTable table."
    INDEX { cfprApAaaTacacsPlusEpInstanceId }
    ::= { cfprApAaaTacacsPlusEpTable 1 }

CfprApAaaTacacsPlusEpEntry ::= SEQUENCE {
    cfprApAaaTacacsPlusEpInstanceId                                  CfprApManagedObjectId,
    cfprApAaaTacacsPlusEpDn                                          CfprApManagedObjectDn,
    cfprApAaaTacacsPlusEpRn                                          SnmpAdminString,
    cfprApAaaTacacsPlusEpDescr                                       SnmpAdminString,
    cfprApAaaTacacsPlusEpFsmDescr                                    SnmpAdminString,
    cfprApAaaTacacsPlusEpFsmPrev                                     SnmpAdminString,
    cfprApAaaTacacsPlusEpFsmProgr                                    Gauge32,
    cfprApAaaTacacsPlusEpFsmRmtInvErrCode                            Gauge32,
    cfprApAaaTacacsPlusEpFsmRmtInvErrDescr                           SnmpAdminString,
    cfprApAaaTacacsPlusEpFsmRmtInvRslt                               CfprApConditionRemoteInvRslt,
    cfprApAaaTacacsPlusEpFsmStageDescr                               SnmpAdminString,
    cfprApAaaTacacsPlusEpFsmStamp                                    DateAndTime,
    cfprApAaaTacacsPlusEpFsmStatus                                   SnmpAdminString,
    cfprApAaaTacacsPlusEpFsmTry                                      Gauge32,
    cfprApAaaTacacsPlusEpIntId                                       SnmpAdminString,
    cfprApAaaTacacsPlusEpName                                        SnmpAdminString,
    cfprApAaaTacacsPlusEpPolicyLevel                                 Gauge32,
    cfprApAaaTacacsPlusEpPolicyOwner                                 CfprApPolicyPolicyOwner,
    cfprApAaaTacacsPlusEpRetries                                     Gauge32,
    cfprApAaaTacacsPlusEpTimeout                                     Gauge32
}

cfprApAaaTacacsPlusEpInstanceId OBJECT-TYPE
    SYNTAX       CfprApManagedObjectId
    MAX-ACCESS   not-accessible
    STATUS       current
    DESCRIPTION
        "Instance identifier of the managed object."
    ::= { cfprApAaaTacacsPlusEpEntry 1 }

cfprApAaaTacacsPlusEpDn OBJECT-TYPE
    SYNTAX       CfprApManagedObjectDn
    MAX-ACCESS   read-only
    STATUS       current
    DESCRIPTION
        "Cisco Firepower aaa:TacacsPlusEp:dn managed object property"
    ::= { cfprApAaaTacacsPlusEpEntry 2 }

cfprApAaaTacacsPlusEpRn OBJECT-TYPE
    SYNTAX       SnmpAdminString
    MAX-ACCESS   read-only
    STATUS       current
    DESCRIPTION
        "Cisco Firepower aaa:TacacsPlusEp:rn managed object property"
    ::= { cfprApAaaTacacsPlusEpEntry 3 }

cfprApAaaTacacsPlusEpDescr OBJECT-TYPE
    SYNTAX       SnmpAdminString
    MAX-ACCESS   read-only
    STATUS       current
    DESCRIPTION
        "Cisco Firepower aaa:TacacsPlusEp:descr managed object property"
    ::= { cfprApAaaTacacsPlusEpEntry 4 }

cfprApAaaTacacsPlusEpFsmDescr OBJECT-TYPE
    SYNTAX       SnmpAdminString
    MAX-ACCESS   read-only
    STATUS       current
    DESCRIPTION
        "Cisco Firepower aaa:TacacsPlusEp:fsmDescr managed
        object property"
    ::= { cfprApAaaTacacsPlusEpEntry 5 }

cfprApAaaTacacsPlusEpFsmPrev OBJECT-TYPE
    SYNTAX       SnmpAdminString
    MAX-ACCESS   read-only
    STATUS       current
    DESCRIPTION
        "Cisco Firepower aaa:TacacsPlusEp:fsmPrev managed object property"
    ::= { cfprApAaaTacacsPlusEpEntry 6 }

cfprApAaaTacacsPlusEpFsmProgr OBJECT-TYPE
    SYNTAX       Gauge32
    MAX-ACCESS   read-only
    STATUS       current
    DESCRIPTION
        "Cisco Firepower aaa:TacacsPlusEp:fsmProgr managed
        object property"
    ::= { cfprApAaaTacacsPlusEpEntry 7 }

cfprApAaaTacacsPlusEpFsmRmtInvErrCode OBJECT-TYPE
    SYNTAX       Gauge32
    MAX-ACCESS   read-only
    STATUS       current
    DESCRIPTION
        "Cisco Firepower aaa:TacacsPlusEp:fsmRmtInvErrCode
        managed object property"
    ::= { cfprApAaaTacacsPlusEpEntry 8 }

cfprApAaaTacacsPlusEpFsmRmtInvErrDescr OBJECT-TYPE
    SYNTAX       SnmpAdminString
    MAX-ACCESS   read-only
    STATUS       current
    DESCRIPTION
        "Cisco Firepower aaa:TacacsPlusEp:fsmRmtInvErrDescr
        managed object property"
    ::= { cfprApAaaTacacsPlusEpEntry 9 }

cfprApAaaTacacsPlusEpFsmRmtInvRslt OBJECT-TYPE
    SYNTAX       CfprApConditionRemoteInvRslt
    MAX-ACCESS   read-only
    STATUS       current
    DESCRIPTION
        "Cisco Firepower aaa:TacacsPlusEp:fsmRmtInvRslt
        managed object property"
    ::= { cfprApAaaTacacsPlusEpEntry 10 }

cfprApAaaTacacsPlusEpFsmStageDescr OBJECT-TYPE
    SYNTAX       SnmpAdminString
    MAX-ACCESS   read-only
    STATUS       current
    DESCRIPTION
        "Cisco Firepower aaa:TacacsPlusEp:fsmStageDescr
        managed object property"
    ::= { cfprApAaaTacacsPlusEpEntry 11 }

cfprApAaaTacacsPlusEpFsmStamp OBJECT-TYPE
    SYNTAX       DateAndTime
    MAX-ACCESS   read-only
    STATUS       current
    DESCRIPTION
        "Cisco Firepower aaa:TacacsPlusEp:fsmStamp managed
        object property"
    ::= { cfprApAaaTacacsPlusEpEntry 12 }

cfprApAaaTacacsPlusEpFsmStatus OBJECT-TYPE
    SYNTAX       SnmpAdminString
    MAX-ACCESS   read-only
    STATUS       current
    DESCRIPTION
        "Cisco Firepower aaa:TacacsPlusEp:fsmStatus managed
        object property"
    ::= { cfprApAaaTacacsPlusEpEntry 13 }

cfprApAaaTacacsPlusEpFsmTry OBJECT-TYPE
    SYNTAX       Gauge32
    MAX-ACCESS   read-only
    STATUS       current
    DESCRIPTION
        "Cisco Firepower aaa:TacacsPlusEp:fsmTry managed object property"
    ::= { cfprApAaaTacacsPlusEpEntry 14 }

cfprApAaaTacacsPlusEpIntId OBJECT-TYPE
    SYNTAX       SnmpAdminString
    MAX-ACCESS   read-only
    STATUS       current
    DESCRIPTION
        "Cisco Firepower aaa:TacacsPlusEp:intId managed object property"
    ::= { cfprApAaaTacacsPlusEpEntry 15 }

cfprApAaaTacacsPlusEpName OBJECT-TYPE
    SYNTAX       SnmpAdminString
    MAX-ACCESS   read-only
    STATUS       current
    DESCRIPTION
        "Cisco Firepower aaa:TacacsPlusEp:name managed object property"
    ::= { cfprApAaaTacacsPlusEpEntry 16 }

cfprApAaaTacacsPlusEpPolicyLevel OBJECT-TYPE
    SYNTAX       Gauge32
    MAX-ACCESS   read-only
    STATUS       current
    DESCRIPTION
        "Cisco Firepower aaa:TacacsPlusEp:policyLevel managed
        object property"
    ::= { cfprApAaaTacacsPlusEpEntry 17 }

cfprApAaaTacacsPlusEpPolicyOwner OBJECT-TYPE
    SYNTAX       CfprApPolicyPolicyOwner
    MAX-ACCESS   read-only
    STATUS       current
    DESCRIPTION
        "Cisco Firepower aaa:TacacsPlusEp:policyOwner managed
        object property"
    ::= { cfprApAaaTacacsPlusEpEntry 18 }

cfprApAaaTacacsPlusEpRetries OBJECT-TYPE
    SYNTAX       Gauge32
    MAX-ACCESS   read-only
    STATUS       current
    DESCRIPTION
        "Cisco Firepower aaa:TacacsPlusEp:retries managed object property"
    ::= { cfprApAaaTacacsPlusEpEntry 19 }

cfprApAaaTacacsPlusEpTimeout OBJECT-TYPE
    SYNTAX       Gauge32
    MAX-ACCESS   read-only
    STATUS       current
    DESCRIPTION
        "Cisco Firepower aaa:TacacsPlusEp:timeout managed object property"
    ::= { cfprApAaaTacacsPlusEpEntry 20 }

cfprApAaaTacacsPlusEpFsmTable OBJECT-TYPE
    SYNTAX           SEQUENCE OF CfprApAaaTacacsPlusEpFsmEntry
    MAX-ACCESS       not-accessible
    STATUS           current
    DESCRIPTION
        "Cisco Firepower aaa:TacacsPlusEpFsm managed object table"
    ::= { cfprApAaaObjects 46 }

cfprApAaaTacacsPlusEpFsmEntry OBJECT-TYPE
    SYNTAX           CfprApAaaTacacsPlusEpFsmEntry
    MAX-ACCESS       not-accessible
    STATUS           current
    DESCRIPTION
        "Entry for the cfprApAaaTacacsPlusEpFsmTable table."
    INDEX { cfprApAaaTacacsPlusEpFsmInstanceId }
    ::= { cfprApAaaTacacsPlusEpFsmTable 1 }

CfprApAaaTacacsPlusEpFsmEntry ::= SEQUENCE {
    cfprApAaaTacacsPlusEpFsmInstanceId                               CfprApManagedObjectId,
    cfprApAaaTacacsPlusEpFsmDn                                       CfprApManagedObjectDn,
    cfprApAaaTacacsPlusEpFsmRn                                       SnmpAdminString,
    cfprApAaaTacacsPlusEpFsmCompletionTime                           DateAndTime,
    cfprApAaaTacacsPlusEpFsmCurrentFsm                               CfprApAaaTacacsPlusEpFsmCurrentFsm,
    cfprApAaaTacacsPlusEpFsmDescrData                                SnmpAdminString,
    cfprApAaaTacacsPlusEpFsmFsmStatus                                CfprApFsmFsmStageStatus,
    cfprApAaaTacacsPlusEpFsmProgress                                 Gauge32,
    cfprApAaaTacacsPlusEpFsmRmtErrCode                               Gauge32,
    cfprApAaaTacacsPlusEpFsmRmtErrDescr                              SnmpAdminString,
    cfprApAaaTacacsPlusEpFsmRmtRslt                                  CfprApConditionRemoteInvRslt
}

cfprApAaaTacacsPlusEpFsmInstanceId OBJECT-TYPE
    SYNTAX       CfprApManagedObjectId
    MAX-ACCESS   not-accessible
    STATUS       current
    DESCRIPTION
        "Instance identifier of the managed object."
    ::= { cfprApAaaTacacsPlusEpFsmEntry 1 }

cfprApAaaTacacsPlusEpFsmDn OBJECT-TYPE
    SYNTAX       CfprApManagedObjectDn
    MAX-ACCESS   read-only
    STATUS       current
    DESCRIPTION
        "Cisco Firepower aaa:TacacsPlusEpFsm:dn managed object property"
    ::= { cfprApAaaTacacsPlusEpFsmEntry 2 }

cfprApAaaTacacsPlusEpFsmRn OBJECT-TYPE
    SYNTAX       SnmpAdminString
    MAX-ACCESS   read-only
    STATUS       current
    DESCRIPTION
        "Cisco Firepower aaa:TacacsPlusEpFsm:rn managed object property"
    ::= { cfprApAaaTacacsPlusEpFsmEntry 3 }

cfprApAaaTacacsPlusEpFsmCompletionTime OBJECT-TYPE
    SYNTAX       DateAndTime
    MAX-ACCESS   read-only
    STATUS       current
    DESCRIPTION
        "Cisco Firepower aaa:TacacsPlusEpFsm:completionTime
        managed object property"
    ::= { cfprApAaaTacacsPlusEpFsmEntry 4 }

cfprApAaaTacacsPlusEpFsmCurrentFsm OBJECT-TYPE
    SYNTAX       CfprApAaaTacacsPlusEpFsmCurrentFsm
    MAX-ACCESS   read-only
    STATUS       current
    DESCRIPTION
        "Cisco Firepower aaa:TacacsPlusEpFsm:currentFsm
        managed object property"
    ::= { cfprApAaaTacacsPlusEpFsmEntry 5 }

cfprApAaaTacacsPlusEpFsmDescrData OBJECT-TYPE
    SYNTAX       SnmpAdminString
    MAX-ACCESS   read-only
    STATUS       current
    DESCRIPTION
        "Cisco Firepower aaa:TacacsPlusEpFsm:descr managed
        object property"
    ::= { cfprApAaaTacacsPlusEpFsmEntry 6 }

cfprApAaaTacacsPlusEpFsmFsmStatus OBJECT-TYPE
    SYNTAX       CfprApFsmFsmStageStatus
    MAX-ACCESS   read-only
    STATUS       current
    DESCRIPTION
        "Cisco Firepower aaa:TacacsPlusEpFsm:fsmStatus
        managed object property"
    ::= { cfprApAaaTacacsPlusEpFsmEntry 7 }

cfprApAaaTacacsPlusEpFsmProgress OBJECT-TYPE
    SYNTAX       Gauge32
    MAX-ACCESS   read-only
    STATUS       current
    DESCRIPTION
        "Cisco Firepower aaa:TacacsPlusEpFsm:progress managed
        object property"
    ::= { cfprApAaaTacacsPlusEpFsmEntry 8 }

cfprApAaaTacacsPlusEpFsmRmtErrCode OBJECT-TYPE
    SYNTAX       Gauge32
    MAX-ACCESS   read-only
    STATUS       current
    DESCRIPTION
        "Cisco Firepower aaa:TacacsPlusEpFsm:rmtErrCode
        managed object property"
    ::= { cfprApAaaTacacsPlusEpFsmEntry 9 }

cfprApAaaTacacsPlusEpFsmRmtErrDescr OBJECT-TYPE
    SYNTAX       SnmpAdminString
    MAX-ACCESS   read-only
    STATUS       current
    DESCRIPTION
        "Cisco Firepower aaa:TacacsPlusEpFsm:rmtErrDescr
        managed object property"
    ::= { cfprApAaaTacacsPlusEpFsmEntry 10 }

cfprApAaaTacacsPlusEpFsmRmtRslt OBJECT-TYPE
    SYNTAX       CfprApConditionRemoteInvRslt
    MAX-ACCESS   read-only
    STATUS       current
    DESCRIPTION
        "Cisco Firepower aaa:TacacsPlusEpFsm:rmtRslt managed
        object property"
    ::= { cfprApAaaTacacsPlusEpFsmEntry 11 }

cfprApAaaTacacsPlusEpFsmStageTable OBJECT-TYPE
    SYNTAX           SEQUENCE OF CfprApAaaTacacsPlusEpFsmStageEntry
    MAX-ACCESS       not-accessible
    STATUS           current
    DESCRIPTION
        "Cisco Firepower aaa:TacacsPlusEpFsmStage managed object table"
    ::= { cfprApAaaObjects 47 }

cfprApAaaTacacsPlusEpFsmStageEntry OBJECT-TYPE
    SYNTAX           CfprApAaaTacacsPlusEpFsmStageEntry
    MAX-ACCESS       not-accessible
    STATUS           current
    DESCRIPTION
        "Entry for the cfprApAaaTacacsPlusEpFsmStageTable table."
    INDEX { cfprApAaaTacacsPlusEpFsmStageInstanceId }
    ::= { cfprApAaaTacacsPlusEpFsmStageTable 1 }

CfprApAaaTacacsPlusEpFsmStageEntry ::= SEQUENCE {
    cfprApAaaTacacsPlusEpFsmStageInstanceId                          CfprApManagedObjectId,
    cfprApAaaTacacsPlusEpFsmStageDn                                  CfprApManagedObjectDn,
    cfprApAaaTacacsPlusEpFsmStageRn                                  SnmpAdminString,
    cfprApAaaTacacsPlusEpFsmStageDescrData                           SnmpAdminString,
    cfprApAaaTacacsPlusEpFsmStageLastUpdateTime                      DateAndTime,
    cfprApAaaTacacsPlusEpFsmStageName                                CfprApAaaTacacsPlusEpFsmStageName,
    cfprApAaaTacacsPlusEpFsmStageOrder                               Gauge32,
    cfprApAaaTacacsPlusEpFsmStageRetry                               Gauge32,
    cfprApAaaTacacsPlusEpFsmStageStageStatus                         CfprApFsmFsmStageStatus
}

cfprApAaaTacacsPlusEpFsmStageInstanceId OBJECT-TYPE
    SYNTAX       CfprApManagedObjectId
    MAX-ACCESS   not-accessible
    STATUS       current
    DESCRIPTION
        "Instance identifier of the managed object."
    ::= { cfprApAaaTacacsPlusEpFsmStageEntry 1 }

cfprApAaaTacacsPlusEpFsmStageDn OBJECT-TYPE
    SYNTAX       CfprApManagedObjectDn
    MAX-ACCESS   read-only
    STATUS       current
    DESCRIPTION
        "Cisco Firepower aaa:TacacsPlusEpFsmStage:dn managed
        object property"
    ::= { cfprApAaaTacacsPlusEpFsmStageEntry 2 }

cfprApAaaTacacsPlusEpFsmStageRn OBJECT-TYPE
    SYNTAX       SnmpAdminString
    MAX-ACCESS   read-only
    STATUS       current
    DESCRIPTION
        "Cisco Firepower aaa:TacacsPlusEpFsmStage:rn managed
        object property"
    ::= { cfprApAaaTacacsPlusEpFsmStageEntry 3 }

cfprApAaaTacacsPlusEpFsmStageDescrData OBJECT-TYPE
    SYNTAX       SnmpAdminString
    MAX-ACCESS   read-only
    STATUS       current
    DESCRIPTION
        "Cisco Firepower aaa:TacacsPlusEpFsmStage:descr
        managed object property"
    ::= { cfprApAaaTacacsPlusEpFsmStageEntry 4 }

cfprApAaaTacacsPlusEpFsmStageLastUpdateTime OBJECT-TYPE
    SYNTAX       DateAndTime
    MAX-ACCESS   read-only
    STATUS       current
    DESCRIPTION
        "Cisco Firepower aaa:TacacsPlusEpFsmStage:lastUpdateTime
        managed object property"
    ::= { cfprApAaaTacacsPlusEpFsmStageEntry 5 }

cfprApAaaTacacsPlusEpFsmStageName OBJECT-TYPE
    SYNTAX       CfprApAaaTacacsPlusEpFsmStageName
    MAX-ACCESS   read-only
    STATUS       current
    DESCRIPTION
        "Cisco Firepower aaa:TacacsPlusEpFsmStage:name
        managed object property"
    ::= { cfprApAaaTacacsPlusEpFsmStageEntry 6 }

cfprApAaaTacacsPlusEpFsmStageOrder OBJECT-TYPE
    SYNTAX       Gauge32
    MAX-ACCESS   read-only
    STATUS       current
    DESCRIPTION
        "Cisco Firepower aaa:TacacsPlusEpFsmStage:order
        managed object property"
    ::= { cfprApAaaTacacsPlusEpFsmStageEntry 7 }

cfprApAaaTacacsPlusEpFsmStageRetry OBJECT-TYPE
    SYNTAX       Gauge32
    MAX-ACCESS   read-only
    STATUS       current
    DESCRIPTION
        "Cisco Firepower aaa:TacacsPlusEpFsmStage:retry
        managed object property"
    ::= { cfprApAaaTacacsPlusEpFsmStageEntry 8 }

cfprApAaaTacacsPlusEpFsmStageStageStatus OBJECT-TYPE
    SYNTAX       CfprApFsmFsmStageStatus
    MAX-ACCESS   read-only
    STATUS       current
    DESCRIPTION
        "Cisco Firepower aaa:TacacsPlusEpFsmStage:stageStatus
        managed object property"
    ::= { cfprApAaaTacacsPlusEpFsmStageEntry 9 }

cfprApAaaTacacsPlusProviderTable OBJECT-TYPE
    SYNTAX           SEQUENCE OF CfprApAaaTacacsPlusProviderEntry
    MAX-ACCESS       not-accessible
    STATUS           current
    DESCRIPTION
        "Cisco Firepower aaa:TacacsPlusProvider managed object table"
    ::= { cfprApAaaObjects 48 }

cfprApAaaTacacsPlusProviderEntry OBJECT-TYPE
    SYNTAX           CfprApAaaTacacsPlusProviderEntry
    MAX-ACCESS       not-accessible
    STATUS           current
    DESCRIPTION
        "Entry for the cfprApAaaTacacsPlusProviderTable table."
    INDEX { cfprApAaaTacacsPlusProviderInstanceId }
    ::= { cfprApAaaTacacsPlusProviderTable 1 }

CfprApAaaTacacsPlusProviderEntry ::= SEQUENCE {
    cfprApAaaTacacsPlusProviderInstanceId                            CfprApManagedObjectId,
    cfprApAaaTacacsPlusProviderDn                                    CfprApManagedObjectDn,
    cfprApAaaTacacsPlusProviderRn                                    SnmpAdminString,
    cfprApAaaTacacsPlusProviderDescr                                 SnmpAdminString,
    cfprApAaaTacacsPlusProviderEncKey                                SnmpAdminString,
    cfprApAaaTacacsPlusProviderKey                                   SnmpAdminString,
    cfprApAaaTacacsPlusProviderKeySet                                TruthValue,
    cfprApAaaTacacsPlusProviderName                                  SnmpAdminString,
    cfprApAaaTacacsPlusProviderOrder                                 Gauge32,
    cfprApAaaTacacsPlusProviderPort                                  Gauge32,
    cfprApAaaTacacsPlusProviderRetries                               Gauge32,
    cfprApAaaTacacsPlusProviderTimeout                               Gauge32
}

cfprApAaaTacacsPlusProviderInstanceId OBJECT-TYPE
    SYNTAX       CfprApManagedObjectId
    MAX-ACCESS   not-accessible
    STATUS       current
    DESCRIPTION
        "Instance identifier of the managed object."
    ::= { cfprApAaaTacacsPlusProviderEntry 1 }

cfprApAaaTacacsPlusProviderDn OBJECT-TYPE
    SYNTAX       CfprApManagedObjectDn
    MAX-ACCESS   read-only
    STATUS       current
    DESCRIPTION
        "Cisco Firepower aaa:TacacsPlusProvider:dn managed
        object property"
    ::= { cfprApAaaTacacsPlusProviderEntry 2 }

cfprApAaaTacacsPlusProviderRn OBJECT-TYPE
    SYNTAX       SnmpAdminString
    MAX-ACCESS   read-only
    STATUS       current
    DESCRIPTION
        "Cisco Firepower aaa:TacacsPlusProvider:rn managed
        object property"
    ::= { cfprApAaaTacacsPlusProviderEntry 3 }

cfprApAaaTacacsPlusProviderDescr OBJECT-TYPE
    SYNTAX       SnmpAdminString
    MAX-ACCESS   read-only
    STATUS       current
    DESCRIPTION
        "Cisco Firepower aaa:TacacsPlusProvider:descr managed
        object property"
    ::= { cfprApAaaTacacsPlusProviderEntry 4 }

cfprApAaaTacacsPlusProviderEncKey OBJECT-TYPE
    SYNTAX       SnmpAdminString
    MAX-ACCESS   read-only
    STATUS       current
    DESCRIPTION
        "Cisco Firepower aaa:TacacsPlusProvider:encKey
        managed object property"
    ::= { cfprApAaaTacacsPlusProviderEntry 5 }

cfprApAaaTacacsPlusProviderKey OBJECT-TYPE
    SYNTAX       SnmpAdminString
    MAX-ACCESS   read-only
    STATUS       current
    DESCRIPTION
        "Cisco Firepower aaa:TacacsPlusProvider:key managed
        object property"
    ::= { cfprApAaaTacacsPlusProviderEntry 6 }

cfprApAaaTacacsPlusProviderKeySet OBJECT-TYPE
    SYNTAX       TruthValue
    MAX-ACCESS   read-only
    STATUS       current
    DESCRIPTION
        "Cisco Firepower aaa:TacacsPlusProvider:keySet
        managed object property"
    ::= { cfprApAaaTacacsPlusProviderEntry 7 }

cfprApAaaTacacsPlusProviderName OBJECT-TYPE
    SYNTAX       SnmpAdminString
    MAX-ACCESS   read-only
    STATUS       current
    DESCRIPTION
        "Cisco Firepower aaa:TacacsPlusProvider:name managed
        object property"
    ::= { cfprApAaaTacacsPlusProviderEntry 8 }

cfprApAaaTacacsPlusProviderOrder OBJECT-TYPE
    SYNTAX       Gauge32
    MAX-ACCESS   read-only
    STATUS       current
    DESCRIPTION
        "Cisco Firepower aaa:TacacsPlusProvider:order managed
        object property"
    ::= { cfprApAaaTacacsPlusProviderEntry 9 }

cfprApAaaTacacsPlusProviderPort OBJECT-TYPE
    SYNTAX       Gauge32
    MAX-ACCESS   read-only
    STATUS       current
    DESCRIPTION
        "Cisco Firepower aaa:TacacsPlusProvider:port managed
        object property"
    ::= { cfprApAaaTacacsPlusProviderEntry 10 }

cfprApAaaTacacsPlusProviderRetries OBJECT-TYPE
    SYNTAX       Gauge32
    MAX-ACCESS   read-only
    STATUS       current
    DESCRIPTION
        "Cisco Firepower aaa:TacacsPlusProvider:retries
        managed object property"
    ::= { cfprApAaaTacacsPlusProviderEntry 11 }

cfprApAaaTacacsPlusProviderTimeout OBJECT-TYPE
    SYNTAX       Gauge32
    MAX-ACCESS   read-only
    STATUS       current
    DESCRIPTION
        "Cisco Firepower aaa:TacacsPlusProvider:timeout
        managed object property"
    ::= { cfprApAaaTacacsPlusProviderEntry 12 }

cfprApAaaUserTable OBJECT-TYPE
    SYNTAX           SEQUENCE OF CfprApAaaUserEntry
    MAX-ACCESS       not-accessible
    STATUS           current
    DESCRIPTION
        "Cisco Firepower aaa:User managed object table"
    ::= { cfprApAaaObjects 49 }

cfprApAaaUserEntry OBJECT-TYPE
    SYNTAX           CfprApAaaUserEntry
    MAX-ACCESS       not-accessible
    STATUS           current
    DESCRIPTION
        "Entry for the cfprApAaaUserTable table."
    INDEX { cfprApAaaUserInstanceId }
    ::= { cfprApAaaUserTable 1 }

CfprApAaaUserEntry ::= SEQUENCE {
    cfprApAaaUserInstanceId                                          CfprApManagedObjectId,
    cfprApAaaUserDn                                                  CfprApManagedObjectDn,
    cfprApAaaUserRn                                                  SnmpAdminString,
    cfprApAaaUserAccountStatus                                       CfprApAaaAccountStatus,
    cfprApAaaUserClearPwdHistory                                     CfprApAaaClear,
    cfprApAaaUserConfigState                                         CfprApAaaConfigState,
    cfprApAaaUserConfigStatusMessage                                 SnmpAdminString,
    cfprApAaaUserDescr                                               SnmpAdminString,
    cfprApAaaUserEmail                                               SnmpAdminString,
    cfprApAaaUserEncPwd                                              SnmpAdminString,
    cfprApAaaUserEncPwdSet                                           TruthValue,
    cfprApAaaUserExpiration                                          DateAndTime,
    cfprApAaaUserExpires                                             TruthValue,
    cfprApAaaUserFirstName                                           SnmpAdminString,
    cfprApAaaUserLastName                                            SnmpAdminString,
    cfprApAaaUserName                                                SnmpAdminString,
    cfprApAaaUserPhone                                               SnmpAdminString,
    cfprApAaaUserPriv                                                CfprApAaaAccess,
    cfprApAaaUserPwd                                                 SnmpAdminString,
    cfprApAaaUserPwdSet                                              TruthValue
}

cfprApAaaUserInstanceId OBJECT-TYPE
    SYNTAX       CfprApManagedObjectId
    MAX-ACCESS   not-accessible
    STATUS       current
    DESCRIPTION
        "Instance identifier of the managed object."
    ::= { cfprApAaaUserEntry 1 }

cfprApAaaUserDn OBJECT-TYPE
    SYNTAX       CfprApManagedObjectDn
    MAX-ACCESS   read-only
    STATUS       current
    DESCRIPTION
        "Cisco Firepower aaa:User:dn managed object property"
    ::= { cfprApAaaUserEntry 2 }

cfprApAaaUserRn OBJECT-TYPE
    SYNTAX       SnmpAdminString
    MAX-ACCESS   read-only
    STATUS       current
    DESCRIPTION
        "Cisco Firepower aaa:User:rn managed object property"
    ::= { cfprApAaaUserEntry 3 }

cfprApAaaUserAccountStatus OBJECT-TYPE
    SYNTAX       CfprApAaaAccountStatus
    MAX-ACCESS   read-only
    STATUS       current
    DESCRIPTION
        "Cisco Firepower aaa:User:accountStatus managed object property"
    ::= { cfprApAaaUserEntry 4 }

cfprApAaaUserClearPwdHistory OBJECT-TYPE
    SYNTAX       CfprApAaaClear
    MAX-ACCESS   read-only
    STATUS       current
    DESCRIPTION
        "Cisco Firepower aaa:User:clearPwdHistory managed object property"
    ::= { cfprApAaaUserEntry 5 }

cfprApAaaUserConfigState OBJECT-TYPE
    SYNTAX       CfprApAaaConfigState
    MAX-ACCESS   read-only
    STATUS       current
    DESCRIPTION
        "Cisco Firepower aaa:User:configState managed object property"
    ::= { cfprApAaaUserEntry 6 }

cfprApAaaUserConfigStatusMessage OBJECT-TYPE
    SYNTAX       SnmpAdminString
    MAX-ACCESS   read-only
    STATUS       current
    DESCRIPTION
        "Cisco Firepower aaa:User:configStatusMessage managed
        object property"
    ::= { cfprApAaaUserEntry 7 }

cfprApAaaUserDescr OBJECT-TYPE
    SYNTAX       SnmpAdminString
    MAX-ACCESS   read-only
    STATUS       current
    DESCRIPTION
        "Cisco Firepower aaa:User:descr managed object property"
    ::= { cfprApAaaUserEntry 8 }

cfprApAaaUserEmail OBJECT-TYPE
    SYNTAX       SnmpAdminString
    MAX-ACCESS   read-only
    STATUS       current
    DESCRIPTION
        "Cisco Firepower aaa:User:email managed object property"
    ::= { cfprApAaaUserEntry 9 }

cfprApAaaUserEncPwd OBJECT-TYPE
    SYNTAX       SnmpAdminString
    MAX-ACCESS   read-only
    STATUS       current
    DESCRIPTION
        "Cisco Firepower aaa:User:encPwd managed object property"
    ::= { cfprApAaaUserEntry 10 }

cfprApAaaUserEncPwdSet OBJECT-TYPE
    SYNTAX       TruthValue
    MAX-ACCESS   read-only
    STATUS       current
    DESCRIPTION
        "Cisco Firepower aaa:User:encPwdSet managed object property"
    ::= { cfprApAaaUserEntry 11 }

cfprApAaaUserExpiration OBJECT-TYPE
    SYNTAX       DateAndTime
    MAX-ACCESS   read-only
    STATUS       current
    DESCRIPTION
        "Cisco Firepower aaa:User:expiration managed object property"
    ::= { cfprApAaaUserEntry 12 }

cfprApAaaUserExpires OBJECT-TYPE
    SYNTAX       TruthValue
    MAX-ACCESS   read-only
    STATUS       current
    DESCRIPTION
        "Cisco Firepower aaa:User:expires managed object property"
    ::= { cfprApAaaUserEntry 13 }

cfprApAaaUserFirstName OBJECT-TYPE
    SYNTAX       SnmpAdminString
    MAX-ACCESS   read-only
    STATUS       current
    DESCRIPTION
        "Cisco Firepower aaa:User:firstName managed object property"
    ::= { cfprApAaaUserEntry 14 }

cfprApAaaUserLastName OBJECT-TYPE
    SYNTAX       SnmpAdminString
    MAX-ACCESS   read-only
    STATUS       current
    DESCRIPTION
        "Cisco Firepower aaa:User:lastName managed object property"
    ::= { cfprApAaaUserEntry 15 }

cfprApAaaUserName OBJECT-TYPE
    SYNTAX       SnmpAdminString
    MAX-ACCESS   read-only
    STATUS       current
    DESCRIPTION
        "Cisco Firepower aaa:User:name managed object property"
    ::= { cfprApAaaUserEntry 16 }

cfprApAaaUserPhone OBJECT-TYPE
    SYNTAX       SnmpAdminString
    MAX-ACCESS   read-only
    STATUS       current
    DESCRIPTION
        "Cisco Firepower aaa:User:phone managed object property"
    ::= { cfprApAaaUserEntry 17 }

cfprApAaaUserPriv OBJECT-TYPE
    SYNTAX       CfprApAaaAccess
    MAX-ACCESS   read-only
    STATUS       current
    DESCRIPTION
        "Cisco Firepower aaa:User:priv managed object property"
    ::= { cfprApAaaUserEntry 18 }

cfprApAaaUserPwd OBJECT-TYPE
    SYNTAX       SnmpAdminString
    MAX-ACCESS   read-only
    STATUS       current
    DESCRIPTION
        "Cisco Firepower aaa:User:pwd managed object property"
    ::= { cfprApAaaUserEntry 19 }

cfprApAaaUserPwdSet OBJECT-TYPE
    SYNTAX       TruthValue
    MAX-ACCESS   read-only
    STATUS       current
    DESCRIPTION
        "Cisco Firepower aaa:User:pwdSet managed object property"
    ::= { cfprApAaaUserEntry 21 }

cfprApAaaUserDataTable OBJECT-TYPE
    SYNTAX           SEQUENCE OF CfprApAaaUserDataEntry
    MAX-ACCESS       not-accessible
    STATUS           current
    DESCRIPTION
        "Cisco Firepower aaa:UserData managed object table"
    ::= { cfprApAaaObjects 50 }

cfprApAaaUserDataEntry OBJECT-TYPE
    SYNTAX           CfprApAaaUserDataEntry
    MAX-ACCESS       not-accessible
    STATUS           current
    DESCRIPTION
        "Entry for the cfprApAaaUserDataTable table."
    INDEX { cfprApAaaUserDataInstanceId }
    ::= { cfprApAaaUserDataTable 1 }

CfprApAaaUserDataEntry ::= SEQUENCE {
    cfprApAaaUserDataInstanceId                                      CfprApManagedObjectId,
    cfprApAaaUserDataDn                                              CfprApManagedObjectDn,
    cfprApAaaUserDataRn                                              SnmpAdminString,
    cfprApAaaUserDataDescr                                           SnmpAdminString,
    cfprApAaaUserDataIntId                                           SnmpAdminString,
    cfprApAaaUserDataName                                            SnmpAdminString,
    cfprApAaaUserDataPolicyLevel                                     Gauge32,
    cfprApAaaUserDataPolicyOwner                                     CfprApPolicyPolicyOwner,
    cfprApAaaUserDataPwdChangeCount                                  Gauge32,
    cfprApAaaUserDataPwdChangeIntervalBegin                          DateAndTime,
    cfprApAaaUserDataPwdChangedDate                                  DateAndTime,
    cfprApAaaUserDataPwdHistory                                      SnmpAdminString
}

cfprApAaaUserDataInstanceId OBJECT-TYPE
    SYNTAX       CfprApManagedObjectId
    MAX-ACCESS   not-accessible
    STATUS       current
    DESCRIPTION
        "Instance identifier of the managed object."
    ::= { cfprApAaaUserDataEntry 1 }

cfprApAaaUserDataDn OBJECT-TYPE
    SYNTAX       CfprApManagedObjectDn
    MAX-ACCESS   read-only
    STATUS       current
    DESCRIPTION
        "Cisco Firepower aaa:UserData:dn managed object property"
    ::= { cfprApAaaUserDataEntry 2 }

cfprApAaaUserDataRn OBJECT-TYPE
    SYNTAX       SnmpAdminString
    MAX-ACCESS   read-only
    STATUS       current
    DESCRIPTION
        "Cisco Firepower aaa:UserData:rn managed object property"
    ::= { cfprApAaaUserDataEntry 3 }

cfprApAaaUserDataDescr OBJECT-TYPE
    SYNTAX       SnmpAdminString
    MAX-ACCESS   read-only
    STATUS       current
    DESCRIPTION
        "Cisco Firepower aaa:UserData:descr managed object property"
    ::= { cfprApAaaUserDataEntry 4 }

cfprApAaaUserDataIntId OBJECT-TYPE
    SYNTAX       SnmpAdminString
    MAX-ACCESS   read-only
    STATUS       current
    DESCRIPTION
        "Cisco Firepower aaa:UserData:intId managed object property"
    ::= { cfprApAaaUserDataEntry 5 }

cfprApAaaUserDataName OBJECT-TYPE
    SYNTAX       SnmpAdminString
    MAX-ACCESS   read-only
    STATUS       current
    DESCRIPTION
        "Cisco Firepower aaa:UserData:name managed object property"
    ::= { cfprApAaaUserDataEntry 6 }

cfprApAaaUserDataPolicyLevel OBJECT-TYPE
    SYNTAX       Gauge32
    MAX-ACCESS   read-only
    STATUS       current
    DESCRIPTION
        "Cisco Firepower aaa:UserData:policyLevel managed object property"
    ::= { cfprApAaaUserDataEntry 7 }

cfprApAaaUserDataPolicyOwner OBJECT-TYPE
    SYNTAX       CfprApPolicyPolicyOwner
    MAX-ACCESS   read-only
    STATUS       current
    DESCRIPTION
        "Cisco Firepower aaa:UserData:policyOwner managed object property"
    ::= { cfprApAaaUserDataEntry 8 }

cfprApAaaUserDataPwdChangeCount OBJECT-TYPE
    SYNTAX       Gauge32
    MAX-ACCESS   read-only
    STATUS       current
    DESCRIPTION
        "Cisco Firepower aaa:UserData:pwdChangeCount managed
        object property"
    ::= { cfprApAaaUserDataEntry 9 }

cfprApAaaUserDataPwdChangeIntervalBegin OBJECT-TYPE
    SYNTAX       DateAndTime
    MAX-ACCESS   read-only
    STATUS       current
    DESCRIPTION
        "Cisco Firepower aaa:UserData:pwdChangeIntervalBegin
        managed object property"
    ::= { cfprApAaaUserDataEntry 10 }

cfprApAaaUserDataPwdChangedDate OBJECT-TYPE
    SYNTAX       DateAndTime
    MAX-ACCESS   read-only
    STATUS       current
    DESCRIPTION
        "Cisco Firepower aaa:UserData:pwdChangedDate managed
        object property"
    ::= { cfprApAaaUserDataEntry 11 }

cfprApAaaUserDataPwdHistory OBJECT-TYPE
    SYNTAX       SnmpAdminString
    MAX-ACCESS   read-only
    STATUS       current
    DESCRIPTION
        "Cisco Firepower aaa:UserData:pwdHistory managed object property"
    ::= { cfprApAaaUserDataEntry 12 }

cfprApAaaUserEpTable OBJECT-TYPE
    SYNTAX           SEQUENCE OF CfprApAaaUserEpEntry
    MAX-ACCESS       not-accessible
    STATUS           current
    DESCRIPTION
        "Cisco Firepower aaa:UserEp managed object table"
    ::= { cfprApAaaObjects 51 }

cfprApAaaUserEpEntry OBJECT-TYPE
    SYNTAX           CfprApAaaUserEpEntry
    MAX-ACCESS       not-accessible
    STATUS           current
    DESCRIPTION
        "Entry for the cfprApAaaUserEpTable table."
    INDEX { cfprApAaaUserEpInstanceId }
    ::= { cfprApAaaUserEpTable 1 }

CfprApAaaUserEpEntry ::= SEQUENCE {
    cfprApAaaUserEpInstanceId                                        CfprApManagedObjectId,
    cfprApAaaUserEpDn                                                CfprApManagedObjectDn,
    cfprApAaaUserEpRn                                                SnmpAdminString,
    cfprApAaaUserEpDescr                                             SnmpAdminString,
    cfprApAaaUserEpFsmDescr                                          SnmpAdminString,
    cfprApAaaUserEpFsmPrev                                           SnmpAdminString,
    cfprApAaaUserEpFsmProgr                                          Gauge32,
    cfprApAaaUserEpFsmRmtInvErrCode                                  Gauge32,
    cfprApAaaUserEpFsmRmtInvErrDescr                                 SnmpAdminString,
    cfprApAaaUserEpFsmRmtInvRslt                                     CfprApConditionRemoteInvRslt,
    cfprApAaaUserEpFsmStageDescr                                     SnmpAdminString,
    cfprApAaaUserEpFsmStamp                                          DateAndTime,
    cfprApAaaUserEpFsmStatus                                         SnmpAdminString,
    cfprApAaaUserEpFsmTry                                            Gauge32,
    cfprApAaaUserEpIntId                                             SnmpAdminString,
    cfprApAaaUserEpMaxLoginAttempts                                  Gauge32,
    cfprApAaaUserEpMinPwdLength                                      Gauge32,
    cfprApAaaUserEpName                                              SnmpAdminString,
    cfprApAaaUserEpPolicyLevel                                       Gauge32,
    cfprApAaaUserEpPolicyOwner                                       CfprApPolicyPolicyOwner,
    cfprApAaaUserEpPwdStrengthCheck                                  TruthValue,
    cfprApAaaUserEpUserAccountUnlockTime                             Gauge32
}

cfprApAaaUserEpInstanceId OBJECT-TYPE
    SYNTAX       CfprApManagedObjectId
    MAX-ACCESS   not-accessible
    STATUS       current
    DESCRIPTION
        "Instance identifier of the managed object."
    ::= { cfprApAaaUserEpEntry 1 }

cfprApAaaUserEpDn OBJECT-TYPE
    SYNTAX       CfprApManagedObjectDn
    MAX-ACCESS   read-only
    STATUS       current
    DESCRIPTION
        "Cisco Firepower aaa:UserEp:dn managed object property"
    ::= { cfprApAaaUserEpEntry 2 }

cfprApAaaUserEpRn OBJECT-TYPE
    SYNTAX       SnmpAdminString
    MAX-ACCESS   read-only
    STATUS       current
    DESCRIPTION
        "Cisco Firepower aaa:UserEp:rn managed object property"
    ::= { cfprApAaaUserEpEntry 3 }

cfprApAaaUserEpDescr OBJECT-TYPE
    SYNTAX       SnmpAdminString
    MAX-ACCESS   read-only
    STATUS       current
    DESCRIPTION
        "Cisco Firepower aaa:UserEp:descr managed object property"
    ::= { cfprApAaaUserEpEntry 4 }

cfprApAaaUserEpFsmDescr OBJECT-TYPE
    SYNTAX       SnmpAdminString
    MAX-ACCESS   read-only
    STATUS       current
    DESCRIPTION
        "Cisco Firepower aaa:UserEp:fsmDescr managed object property"
    ::= { cfprApAaaUserEpEntry 5 }

cfprApAaaUserEpFsmPrev OBJECT-TYPE
    SYNTAX       SnmpAdminString
    MAX-ACCESS   read-only
    STATUS       current
    DESCRIPTION
        "Cisco Firepower aaa:UserEp:fsmPrev managed object property"
    ::= { cfprApAaaUserEpEntry 6 }

cfprApAaaUserEpFsmProgr OBJECT-TYPE
    SYNTAX       Gauge32
    MAX-ACCESS   read-only
    STATUS       current
    DESCRIPTION
        "Cisco Firepower aaa:UserEp:fsmProgr managed object property"
    ::= { cfprApAaaUserEpEntry 7 }

cfprApAaaUserEpFsmRmtInvErrCode OBJECT-TYPE
    SYNTAX       Gauge32
    MAX-ACCESS   read-only
    STATUS       current
    DESCRIPTION
        "Cisco Firepower aaa:UserEp:fsmRmtInvErrCode managed
        object property"
    ::= { cfprApAaaUserEpEntry 8 }

cfprApAaaUserEpFsmRmtInvErrDescr OBJECT-TYPE
    SYNTAX       SnmpAdminString
    MAX-ACCESS   read-only
    STATUS       current
    DESCRIPTION
        "Cisco Firepower aaa:UserEp:fsmRmtInvErrDescr managed
        object property"
    ::= { cfprApAaaUserEpEntry 9 }

cfprApAaaUserEpFsmRmtInvRslt OBJECT-TYPE
    SYNTAX       CfprApConditionRemoteInvRslt
    MAX-ACCESS   read-only
    STATUS       current
    DESCRIPTION
        "Cisco Firepower aaa:UserEp:fsmRmtInvRslt managed object property"
    ::= { cfprApAaaUserEpEntry 10 }

cfprApAaaUserEpFsmStageDescr OBJECT-TYPE
    SYNTAX       SnmpAdminString
    MAX-ACCESS   read-only
    STATUS       current
    DESCRIPTION
        "Cisco Firepower aaa:UserEp:fsmStageDescr managed object property"
    ::= { cfprApAaaUserEpEntry 11 }

cfprApAaaUserEpFsmStamp OBJECT-TYPE
    SYNTAX       DateAndTime
    MAX-ACCESS   read-only
    STATUS       current
    DESCRIPTION
        "Cisco Firepower aaa:UserEp:fsmStamp managed object property"
    ::= { cfprApAaaUserEpEntry 12 }

cfprApAaaUserEpFsmStatus OBJECT-TYPE
    SYNTAX       SnmpAdminString
    MAX-ACCESS   read-only
    STATUS       current
    DESCRIPTION
        "Cisco Firepower aaa:UserEp:fsmStatus managed object property"
    ::= { cfprApAaaUserEpEntry 13 }

cfprApAaaUserEpFsmTry OBJECT-TYPE
    SYNTAX       Gauge32
    MAX-ACCESS   read-only
    STATUS       current
    DESCRIPTION
        "Cisco Firepower aaa:UserEp:fsmTry managed object property"
    ::= { cfprApAaaUserEpEntry 14 }

cfprApAaaUserEpIntId OBJECT-TYPE
    SYNTAX       SnmpAdminString
    MAX-ACCESS   read-only
    STATUS       current
    DESCRIPTION
        "Cisco Firepower aaa:UserEp:intId managed object property"
    ::= { cfprApAaaUserEpEntry 15 }

cfprApAaaUserEpMaxLoginAttempts OBJECT-TYPE
    SYNTAX       Gauge32
    MAX-ACCESS   read-only
    STATUS       current
    DESCRIPTION
        "Cisco Firepower aaa:UserEp:maxLoginAttempts managed
        object property"
    ::= { cfprApAaaUserEpEntry 16 }

cfprApAaaUserEpMinPwdLength OBJECT-TYPE
    SYNTAX       Gauge32
    MAX-ACCESS   read-only
    STATUS       current
    DESCRIPTION
        "Cisco Firepower aaa:UserEp:minPwdLength managed object property"
    ::= { cfprApAaaUserEpEntry 17 }

cfprApAaaUserEpName OBJECT-TYPE
    SYNTAX       SnmpAdminString
    MAX-ACCESS   read-only
    STATUS       current
    DESCRIPTION
        "Cisco Firepower aaa:UserEp:name managed object property"
    ::= { cfprApAaaUserEpEntry 18 }

cfprApAaaUserEpPolicyLevel OBJECT-TYPE
    SYNTAX       Gauge32
    MAX-ACCESS   read-only
    STATUS       current
    DESCRIPTION
        "Cisco Firepower aaa:UserEp:policyLevel managed object property"
    ::= { cfprApAaaUserEpEntry 19 }

cfprApAaaUserEpPolicyOwner OBJECT-TYPE
    SYNTAX       CfprApPolicyPolicyOwner
    MAX-ACCESS   read-only
    STATUS       current
    DESCRIPTION
        "Cisco Firepower aaa:UserEp:policyOwner managed object property"
    ::= { cfprApAaaUserEpEntry 20 }

cfprApAaaUserEpPwdStrengthCheck OBJECT-TYPE
    SYNTAX       TruthValue
    MAX-ACCESS   read-only
    STATUS       current
    DESCRIPTION
        "Cisco Firepower aaa:UserEp:pwdStrengthCheck managed
        object property"
    ::= { cfprApAaaUserEpEntry 21 }

cfprApAaaUserEpUserAccountUnlockTime OBJECT-TYPE
    SYNTAX       Gauge32
    MAX-ACCESS   read-only
    STATUS       current
    DESCRIPTION
        "Cisco Firepower aaa:UserEp:userAccountUnlockTime
        managed object property"
    ::= { cfprApAaaUserEpEntry 22 }

cfprApAaaUserEpFsmTable OBJECT-TYPE
    SYNTAX           SEQUENCE OF CfprApAaaUserEpFsmEntry
    MAX-ACCESS       not-accessible
    STATUS           current
    DESCRIPTION
        "Cisco Firepower aaa:UserEpFsm managed object table"
    ::= { cfprApAaaObjects 52 }

cfprApAaaUserEpFsmEntry OBJECT-TYPE
    SYNTAX           CfprApAaaUserEpFsmEntry
    MAX-ACCESS       not-accessible
    STATUS           current
    DESCRIPTION
        "Entry for the cfprApAaaUserEpFsmTable table."
    INDEX { cfprApAaaUserEpFsmInstanceId }
    ::= { cfprApAaaUserEpFsmTable 1 }

CfprApAaaUserEpFsmEntry ::= SEQUENCE {
    cfprApAaaUserEpFsmInstanceId                                     CfprApManagedObjectId,
    cfprApAaaUserEpFsmDn                                             CfprApManagedObjectDn,
    cfprApAaaUserEpFsmRn                                             SnmpAdminString,
    cfprApAaaUserEpFsmCompletionTime                                 DateAndTime,
    cfprApAaaUserEpFsmCurrentFsm                                     CfprApAaaUserEpFsmCurrentFsm,
    cfprApAaaUserEpFsmDescrData                                      SnmpAdminString,
    cfprApAaaUserEpFsmFsmStatus                                      CfprApFsmFsmStageStatus,
    cfprApAaaUserEpFsmProgress                                       Gauge32,
    cfprApAaaUserEpFsmRmtErrCode                                     Gauge32,
    cfprApAaaUserEpFsmRmtErrDescr                                    SnmpAdminString,
    cfprApAaaUserEpFsmRmtRslt                                        CfprApConditionRemoteInvRslt
}

cfprApAaaUserEpFsmInstanceId OBJECT-TYPE
    SYNTAX       CfprApManagedObjectId
    MAX-ACCESS   not-accessible
    STATUS       current
    DESCRIPTION
        "Instance identifier of the managed object."
    ::= { cfprApAaaUserEpFsmEntry 1 }

cfprApAaaUserEpFsmDn OBJECT-TYPE
    SYNTAX       CfprApManagedObjectDn
    MAX-ACCESS   read-only
    STATUS       current
    DESCRIPTION
        "Cisco Firepower aaa:UserEpFsm:dn managed object property"
    ::= { cfprApAaaUserEpFsmEntry 2 }

cfprApAaaUserEpFsmRn OBJECT-TYPE
    SYNTAX       SnmpAdminString
    MAX-ACCESS   read-only
    STATUS       current
    DESCRIPTION
        "Cisco Firepower aaa:UserEpFsm:rn managed object property"
    ::= { cfprApAaaUserEpFsmEntry 3 }

cfprApAaaUserEpFsmCompletionTime OBJECT-TYPE
    SYNTAX       DateAndTime
    MAX-ACCESS   read-only
    STATUS       current
    DESCRIPTION
        "Cisco Firepower aaa:UserEpFsm:completionTime managed
        object property"
    ::= { cfprApAaaUserEpFsmEntry 4 }

cfprApAaaUserEpFsmCurrentFsm OBJECT-TYPE
    SYNTAX       CfprApAaaUserEpFsmCurrentFsm
    MAX-ACCESS   read-only
    STATUS       current
    DESCRIPTION
        "Cisco Firepower aaa:UserEpFsm:currentFsm managed object property"
    ::= { cfprApAaaUserEpFsmEntry 5 }

cfprApAaaUserEpFsmDescrData OBJECT-TYPE
    SYNTAX       SnmpAdminString
    MAX-ACCESS   read-only
    STATUS       current
    DESCRIPTION
        "Cisco Firepower aaa:UserEpFsm:descr managed object property"
    ::= { cfprApAaaUserEpFsmEntry 6 }

cfprApAaaUserEpFsmFsmStatus OBJECT-TYPE
    SYNTAX       CfprApFsmFsmStageStatus
    MAX-ACCESS   read-only
    STATUS       current
    DESCRIPTION
        "Cisco Firepower aaa:UserEpFsm:fsmStatus managed object property"
    ::= { cfprApAaaUserEpFsmEntry 7 }

cfprApAaaUserEpFsmProgress OBJECT-TYPE
    SYNTAX       Gauge32
    MAX-ACCESS   read-only
    STATUS       current
    DESCRIPTION
        "Cisco Firepower aaa:UserEpFsm:progress managed object property"
    ::= { cfprApAaaUserEpFsmEntry 8 }

cfprApAaaUserEpFsmRmtErrCode OBJECT-TYPE
    SYNTAX       Gauge32
    MAX-ACCESS   read-only
    STATUS       current
    DESCRIPTION
        "Cisco Firepower aaa:UserEpFsm:rmtErrCode managed object property"
    ::= { cfprApAaaUserEpFsmEntry 9 }

cfprApAaaUserEpFsmRmtErrDescr OBJECT-TYPE
    SYNTAX       SnmpAdminString
    MAX-ACCESS   read-only
    STATUS       current
    DESCRIPTION
        "Cisco Firepower aaa:UserEpFsm:rmtErrDescr managed
        object property"
    ::= { cfprApAaaUserEpFsmEntry 10 }

cfprApAaaUserEpFsmRmtRslt OBJECT-TYPE
    SYNTAX       CfprApConditionRemoteInvRslt
    MAX-ACCESS   read-only
    STATUS       current
    DESCRIPTION
        "Cisco Firepower aaa:UserEpFsm:rmtRslt managed object property"
    ::= { cfprApAaaUserEpFsmEntry 11 }

cfprApAaaUserEpFsmStageTable OBJECT-TYPE
    SYNTAX           SEQUENCE OF CfprApAaaUserEpFsmStageEntry
    MAX-ACCESS       not-accessible
    STATUS           current
    DESCRIPTION
        "Cisco Firepower aaa:UserEpFsmStage managed object table"
    ::= { cfprApAaaObjects 53 }

cfprApAaaUserEpFsmStageEntry OBJECT-TYPE
    SYNTAX           CfprApAaaUserEpFsmStageEntry
    MAX-ACCESS       not-accessible
    STATUS           current
    DESCRIPTION
        "Entry for the cfprApAaaUserEpFsmStageTable table."
    INDEX { cfprApAaaUserEpFsmStageInstanceId }
    ::= { cfprApAaaUserEpFsmStageTable 1 }

CfprApAaaUserEpFsmStageEntry ::= SEQUENCE {
    cfprApAaaUserEpFsmStageInstanceId                                CfprApManagedObjectId,
    cfprApAaaUserEpFsmStageDn                                        CfprApManagedObjectDn,
    cfprApAaaUserEpFsmStageRn                                        SnmpAdminString,
    cfprApAaaUserEpFsmStageDescrData                                 SnmpAdminString,
    cfprApAaaUserEpFsmStageLastUpdateTime                            DateAndTime,
    cfprApAaaUserEpFsmStageName                                      CfprApAaaUserEpFsmStageName,
    cfprApAaaUserEpFsmStageOrder                                     Gauge32,
    cfprApAaaUserEpFsmStageRetry                                     Gauge32,
    cfprApAaaUserEpFsmStageStageStatus                               CfprApFsmFsmStageStatus
}

cfprApAaaUserEpFsmStageInstanceId OBJECT-TYPE
    SYNTAX       CfprApManagedObjectId
    MAX-ACCESS   not-accessible
    STATUS       current
    DESCRIPTION
        "Instance identifier of the managed object."
    ::= { cfprApAaaUserEpFsmStageEntry 1 }

cfprApAaaUserEpFsmStageDn OBJECT-TYPE
    SYNTAX       CfprApManagedObjectDn
    MAX-ACCESS   read-only
    STATUS       current
    DESCRIPTION
        "Cisco Firepower aaa:UserEpFsmStage:dn managed object property"
    ::= { cfprApAaaUserEpFsmStageEntry 2 }

cfprApAaaUserEpFsmStageRn OBJECT-TYPE
    SYNTAX       SnmpAdminString
    MAX-ACCESS   read-only
    STATUS       current
    DESCRIPTION
        "Cisco Firepower aaa:UserEpFsmStage:rn managed object property"
    ::= { cfprApAaaUserEpFsmStageEntry 3 }

cfprApAaaUserEpFsmStageDescrData OBJECT-TYPE
    SYNTAX       SnmpAdminString
    MAX-ACCESS   read-only
    STATUS       current
    DESCRIPTION
        "Cisco Firepower aaa:UserEpFsmStage:descr managed object property"
    ::= { cfprApAaaUserEpFsmStageEntry 4 }

cfprApAaaUserEpFsmStageLastUpdateTime OBJECT-TYPE
    SYNTAX       DateAndTime
    MAX-ACCESS   read-only
    STATUS       current
    DESCRIPTION
        "Cisco Firepower aaa:UserEpFsmStage:lastUpdateTime
        managed object property"
    ::= { cfprApAaaUserEpFsmStageEntry 5 }

cfprApAaaUserEpFsmStageName OBJECT-TYPE
    SYNTAX       CfprApAaaUserEpFsmStageName
    MAX-ACCESS   read-only
    STATUS       current
    DESCRIPTION
        "Cisco Firepower aaa:UserEpFsmStage:name managed object property"
    ::= { cfprApAaaUserEpFsmStageEntry 6 }

cfprApAaaUserEpFsmStageOrder OBJECT-TYPE
    SYNTAX       Gauge32
    MAX-ACCESS   read-only
    STATUS       current
    DESCRIPTION
        "Cisco Firepower aaa:UserEpFsmStage:order managed object property"
    ::= { cfprApAaaUserEpFsmStageEntry 7 }

cfprApAaaUserEpFsmStageRetry OBJECT-TYPE
    SYNTAX       Gauge32
    MAX-ACCESS   read-only
    STATUS       current
    DESCRIPTION
        "Cisco Firepower aaa:UserEpFsmStage:retry managed object property"
    ::= { cfprApAaaUserEpFsmStageEntry 8 }

cfprApAaaUserEpFsmStageStageStatus OBJECT-TYPE
    SYNTAX       CfprApFsmFsmStageStatus
    MAX-ACCESS   read-only
    STATUS       current
    DESCRIPTION
        "Cisco Firepower aaa:UserEpFsmStage:stageStatus
        managed object property"
    ::= { cfprApAaaUserEpFsmStageEntry 9 }

cfprApAaaUserEpFsmTaskTable OBJECT-TYPE
    SYNTAX           SEQUENCE OF CfprApAaaUserEpFsmTaskEntry
    MAX-ACCESS       not-accessible
    STATUS           current
    DESCRIPTION
        "Cisco Firepower aaa:UserEpFsmTask managed object table"
    ::= { cfprApAaaObjects 54 }

cfprApAaaUserEpFsmTaskEntry OBJECT-TYPE
    SYNTAX           CfprApAaaUserEpFsmTaskEntry
    MAX-ACCESS       not-accessible
    STATUS           current
    DESCRIPTION
        "Entry for the cfprApAaaUserEpFsmTaskTable table."
    INDEX { cfprApAaaUserEpFsmTaskInstanceId }
    ::= { cfprApAaaUserEpFsmTaskTable 1 }

CfprApAaaUserEpFsmTaskEntry ::= SEQUENCE {
    cfprApAaaUserEpFsmTaskInstanceId                                 CfprApManagedObjectId,
    cfprApAaaUserEpFsmTaskDn                                         CfprApManagedObjectDn,
    cfprApAaaUserEpFsmTaskRn                                         SnmpAdminString,
    cfprApAaaUserEpFsmTaskCompletion                                 CfprApFsmCompletion,
    cfprApAaaUserEpFsmTaskFlags                                      CfprApFsmFlags,
    cfprApAaaUserEpFsmTaskItem                                       CfprApAaaUserEpFsmTaskItem,
    cfprApAaaUserEpFsmTaskSeqId                                      Gauge32
}

cfprApAaaUserEpFsmTaskInstanceId OBJECT-TYPE
    SYNTAX       CfprApManagedObjectId
    MAX-ACCESS   not-accessible
    STATUS       current
    DESCRIPTION
        "Instance identifier of the managed object."
    ::= { cfprApAaaUserEpFsmTaskEntry 1 }

cfprApAaaUserEpFsmTaskDn OBJECT-TYPE
    SYNTAX       CfprApManagedObjectDn
    MAX-ACCESS   read-only
    STATUS       current
    DESCRIPTION
        "Cisco Firepower aaa:UserEpFsmTask:dn managed object property"
    ::= { cfprApAaaUserEpFsmTaskEntry 2 }

cfprApAaaUserEpFsmTaskRn OBJECT-TYPE
    SYNTAX       SnmpAdminString
    MAX-ACCESS   read-only
    STATUS       current
    DESCRIPTION
        "Cisco Firepower aaa:UserEpFsmTask:rn managed object property"
    ::= { cfprApAaaUserEpFsmTaskEntry 3 }

cfprApAaaUserEpFsmTaskCompletion OBJECT-TYPE
    SYNTAX       CfprApFsmCompletion
    MAX-ACCESS   read-only
    STATUS       current
    DESCRIPTION
        "Cisco Firepower aaa:UserEpFsmTask:completion managed
        object property"
    ::= { cfprApAaaUserEpFsmTaskEntry 4 }

cfprApAaaUserEpFsmTaskFlags OBJECT-TYPE
    SYNTAX       CfprApFsmFlags
    MAX-ACCESS   read-only
    STATUS       current
    DESCRIPTION
        "Cisco Firepower aaa:UserEpFsmTask:flags managed object property"
    ::= { cfprApAaaUserEpFsmTaskEntry 5 }

cfprApAaaUserEpFsmTaskItem OBJECT-TYPE
    SYNTAX       CfprApAaaUserEpFsmTaskItem
    MAX-ACCESS   read-only
    STATUS       current
    DESCRIPTION
        "Cisco Firepower aaa:UserEpFsmTask:item managed object property"
    ::= { cfprApAaaUserEpFsmTaskEntry 6 }

cfprApAaaUserEpFsmTaskSeqId OBJECT-TYPE
    SYNTAX       Gauge32
    MAX-ACCESS   read-only
    STATUS       current
    DESCRIPTION
        "Cisco Firepower aaa:UserEpFsmTask:seqId managed object property"
    ::= { cfprApAaaUserEpFsmTaskEntry 7 }

cfprApAaaUserLocaleTable OBJECT-TYPE
    SYNTAX           SEQUENCE OF CfprApAaaUserLocaleEntry
    MAX-ACCESS       not-accessible
    STATUS           current
    DESCRIPTION
        "Cisco Firepower aaa:UserLocale managed object table"
    ::= { cfprApAaaObjects 55 }

cfprApAaaUserLocaleEntry OBJECT-TYPE
    SYNTAX           CfprApAaaUserLocaleEntry
    MAX-ACCESS       not-accessible
    STATUS           current
    DESCRIPTION
        "Entry for the cfprApAaaUserLocaleTable table."
    INDEX { cfprApAaaUserLocaleInstanceId }
    ::= { cfprApAaaUserLocaleTable 1 }

CfprApAaaUserLocaleEntry ::= SEQUENCE {
    cfprApAaaUserLocaleInstanceId                                    CfprApManagedObjectId,
    cfprApAaaUserLocaleDn                                            CfprApManagedObjectDn,
    cfprApAaaUserLocaleRn                                            SnmpAdminString,
    cfprApAaaUserLocaleConfigState                                   CfprApAaaConfigState,
    cfprApAaaUserLocaleConfigStatusMessage                           SnmpAdminString,
    cfprApAaaUserLocaleDescr                                         SnmpAdminString,
    cfprApAaaUserLocaleName                                          SnmpAdminString
}

cfprApAaaUserLocaleInstanceId OBJECT-TYPE
    SYNTAX       CfprApManagedObjectId
    MAX-ACCESS   not-accessible
    STATUS       current
    DESCRIPTION
        "Instance identifier of the managed object."
    ::= { cfprApAaaUserLocaleEntry 1 }

cfprApAaaUserLocaleDn OBJECT-TYPE
    SYNTAX       CfprApManagedObjectDn
    MAX-ACCESS   read-only
    STATUS       current
    DESCRIPTION
        "Cisco Firepower aaa:UserLocale:dn managed object property"
    ::= { cfprApAaaUserLocaleEntry 2 }

cfprApAaaUserLocaleRn OBJECT-TYPE
    SYNTAX       SnmpAdminString
    MAX-ACCESS   read-only
    STATUS       current
    DESCRIPTION
        "Cisco Firepower aaa:UserLocale:rn managed object property"
    ::= { cfprApAaaUserLocaleEntry 3 }

cfprApAaaUserLocaleConfigState OBJECT-TYPE
    SYNTAX       CfprApAaaConfigState
    MAX-ACCESS   read-only
    STATUS       current
    DESCRIPTION
        "Cisco Firepower aaa:UserLocale:configState managed
        object property"
    ::= { cfprApAaaUserLocaleEntry 4 }

cfprApAaaUserLocaleConfigStatusMessage OBJECT-TYPE
    SYNTAX       SnmpAdminString
    MAX-ACCESS   read-only
    STATUS       current
    DESCRIPTION
        "Cisco Firepower aaa:UserLocale:configStatusMessage
        managed object property"
    ::= { cfprApAaaUserLocaleEntry 5 }

cfprApAaaUserLocaleDescr OBJECT-TYPE
    SYNTAX       SnmpAdminString
    MAX-ACCESS   read-only
    STATUS       current
    DESCRIPTION
        "Cisco Firepower aaa:UserLocale:descr managed object property"
    ::= { cfprApAaaUserLocaleEntry 6 }

cfprApAaaUserLocaleName OBJECT-TYPE
    SYNTAX       SnmpAdminString
    MAX-ACCESS   read-only
    STATUS       current
    DESCRIPTION
        "Cisco Firepower aaa:UserLocale:name managed object property"
    ::= { cfprApAaaUserLocaleEntry 7 }

cfprApAaaUserRoleTable OBJECT-TYPE
    SYNTAX           SEQUENCE OF CfprApAaaUserRoleEntry
    MAX-ACCESS       not-accessible
    STATUS           current
    DESCRIPTION
        "Cisco Firepower aaa:UserRole managed object table"
    ::= { cfprApAaaObjects 56 }

cfprApAaaUserRoleEntry OBJECT-TYPE
    SYNTAX           CfprApAaaUserRoleEntry
    MAX-ACCESS       not-accessible
    STATUS           current
    DESCRIPTION
        "Entry for the cfprApAaaUserRoleTable table."
    INDEX { cfprApAaaUserRoleInstanceId }
    ::= { cfprApAaaUserRoleTable 1 }

CfprApAaaUserRoleEntry ::= SEQUENCE {
    cfprApAaaUserRoleInstanceId                                      CfprApManagedObjectId,
    cfprApAaaUserRoleDn                                              CfprApManagedObjectDn,
    cfprApAaaUserRoleRn                                              SnmpAdminString,
    cfprApAaaUserRoleConfigState                                     CfprApAaaConfigState,
    cfprApAaaUserRoleConfigStatusMessage                             SnmpAdminString,
    cfprApAaaUserRoleDescr                                           SnmpAdminString,
    cfprApAaaUserRoleName                                            SnmpAdminString
}

cfprApAaaUserRoleInstanceId OBJECT-TYPE
    SYNTAX       CfprApManagedObjectId
    MAX-ACCESS   not-accessible
    STATUS       current
    DESCRIPTION
        "Instance identifier of the managed object."
    ::= { cfprApAaaUserRoleEntry 1 }

cfprApAaaUserRoleDn OBJECT-TYPE
    SYNTAX       CfprApManagedObjectDn
    MAX-ACCESS   read-only
    STATUS       current
    DESCRIPTION
        "Cisco Firepower aaa:UserRole:dn managed object property"
    ::= { cfprApAaaUserRoleEntry 2 }

cfprApAaaUserRoleRn OBJECT-TYPE
    SYNTAX       SnmpAdminString
    MAX-ACCESS   read-only
    STATUS       current
    DESCRIPTION
        "Cisco Firepower aaa:UserRole:rn managed object property"
    ::= { cfprApAaaUserRoleEntry 3 }

cfprApAaaUserRoleConfigState OBJECT-TYPE
    SYNTAX       CfprApAaaConfigState
    MAX-ACCESS   read-only
    STATUS       current
    DESCRIPTION
        "Cisco Firepower aaa:UserRole:configState managed object property"
    ::= { cfprApAaaUserRoleEntry 4 }

cfprApAaaUserRoleConfigStatusMessage OBJECT-TYPE
    SYNTAX       SnmpAdminString
    MAX-ACCESS   read-only
    STATUS       current
    DESCRIPTION
        "Cisco Firepower aaa:UserRole:configStatusMessage
        managed object property"
    ::= { cfprApAaaUserRoleEntry 5 }

cfprApAaaUserRoleDescr OBJECT-TYPE
    SYNTAX       SnmpAdminString
    MAX-ACCESS   read-only
    STATUS       current
    DESCRIPTION
        "Cisco Firepower aaa:UserRole:descr managed object property"
    ::= { cfprApAaaUserRoleEntry 6 }

cfprApAaaUserRoleName OBJECT-TYPE
    SYNTAX       SnmpAdminString
    MAX-ACCESS   read-only
    STATUS       current
    DESCRIPTION
        "Cisco Firepower aaa:UserRole:name managed object property"
    ::= { cfprApAaaUserRoleEntry 7 }

cfprApAaaWebLoginTable OBJECT-TYPE
    SYNTAX           SEQUENCE OF CfprApAaaWebLoginEntry
    MAX-ACCESS       not-accessible
    STATUS           current
    DESCRIPTION
        "Cisco Firepower aaa:WebLogin managed object table"
    ::= { cfprApAaaObjects 57 }

cfprApAaaWebLoginEntry OBJECT-TYPE
    SYNTAX           CfprApAaaWebLoginEntry
    MAX-ACCESS       not-accessible
    STATUS           current
    DESCRIPTION
        "Entry for the cfprApAaaWebLoginTable table."
    INDEX { cfprApAaaWebLoginInstanceId }
    ::= { cfprApAaaWebLoginTable 1 }

CfprApAaaWebLoginEntry ::= SEQUENCE {
    cfprApAaaWebLoginInstanceId                                      CfprApManagedObjectId,
    cfprApAaaWebLoginDn                                              CfprApManagedObjectDn,
    cfprApAaaWebLoginRn                                              SnmpAdminString,
    cfprApAaaWebLoginDescr                                           SnmpAdminString,
    cfprApAaaWebLoginId                                              SnmpAdminString,
    cfprApAaaWebLoginIntId                                           SnmpAdminString,
    cfprApAaaWebLoginLocalHost                                       SnmpAdminString,
    cfprApAaaWebLoginName                                            SnmpAdminString,
    cfprApAaaWebLoginPolicyLevel                                     Gauge32,
    cfprApAaaWebLoginPolicyOwner                                     CfprApPolicyPolicyOwner,
    cfprApAaaWebLoginRemoteHost                                      SnmpAdminString,
    cfprApAaaWebLoginSession                                         CfprApAaaSession,
    cfprApAaaWebLoginSwitchId                                        CfprApNetworkSwitchId
}

cfprApAaaWebLoginInstanceId OBJECT-TYPE
    SYNTAX       CfprApManagedObjectId
    MAX-ACCESS   not-accessible
    STATUS       current
    DESCRIPTION
        "Instance identifier of the managed object."
    ::= { cfprApAaaWebLoginEntry 1 }

cfprApAaaWebLoginDn OBJECT-TYPE
    SYNTAX       CfprApManagedObjectDn
    MAX-ACCESS   read-only
    STATUS       current
    DESCRIPTION
        "Cisco Firepower aaa:WebLogin:dn managed object property"
    ::= { cfprApAaaWebLoginEntry 2 }

cfprApAaaWebLoginRn OBJECT-TYPE
    SYNTAX       SnmpAdminString
    MAX-ACCESS   read-only
    STATUS       current
    DESCRIPTION
        "Cisco Firepower aaa:WebLogin:rn managed object property"
    ::= { cfprApAaaWebLoginEntry 3 }

cfprApAaaWebLoginDescr OBJECT-TYPE
    SYNTAX       SnmpAdminString
    MAX-ACCESS   read-only
    STATUS       current
    DESCRIPTION
        "Cisco Firepower aaa:WebLogin:descr managed object property"
    ::= { cfprApAaaWebLoginEntry 4 }

cfprApAaaWebLoginId OBJECT-TYPE
    SYNTAX       SnmpAdminString
    MAX-ACCESS   read-only
    STATUS       current
    DESCRIPTION
        "Cisco Firepower aaa:WebLogin:id managed object property"
    ::= { cfprApAaaWebLoginEntry 5 }

cfprApAaaWebLoginIntId OBJECT-TYPE
    SYNTAX       SnmpAdminString
    MAX-ACCESS   read-only
    STATUS       current
    DESCRIPTION
        "Cisco Firepower aaa:WebLogin:intId managed object property"
    ::= { cfprApAaaWebLoginEntry 6 }

cfprApAaaWebLoginLocalHost OBJECT-TYPE
    SYNTAX       SnmpAdminString
    MAX-ACCESS   read-only
    STATUS       current
    DESCRIPTION
        "Cisco Firepower aaa:WebLogin:localHost managed object property"
    ::= { cfprApAaaWebLoginEntry 7 }

cfprApAaaWebLoginName OBJECT-TYPE
    SYNTAX       SnmpAdminString
    MAX-ACCESS   read-only
    STATUS       current
    DESCRIPTION
        "Cisco Firepower aaa:WebLogin:name managed object property"
    ::= { cfprApAaaWebLoginEntry 8 }

cfprApAaaWebLoginPolicyLevel OBJECT-TYPE
    SYNTAX       Gauge32
    MAX-ACCESS   read-only
    STATUS       current
    DESCRIPTION
        "Cisco Firepower aaa:WebLogin:policyLevel managed object property"
    ::= { cfprApAaaWebLoginEntry 9 }

cfprApAaaWebLoginPolicyOwner OBJECT-TYPE
    SYNTAX       CfprApPolicyPolicyOwner
    MAX-ACCESS   read-only
    STATUS       current
    DESCRIPTION
        "Cisco Firepower aaa:WebLogin:policyOwner managed object property"
    ::= { cfprApAaaWebLoginEntry 10 }

cfprApAaaWebLoginRemoteHost OBJECT-TYPE
    SYNTAX       SnmpAdminString
    MAX-ACCESS   read-only
    STATUS       current
    DESCRIPTION
        "Cisco Firepower aaa:WebLogin:remoteHost managed object property"
    ::= { cfprApAaaWebLoginEntry 11 }

cfprApAaaWebLoginSession OBJECT-TYPE
    SYNTAX       CfprApAaaSession
    MAX-ACCESS   read-only
    STATUS       current
    DESCRIPTION
        "Cisco Firepower aaa:WebLogin:session managed object property"
    ::= { cfprApAaaWebLoginEntry 12 }

cfprApAaaWebLoginSwitchId OBJECT-TYPE
    SYNTAX       CfprApNetworkSwitchId
    MAX-ACCESS   read-only
    STATUS       current
    DESCRIPTION
        "Cisco Firepower aaa:WebLogin:switchId managed object property"
    ::= { cfprApAaaWebLoginEntry 13 }

END
