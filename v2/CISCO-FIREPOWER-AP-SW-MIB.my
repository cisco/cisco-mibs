-- *********************************************************************
-- CISCO-FIREPOWER-AP-SW-MIB.my
-- 
-- MIB representation of the Cisco Firepower
-- SW management information model package
-- 
-- Created January 2023 by Charles Bullis
-- 
-- Copyright (c) 2005-2023 Cisco Systems, Inc. All rights reserved.
-- 
-- *********************************************************************

CISCO-FIREPOWER-AP-SW-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApConditionRemoteInvRslt,
    CfprApDpsecForgedTransmit,
    CfprApFabricAVlanAssocPrimaryVlanSwitchId,
    CfprApFabricAVlanSharing,
    CfprApFabricAVlanTransport,
    CfprApFabricAVlanType,
    CfprApFabricAVsanTransport,
    CfprApFabricAVsanType,
    CfprApFabricAdminState,
    CfprApFabricDefaultZoningState,
    CfprApFabricEpVlanVlanType,
    CfprApFabricEthEstcPortMode,
    CfprApFabricEthPcProtocol,
    CfprApFabricExternalEpLocale,
    CfprApFabricFcZoneSharingMode,
    CfprApFabricFillPattern,
    CfprApFabricLacpMode,
    CfprApFabricPIoEpIfType,
    CfprApFabricPIoEpOperState,
    CfprApFabricPIoEpPortId,
    CfprApFabricPIoEpSlotId,
    CfprApFabricPktCaptureAppendFlag,
    CfprApFabricPort,
    CfprApFabricQosPrio,
    CfprApFabricRecoveryAction,
    CfprApFabricSpannedCluster,
    CfprApFabricTrafficDirection,
    CfprApFabricVlanAssocPrimaryVlanState,
    CfprApFabricVlanOperState,
    CfprApFabricVlanOverlapState,
    CfprApFabricVnetEpIfRole,
    CfprApFabricVnetEpLocale,
    CfprApFabricVnetEpPolicyOwner,
    CfprApFabricVsanOperState,
    CfprApFabricWarnings,
    CfprApFabricZoningState,
    CfprApFlowctrlFlowControl,
    CfprApFlowctrlPriorityPause,
    CfprApFsmCompletion,
    CfprApFsmFlags,
    CfprApFsmFsmStageStatus,
    CfprApFsmLifecycle,
    CfprApLicenseState,
    CfprApLsFcZoneState,
    CfprApNetworkConnectionType,
    CfprApNetworkLocale,
    CfprApNetworkPortRole,
    CfprApNetworkSwitchId,
    CfprApNetworkTransport,
    CfprApNetworkVlanCountStatus,
    CfprApNetworkVnetEpIfType,
    CfprApNwctrlAdminState,
    CfprApNwctrlLinkFailAction,
    CfprApPortDuplex,
    CfprApPortEthSpeed,
    CfprApPortSpeed,
    CfprApSwAccessDomainFsmCurrentFsm,
    CfprApSwAccessDomainFsmStageName,
    CfprApSwAccessDomainFsmTaskItem,
    CfprApSwAccessDomainLocale,
    CfprApSwAccessDomainType,
    CfprApSwAccessEpLocale,
    CfprApSwAccessEpTransport,
    CfprApSwAdminState,
    CfprApSwBorderDomainLocale,
    CfprApSwBorderEpLocale,
    CfprApSwBorderPcLocale,
    CfprApSwBreakoutType,
    CfprApSwCIoEpIfType,
    CfprApSwCardEnvStatsHistThresholded,
    CfprApSwCardEnvStatsThresholded,
    CfprApSwCimcId,
    CfprApSwConfMode,
    CfprApSwConfigStatus,
    CfprApSwEnvStatsHistThresholded,
    CfprApSwEnvStatsThresholded,
    CfprApSwEstcEpLocale,
    CfprApSwEthEstcEpTransport,
    CfprApSwEthEstcPcTransport,
    CfprApSwEthLanBorderFsmCurrentFsm,
    CfprApSwEthLanBorderFsmStageName,
    CfprApSwEthLanBorderFsmTaskFlags,
    CfprApSwEthLanBorderFsmTaskItem,
    CfprApSwEthLanBorderTransport,
    CfprApSwEthLanEpTransport,
    CfprApSwEthLanEpUdldAdminState,
    CfprApSwEthLanEpUdldMode,
    CfprApSwEthLanMonTransport,
    CfprApSwEthLanPcTransport,
    CfprApSwEthMonDestEpTransport,
    CfprApSwEthMonFsmCurrentFsm,
    CfprApSwEthMonFsmStageName,
    CfprApSwEthMonFsmTaskItem,
    CfprApSwEthMonSrcEpTransport,
    CfprApSwEthMonTransport,
    CfprApSwEthMonType,
    CfprApSwEthTargetEpAdminState,
    CfprApSwEthTargetEpTransport,
    CfprApSwExtUtilityFsmCurrentFsm,
    CfprApSwExtUtilityFsmStageName,
    CfprApSwExtUtilityFsmTaskItem,
    CfprApSwFabricRole,
    CfprApSwFabricZoneNsAllocStatus,
    CfprApSwFcSanBorderFsmCurrentFsm,
    CfprApSwFcSanBorderFsmStageName,
    CfprApSwFcSanBorderFsmTaskItem,
    CfprApSwFcSanBorderTransport,
    CfprApSwFcSanBorderUplinkTrunking,
    CfprApSwFcSanEpTransport,
    CfprApSwFcSanPcTransport,
    CfprApSwFcServerZoneGroupLc,
    CfprApSwFcZoneLc,
    CfprApSwFcZoneMemberLc,
    CfprApSwFcZoneSetLc,
    CfprApSwFcoeSanEpTransport,
    CfprApSwFcoeSanEpUdldAdminState,
    CfprApSwFcoeSanEpUdldMode,
    CfprApSwFcoeSanPcTransport,
    CfprApSwLanBorderType,
    CfprApSwLanEpIfRole,
    CfprApSwLanEpType,
    CfprApSwLanMonType,
    CfprApSwLanPcIfRole,
    CfprApSwLanPcType,
    CfprApSwMonAdminState,
    CfprApSwMonDomainLocale,
    CfprApSwMonLifeCycle,
    CfprApSwMonSrcEpLocale,
    CfprApSwPIoEpIfType,
    CfprApSwPIoEpLc,
    CfprApSwPeerStatus,
    CfprApSwPhysFsmCurrentFsm,
    CfprApSwPhysFsmStageName,
    CfprApSwPhysFsmTaskItem,
    CfprApSwPktCaptureLifeCycle,
    CfprApSwPortBreakoutPortId,
    CfprApSwPortBreakoutSlotId,
    CfprApSwSanBorderType,
    CfprApSwSanEpIfRole,
    CfprApSwSanEpType,
    CfprApSwSanPcIfRole,
    CfprApSwSanPcType,
    CfprApSwSspEthLanMonTransport,
    CfprApSwSspEthMonFsmCurrentFsm,
    CfprApSwSspEthMonFsmStageName,
    CfprApSwSspEthMonFsmTaskFlags,
    CfprApSwSspEthMonFsmTaskItem,
    CfprApSwSspEthMonSrcPhyEpFsmCurrentFsm,
    CfprApSwSspEthMonSrcPhyEpFsmStageName,
    CfprApSwSspEthMonSrcPhyEpFsmTaskItem,
    CfprApSwSspEthMonTransport,
    CfprApSwSspEthMonType,
    CfprApSwSspLanMonType,
    CfprApSwSspMonAdminState,
    CfprApSwSspMonDelPcap,
    CfprApSwSspMonDomainLocale,
    CfprApSwSubGroupAggrPortId,
    CfprApSwSubGroupSlotId,
    CfprApSwSystemStatsHistThresholded,
    CfprApSwSystemStatsThresholded,
    CfprApSwTargetEpType,
    CfprApSwUlanPurpose,
    CfprApSwUtilityDomainFsmCurrentFsm,
    CfprApSwUtilityDomainFsmStageName,
    CfprApSwUtilityDomainFsmTaskItem,
    CfprApSwUtilityDomainLocale,
    CfprApSwUtilityDomainType,
    CfprApSwVlanCompType,
    CfprApSwVlanConfigStatusType,
    CfprApSwVlanGroupType,
    CfprApSwVlanLc,
    CfprApSwVlanPortNsAllocStatus
        FROM CISCO-FIREPOWER-AP-TC-MIB;

cfprApSwObjects MODULE-IDENTITY
    LAST-UPDATED    "202301250000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        SW management information model package"
    ::= { ciscoFirepowerApMIBObjects 75 }

cfprApSwAccessDomainTable OBJECT-TYPE
    SYNTAX           SEQUENCE OF CfprApSwAccessDomainEntry
    MAX-ACCESS       not-accessible
    STATUS           current
    DESCRIPTION
        "Cisco Firepower sw:AccessDomain managed object table"
    ::= { cfprApSwObjects 1 }

cfprApSwAccessDomainEntry OBJECT-TYPE
    SYNTAX           CfprApSwAccessDomainEntry
    MAX-ACCESS       not-accessible
    STATUS           current
    DESCRIPTION
        "Entry for the cfprApSwAccessDomainTable table."
    INDEX { cfprApSwAccessDomainInstanceId }
    ::= { cfprApSwAccessDomainTable 1 }

CfprApSwAccessDomainEntry ::= SEQUENCE {
    cfprApSwAccessDomainInstanceId                                   CfprApManagedObjectId,
    cfprApSwAccessDomainDn                                           CfprApManagedObjectDn,
    cfprApSwAccessDomainRn                                           SnmpAdminString,
    cfprApSwAccessDomainFsmDescr                                     SnmpAdminString,
    cfprApSwAccessDomainFsmPrev                                      SnmpAdminString,
    cfprApSwAccessDomainFsmProgr                                     Gauge32,
    cfprApSwAccessDomainFsmRmtInvErrCode                             Gauge32,
    cfprApSwAccessDomainFsmRmtInvErrDescr                            SnmpAdminString,
    cfprApSwAccessDomainFsmRmtInvRslt                                CfprApConditionRemoteInvRslt,
    cfprApSwAccessDomainFsmStageDescr                                SnmpAdminString,
    cfprApSwAccessDomainFsmStamp                                     DateAndTime,
    cfprApSwAccessDomainFsmStatus                                    SnmpAdminString,
    cfprApSwAccessDomainFsmTry                                       Gauge32,
    cfprApSwAccessDomainLocale                                       CfprApSwAccessDomainLocale,
    cfprApSwAccessDomainName                                         SnmpAdminString,
    cfprApSwAccessDomainSwitchId                                     CfprApNetworkSwitchId,
    cfprApSwAccessDomainTransport                                    CfprApNetworkTransport,
    cfprApSwAccessDomainType                                         CfprApSwAccessDomainType
}

cfprApSwAccessDomainInstanceId OBJECT-TYPE
    SYNTAX       CfprApManagedObjectId
    MAX-ACCESS   not-accessible
    STATUS       current
    DESCRIPTION
        "Instance identifier of the managed object."
    ::= { cfprApSwAccessDomainEntry 1 }

cfprApSwAccessDomainDn OBJECT-TYPE
    SYNTAX       CfprApManagedObjectDn
    MAX-ACCESS   read-only
    STATUS       current
    DESCRIPTION
        "Cisco Firepower sw:AccessDomain:dn managed object property"
    ::= { cfprApSwAccessDomainEntry 2 }

cfprApSwAccessDomainRn OBJECT-TYPE
    SYNTAX       SnmpAdminString
    MAX-ACCESS   read-only
    STATUS       current
    DESCRIPTION
        "Cisco Firepower sw:AccessDomain:rn managed object property"
    ::= { cfprApSwAccessDomainEntry 3 }

cfprApSwAccessDomainFsmDescr OBJECT-TYPE
    SYNTAX       SnmpAdminString
    MAX-ACCESS   read-only
    STATUS       current
    DESCRIPTION
        "Cisco Firepower sw:AccessDomain:fsmDescr managed object property"
    ::= { cfprApSwAccessDomainEntry 4 }

cfprApSwAccessDomainFsmPrev OBJECT-TYPE
    SYNTAX       SnmpAdminString
    MAX-ACCESS   read-only
    STATUS       current
    DESCRIPTION
        "Cisco Firepower sw:AccessDomain:fsmPrev managed object property"
    ::= { cfprApSwAccessDomainEntry 5 }

cfprApSwAccessDomainFsmProgr OBJECT-TYPE
    SYNTAX       Gauge32
    MAX-ACCESS   read-only
    STATUS       current
    DESCRIPTION
        "Cisco Firepower sw:AccessDomain:fsmProgr managed object property"
    ::= { cfprApSwAccessDomainEntry 6 }

cfprApSwAccessDomainFsmRmtInvErrCode OBJECT-TYPE
    SYNTAX       Gauge32
    MAX-ACCESS   read-only
    STATUS       current
    DESCRIPTION
        "Cisco Firepower sw:AccessDomain:fsmRmtInvErrCode
        managed object property"
    ::= { cfprApSwAccessDomainEntry 7 }

cfprApSwAccessDomainFsmRmtInvErrDescr OBJECT-TYPE
    SYNTAX       SnmpAdminString
    MAX-ACCESS   read-only
    STATUS       current
    DESCRIPTION
        "Cisco Firepower sw:AccessDomain:fsmRmtInvErrDescr
        managed object property"
    ::= { cfprApSwAccessDomainEntry 8 }

cfprApSwAccessDomainFsmRmtInvRslt OBJECT-TYPE
    SYNTAX       CfprApConditionRemoteInvRslt
    MAX-ACCESS   read-only
    STATUS       current
    DESCRIPTION
        "Cisco Firepower sw:AccessDomain:fsmRmtInvRslt
        managed object property"
    ::= { cfprApSwAccessDomainEntry 9 }

cfprApSwAccessDomainFsmStageDescr OBJECT-TYPE
    SYNTAX       SnmpAdminString
    MAX-ACCESS   read-only
    STATUS       current
    DESCRIPTION
        "Cisco Firepower sw:AccessDomain:fsmStageDescr
        managed object property"
    ::= { cfprApSwAccessDomainEntry 10 }

cfprApSwAccessDomainFsmStamp OBJECT-TYPE
    SYNTAX       DateAndTime
    MAX-ACCESS   read-only
    STATUS       current
    DESCRIPTION
        "Cisco Firepower sw:AccessDomain:fsmStamp managed object property"
    ::= { cfprApSwAccessDomainEntry 11 }

cfprApSwAccessDomainFsmStatus OBJECT-TYPE
    SYNTAX       SnmpAdminString
    MAX-ACCESS   read-only
    STATUS       current
    DESCRIPTION
        "Cisco Firepower sw:AccessDomain:fsmStatus managed
        object property"
    ::= { cfprApSwAccessDomainEntry 12 }

cfprApSwAccessDomainFsmTry OBJECT-TYPE
    SYNTAX       Gauge32
    MAX-ACCESS   read-only
    STATUS       current
    DESCRIPTION
        "Cisco Firepower sw:AccessDomain:fsmTry managed object property"
    ::= { cfprApSwAccessDomainEntry 13 }

cfprApSwAccessDomainLocale OBJECT-TYPE
    SYNTAX       CfprApSwAccessDomainLocale
    MAX-ACCESS   read-only
    STATUS       current
    DESCRIPTION
        "Cisco Firepower sw:AccessDomain:locale managed object property"
    ::= { cfprApSwAccessDomainEntry 14 }

cfprApSwAccessDomainName OBJECT-TYPE
    SYNTAX       SnmpAdminString
    MAX-ACCESS   read-only
    STATUS       current
    DESCRIPTION
        "Cisco Firepower sw:AccessDomain:name managed object property"
    ::= { cfprApSwAccessDomainEntry 15 }

cfprApSwAccessDomainSwitchId OBJECT-TYPE
    SYNTAX       CfprApNetworkSwitchId
    MAX-ACCESS   read-only
    STATUS       current
    DESCRIPTION
        "Cisco Firepower sw:AccessDomain:switchId managed object property"
    ::= { cfprApSwAccessDomainEntry 16 }

cfprApSwAccessDomainTransport OBJECT-TYPE
    SYNTAX       CfprApNetworkTransport
    MAX-ACCESS   read-only
    STATUS       current
    DESCRIPTION
        "Cisco Firepower sw:AccessDomain:transport managed
        object property"
    ::= { cfprApSwAccessDomainEntry 17 }

cfprApSwAccessDomainType OBJECT-TYPE
    SYNTAX       CfprApSwAccessDomainType
    MAX-ACCESS   read-only
    STATUS       current
    DESCRIPTION
        "Cisco Firepower sw:AccessDomain:type managed object property"
    ::= { cfprApSwAccessDomainEntry 18 }

cfprApSwAccessDomainFsmTable OBJECT-TYPE
    SYNTAX           SEQUENCE OF CfprApSwAccessDomainFsmEntry
    MAX-ACCESS       not-accessible
    STATUS           current
    DESCRIPTION
        "Cisco Firepower sw:AccessDomainFsm managed object table"
    ::= { cfprApSwObjects 2 }

cfprApSwAccessDomainFsmEntry OBJECT-TYPE
    SYNTAX           CfprApSwAccessDomainFsmEntry
    MAX-ACCESS       not-accessible
    STATUS           current
    DESCRIPTION
        "Entry for the cfprApSwAccessDomainFsmTable table."
    INDEX { cfprApSwAccessDomainFsmInstanceId }
    ::= { cfprApSwAccessDomainFsmTable 1 }

CfprApSwAccessDomainFsmEntry ::= SEQUENCE {
    cfprApSwAccessDomainFsmInstanceId                                CfprApManagedObjectId,
    cfprApSwAccessDomainFsmDn                                        CfprApManagedObjectDn,
    cfprApSwAccessDomainFsmRn                                        SnmpAdminString,
    cfprApSwAccessDomainFsmCompletionTime                            DateAndTime,
    cfprApSwAccessDomainFsmCurrentFsm                                CfprApSwAccessDomainFsmCurrentFsm,
    cfprApSwAccessDomainFsmDescrData                                 SnmpAdminString,
    cfprApSwAccessDomainFsmFsmStatus                                 CfprApFsmFsmStageStatus,
    cfprApSwAccessDomainFsmProgress                                  Gauge32,
    cfprApSwAccessDomainFsmRmtErrCode                                Gauge32,
    cfprApSwAccessDomainFsmRmtErrDescr                               SnmpAdminString,
    cfprApSwAccessDomainFsmRmtRslt                                   CfprApConditionRemoteInvRslt
}

cfprApSwAccessDomainFsmInstanceId OBJECT-TYPE
    SYNTAX       CfprApManagedObjectId
    MAX-ACCESS   not-accessible
    STATUS       current
    DESCRIPTION
        "Instance identifier of the managed object."
    ::= { cfprApSwAccessDomainFsmEntry 1 }

cfprApSwAccessDomainFsmDn OBJECT-TYPE
    SYNTAX       CfprApManagedObjectDn
    MAX-ACCESS   read-only
    STATUS       current
    DESCRIPTION
        "Cisco Firepower sw:AccessDomainFsm:dn managed object property"
    ::= { cfprApSwAccessDomainFsmEntry 2 }

cfprApSwAccessDomainFsmRn OBJECT-TYPE
    SYNTAX       SnmpAdminString
    MAX-ACCESS   read-only
    STATUS       current
    DESCRIPTION
        "Cisco Firepower sw:AccessDomainFsm:rn managed object property"
    ::= { cfprApSwAccessDomainFsmEntry 3 }

cfprApSwAccessDomainFsmCompletionTime OBJECT-TYPE
    SYNTAX       DateAndTime
    MAX-ACCESS   read-only
    STATUS       current
    DESCRIPTION
        "Cisco Firepower sw:AccessDomainFsm:completionTime
        managed object property"
    ::= { cfprApSwAccessDomainFsmEntry 4 }

cfprApSwAccessDomainFsmCurrentFsm OBJECT-TYPE
    SYNTAX       CfprApSwAccessDomainFsmCurrentFsm
    MAX-ACCESS   read-only
    STATUS       current
    DESCRIPTION
        "Cisco Firepower sw:AccessDomainFsm:currentFsm
        managed object property"
    ::= { cfprApSwAccessDomainFsmEntry 5 }

cfprApSwAccessDomainFsmDescrData OBJECT-TYPE
    SYNTAX       SnmpAdminString
    MAX-ACCESS   read-only
    STATUS       current
    DESCRIPTION
        "Cisco Firepower sw:AccessDomainFsm:descr managed object property"
    ::= { cfprApSwAccessDomainFsmEntry 6 }

cfprApSwAccessDomainFsmFsmStatus OBJECT-TYPE
    SYNTAX       CfprApFsmFsmStageStatus
    MAX-ACCESS   read-only
    STATUS       current
    DESCRIPTION
        "Cisco Firepower sw:AccessDomainFsm:fsmStatus managed
        object property"
    ::= { cfprApSwAccessDomainFsmEntry 7 }

cfprApSwAccessDomainFsmProgress OBJECT-TYPE
    SYNTAX       Gauge32
    MAX-ACCESS   read-only
    STATUS       current
    DESCRIPTION
        "Cisco Firepower sw:AccessDomainFsm:progress managed
        object property"
    ::= { cfprApSwAccessDomainFsmEntry 8 }

cfprApSwAccessDomainFsmRmtErrCode OBJECT-TYPE
    SYNTAX       Gauge32
    MAX-ACCESS   read-only
    STATUS       current
    DESCRIPTION
        "Cisco Firepower sw:AccessDomainFsm:rmtErrCode
        managed object property"
    ::= { cfprApSwAccessDomainFsmEntry 9 }

cfprApSwAccessDomainFsmRmtErrDescr OBJECT-TYPE
    SYNTAX       SnmpAdminString
    MAX-ACCESS   read-only
    STATUS       current
    DESCRIPTION
        "Cisco Firepower sw:AccessDomainFsm:rmtErrDescr
        managed object property"
    ::= { cfprApSwAccessDomainFsmEntry 10 }

cfprApSwAccessDomainFsmRmtRslt OBJECT-TYPE
    SYNTAX       CfprApConditionRemoteInvRslt
    MAX-ACCESS   read-only
    STATUS       current
    DESCRIPTION
        "Cisco Firepower sw:AccessDomainFsm:rmtRslt managed
        object property"
    ::= { cfprApSwAccessDomainFsmEntry 11 }

cfprApSwAccessDomainFsmStageTable OBJECT-TYPE
    SYNTAX           SEQUENCE OF CfprApSwAccessDomainFsmStageEntry
    MAX-ACCESS       not-accessible
    STATUS           current
    DESCRIPTION
        "Cisco Firepower sw:AccessDomainFsmStage managed object table"
    ::= { cfprApSwObjects 3 }

cfprApSwAccessDomainFsmStageEntry OBJECT-TYPE
    SYNTAX           CfprApSwAccessDomainFsmStageEntry
    MAX-ACCESS       not-accessible
    STATUS           current
    DESCRIPTION
        "Entry for the cfprApSwAccessDomainFsmStageTable table."
    INDEX { cfprApSwAccessDomainFsmStageInstanceId }
    ::= { cfprApSwAccessDomainFsmStageTable 1 }

CfprApSwAccessDomainFsmStageEntry ::= SEQUENCE {
    cfprApSwAccessDomainFsmStageInstanceId                           CfprApManagedObjectId,
    cfprApSwAccessDomainFsmStageDn                                   CfprApManagedObjectDn,
    cfprApSwAccessDomainFsmStageRn                                   SnmpAdminString,
    cfprApSwAccessDomainFsmStageDescrData                            SnmpAdminString,
    cfprApSwAccessDomainFsmStageLastUpdateTime                       DateAndTime,
    cfprApSwAccessDomainFsmStageName                                 CfprApSwAccessDomainFsmStageName,
    cfprApSwAccessDomainFsmStageOrder                                Gauge32,
    cfprApSwAccessDomainFsmStageRetry                                Gauge32,
    cfprApSwAccessDomainFsmStageStageStatus                          CfprApFsmFsmStageStatus
}

cfprApSwAccessDomainFsmStageInstanceId OBJECT-TYPE
    SYNTAX       CfprApManagedObjectId
    MAX-ACCESS   not-accessible
    STATUS       current
    DESCRIPTION
        "Instance identifier of the managed object."
    ::= { cfprApSwAccessDomainFsmStageEntry 1 }

cfprApSwAccessDomainFsmStageDn OBJECT-TYPE
    SYNTAX       CfprApManagedObjectDn
    MAX-ACCESS   read-only
    STATUS       current
    DESCRIPTION
        "Cisco Firepower sw:AccessDomainFsmStage:dn managed
        object property"
    ::= { cfprApSwAccessDomainFsmStageEntry 2 }

cfprApSwAccessDomainFsmStageRn OBJECT-TYPE
    SYNTAX       SnmpAdminString
    MAX-ACCESS   read-only
    STATUS       current
    DESCRIPTION
        "Cisco Firepower sw:AccessDomainFsmStage:rn managed
        object property"
    ::= { cfprApSwAccessDomainFsmStageEntry 3 }

cfprApSwAccessDomainFsmStageDescrData OBJECT-TYPE
    SYNTAX       SnmpAdminString
    MAX-ACCESS   read-only
    STATUS       current
    DESCRIPTION
        "Cisco Firepower sw:AccessDomainFsmStage:descr
        managed object property"
    ::= { cfprApSwAccessDomainFsmStageEntry 4 }

cfprApSwAccessDomainFsmStageLastUpdateTime OBJECT-TYPE
    SYNTAX       DateAndTime
    MAX-ACCESS   read-only
    STATUS       current
    DESCRIPTION
        "Cisco Firepower sw:AccessDomainFsmStage:lastUpdateTime
        managed object property"
    ::= { cfprApSwAccessDomainFsmStageEntry 5 }

cfprApSwAccessDomainFsmStageName OBJECT-TYPE
    SYNTAX       CfprApSwAccessDomainFsmStageName
    MAX-ACCESS   read-only
    STATUS       current
    DESCRIPTION
        "Cisco Firepower sw:AccessDomainFsmStage:name managed
        object property"
    ::= { cfprApSwAccessDomainFsmStageEntry 6 }

cfprApSwAccessDomainFsmStageOrder OBJECT-TYPE
    SYNTAX       Gauge32
    MAX-ACCESS   read-only
    STATUS       current
    DESCRIPTION
        "Cisco Firepower sw:AccessDomainFsmStage:order
        managed object property"
    ::= { cfprApSwAccessDomainFsmStageEntry 7 }

cfprApSwAccessDomainFsmStageRetry OBJECT-TYPE
    SYNTAX       Gauge32
    MAX-ACCESS   read-only
    STATUS       current
    DESCRIPTION
        "Cisco Firepower sw:AccessDomainFsmStage:retry
        managed object property"
    ::= { cfprApSwAccessDomainFsmStageEntry 8 }

cfprApSwAccessDomainFsmStageStageStatus OBJECT-TYPE
    SYNTAX       CfprApFsmFsmStageStatus
    MAX-ACCESS   read-only
    STATUS       current
    DESCRIPTION
        "Cisco Firepower sw:AccessDomainFsmStage:stageStatus
        managed object property"
    ::= { cfprApSwAccessDomainFsmStageEntry 9 }

cfprApSwAccessDomainFsmTaskTable OBJECT-TYPE
    SYNTAX           SEQUENCE OF CfprApSwAccessDomainFsmTaskEntry
    MAX-ACCESS       not-accessible
    STATUS           current
    DESCRIPTION
        "Cisco Firepower sw:AccessDomainFsmTask managed object table"
    ::= { cfprApSwObjects 4 }

cfprApSwAccessDomainFsmTaskEntry OBJECT-TYPE
    SYNTAX           CfprApSwAccessDomainFsmTaskEntry
    MAX-ACCESS       not-accessible
    STATUS           current
    DESCRIPTION
        "Entry for the cfprApSwAccessDomainFsmTaskTable table."
    INDEX { cfprApSwAccessDomainFsmTaskInstanceId }
    ::= { cfprApSwAccessDomainFsmTaskTable 1 }

CfprApSwAccessDomainFsmTaskEntry ::= SEQUENCE {
    cfprApSwAccessDomainFsmTaskInstanceId                            CfprApManagedObjectId,
    cfprApSwAccessDomainFsmTaskDn                                    CfprApManagedObjectDn,
    cfprApSwAccessDomainFsmTaskRn                                    SnmpAdminString,
    cfprApSwAccessDomainFsmTaskCompletion                            CfprApFsmCompletion,
    cfprApSwAccessDomainFsmTaskFlags                                 CfprApFsmFlags,
    cfprApSwAccessDomainFsmTaskItem                                  CfprApSwAccessDomainFsmTaskItem,
    cfprApSwAccessDomainFsmTaskSeqId                                 Gauge32
}

cfprApSwAccessDomainFsmTaskInstanceId OBJECT-TYPE
    SYNTAX       CfprApManagedObjectId
    MAX-ACCESS   not-accessible
    STATUS       current
    DESCRIPTION
        "Instance identifier of the managed object."
    ::= { cfprApSwAccessDomainFsmTaskEntry 1 }

cfprApSwAccessDomainFsmTaskDn OBJECT-TYPE
    SYNTAX       CfprApManagedObjectDn
    MAX-ACCESS   read-only
    STATUS       current
    DESCRIPTION
        "Cisco Firepower sw:AccessDomainFsmTask:dn managed
        object property"
    ::= { cfprApSwAccessDomainFsmTaskEntry 2 }

cfprApSwAccessDomainFsmTaskRn OBJECT-TYPE
    SYNTAX       SnmpAdminString
    MAX-ACCESS   read-only
    STATUS       current
    DESCRIPTION
        "Cisco Firepower sw:AccessDomainFsmTask:rn managed
        object property"
    ::= { cfprApSwAccessDomainFsmTaskEntry 3 }

cfprApSwAccessDomainFsmTaskCompletion OBJECT-TYPE
    SYNTAX       CfprApFsmCompletion
    MAX-ACCESS   read-only
    STATUS       current
    DESCRIPTION
        "Cisco Firepower sw:AccessDomainFsmTask:completion
        managed object property"
    ::= { cfprApSwAccessDomainFsmTaskEntry 4 }

cfprApSwAccessDomainFsmTaskFlags OBJECT-TYPE
    SYNTAX       CfprApFsmFlags
    MAX-ACCESS   read-only
    STATUS       current
    DESCRIPTION
        "Cisco Firepower sw:AccessDomainFsmTask:flags managed
        object property"
    ::= { cfprApSwAccessDomainFsmTaskEntry 5 }

cfprApSwAccessDomainFsmTaskItem OBJECT-TYPE
    SYNTAX       CfprApSwAccessDomainFsmTaskItem
    MAX-ACCESS   read-only
    STATUS       current
    DESCRIPTION
        "Cisco Firepower sw:AccessDomainFsmTask:item managed
        object property"
    ::= { cfprApSwAccessDomainFsmTaskEntry 6 }

cfprApSwAccessDomainFsmTaskSeqId OBJECT-TYPE
    SYNTAX       Gauge32
    MAX-ACCESS   read-only
    STATUS       current
    DESCRIPTION
        "Cisco Firepower sw:AccessDomainFsmTask:seqId managed
        object property"
    ::= { cfprApSwAccessDomainFsmTaskEntry 7 }

cfprApSwAccessEpTable OBJECT-TYPE
    SYNTAX           SEQUENCE OF CfprApSwAccessEpEntry
    MAX-ACCESS       not-accessible
    STATUS           current
    DESCRIPTION
        "Cisco Firepower sw:AccessEp managed object table"
    ::= { cfprApSwObjects 5 }

cfprApSwAccessEpEntry OBJECT-TYPE
    SYNTAX           CfprApSwAccessEpEntry
    MAX-ACCESS       not-accessible
    STATUS           current
    DESCRIPTION
        "Entry for the cfprApSwAccessEpTable table."
    INDEX { cfprApSwAccessEpInstanceId }
    ::= { cfprApSwAccessEpTable 1 }

CfprApSwAccessEpEntry ::= SEQUENCE {
    cfprApSwAccessEpInstanceId                                       CfprApManagedObjectId,
    cfprApSwAccessEpDn                                               CfprApManagedObjectDn,
    cfprApSwAccessEpRn                                               SnmpAdminString,
    cfprApSwAccessEpAdminState                                       CfprApFabricAdminState,
    cfprApSwAccessEpAggrPortId                                       Gauge32,
    cfprApSwAccessEpChassisId                                        Gauge32,
    cfprApSwAccessEpEncap                                            Gauge32,
    cfprApSwAccessEpEpDn                                             SnmpAdminString,
    cfprApSwAccessEpIfRole                                           CfprApNetworkPortRole,
    cfprApSwAccessEpIfType                                           CfprApSwPIoEpIfType,
    cfprApSwAccessEpLc                                               CfprApSwPIoEpLc,
    cfprApSwAccessEpLocale                                           CfprApSwAccessEpLocale,
    cfprApSwAccessEpName                                             SnmpAdminString,
    cfprApSwAccessEpNsSize                                           Gauge32,
    cfprApSwAccessEpPeerAggrPortId                                   Gauge32,
    cfprApSwAccessEpPeerChassisId                                    Gauge32,
    cfprApSwAccessEpPeerDn                                           SnmpAdminString,
    cfprApSwAccessEpPeerPortId                                       Gauge32,
    cfprApSwAccessEpPeerSlotId                                       Gauge32,
    cfprApSwAccessEpPortId                                           Gauge32,
    cfprApSwAccessEpSlotId                                           Gauge32,
    cfprApSwAccessEpSwitchId                                         CfprApNetworkSwitchId,
    cfprApSwAccessEpTransport                                        CfprApSwAccessEpTransport,
    cfprApSwAccessEpType                                             CfprApNetworkConnectionType
}

cfprApSwAccessEpInstanceId OBJECT-TYPE
    SYNTAX       CfprApManagedObjectId
    MAX-ACCESS   not-accessible
    STATUS       current
    DESCRIPTION
        "Instance identifier of the managed object."
    ::= { cfprApSwAccessEpEntry 1 }

cfprApSwAccessEpDn OBJECT-TYPE
    SYNTAX       CfprApManagedObjectDn
    MAX-ACCESS   read-only
    STATUS       current
    DESCRIPTION
        "Cisco Firepower sw:AccessEp:dn managed object property"
    ::= { cfprApSwAccessEpEntry 2 }

cfprApSwAccessEpRn OBJECT-TYPE
    SYNTAX       SnmpAdminString
    MAX-ACCESS   read-only
    STATUS       current
    DESCRIPTION
        "Cisco Firepower sw:AccessEp:rn managed object property"
    ::= { cfprApSwAccessEpEntry 3 }

cfprApSwAccessEpAdminState OBJECT-TYPE
    SYNTAX       CfprApFabricAdminState
    MAX-ACCESS   read-only
    STATUS       current
    DESCRIPTION
        "Cisco Firepower sw:AccessEp:adminState managed object property"
    ::= { cfprApSwAccessEpEntry 4 }

cfprApSwAccessEpAggrPortId OBJECT-TYPE
    SYNTAX       Gauge32
    MAX-ACCESS   read-only
    STATUS       current
    DESCRIPTION
        "Cisco Firepower sw:AccessEp:aggrPortId managed object property"
    ::= { cfprApSwAccessEpEntry 5 }

cfprApSwAccessEpChassisId OBJECT-TYPE
    SYNTAX       Gauge32
    MAX-ACCESS   read-only
    STATUS       current
    DESCRIPTION
        "Cisco Firepower sw:AccessEp:chassisId managed object property"
    ::= { cfprApSwAccessEpEntry 6 }

cfprApSwAccessEpEncap OBJECT-TYPE
    SYNTAX       Gauge32
    MAX-ACCESS   read-only
    STATUS       current
    DESCRIPTION
        "Cisco Firepower sw:AccessEp:encap managed object property"
    ::= { cfprApSwAccessEpEntry 7 }

cfprApSwAccessEpEpDn OBJECT-TYPE
    SYNTAX       SnmpAdminString
    MAX-ACCESS   read-only
    STATUS       current
    DESCRIPTION
        "Cisco Firepower sw:AccessEp:epDn managed object property"
    ::= { cfprApSwAccessEpEntry 8 }

cfprApSwAccessEpIfRole OBJECT-TYPE
    SYNTAX       CfprApNetworkPortRole
    MAX-ACCESS   read-only
    STATUS       current
    DESCRIPTION
        "Cisco Firepower sw:AccessEp:ifRole managed object property"
    ::= { cfprApSwAccessEpEntry 9 }

cfprApSwAccessEpIfType OBJECT-TYPE
    SYNTAX       CfprApSwPIoEpIfType
    MAX-ACCESS   read-only
    STATUS       current
    DESCRIPTION
        "Cisco Firepower sw:AccessEp:ifType managed object property"
    ::= { cfprApSwAccessEpEntry 10 }

cfprApSwAccessEpLc OBJECT-TYPE
    SYNTAX       CfprApSwPIoEpLc
    MAX-ACCESS   read-only
    STATUS       current
    DESCRIPTION
        "Cisco Firepower sw:AccessEp:lc managed object property"
    ::= { cfprApSwAccessEpEntry 11 }

cfprApSwAccessEpLocale OBJECT-TYPE
    SYNTAX       CfprApSwAccessEpLocale
    MAX-ACCESS   read-only
    STATUS       current
    DESCRIPTION
        "Cisco Firepower sw:AccessEp:locale managed object property"
    ::= { cfprApSwAccessEpEntry 12 }

cfprApSwAccessEpName OBJECT-TYPE
    SYNTAX       SnmpAdminString
    MAX-ACCESS   read-only
    STATUS       current
    DESCRIPTION
        "Cisco Firepower sw:AccessEp:name managed object property"
    ::= { cfprApSwAccessEpEntry 13 }

cfprApSwAccessEpNsSize OBJECT-TYPE
    SYNTAX       Gauge32
    MAX-ACCESS   read-only
    STATUS       current
    DESCRIPTION
        "Cisco Firepower sw:AccessEp:nsSize managed object property"
    ::= { cfprApSwAccessEpEntry 14 }

cfprApSwAccessEpPeerAggrPortId OBJECT-TYPE
    SYNTAX       Gauge32
    MAX-ACCESS   read-only
    STATUS       current
    DESCRIPTION
        "Cisco Firepower sw:AccessEp:peerAggrPortId managed
        object property"
    ::= { cfprApSwAccessEpEntry 15 }

cfprApSwAccessEpPeerChassisId OBJECT-TYPE
    SYNTAX       Gauge32
    MAX-ACCESS   read-only
    STATUS       current
    DESCRIPTION
        "Cisco Firepower sw:AccessEp:peerChassisId managed
        object property"
    ::= { cfprApSwAccessEpEntry 16 }

cfprApSwAccessEpPeerDn OBJECT-TYPE
    SYNTAX       SnmpAdminString
    MAX-ACCESS   read-only
    STATUS       current
    DESCRIPTION
        "Cisco Firepower sw:AccessEp:peerDn managed object property"
    ::= { cfprApSwAccessEpEntry 17 }

cfprApSwAccessEpPeerPortId OBJECT-TYPE
    SYNTAX       Gauge32
    MAX-ACCESS   read-only
    STATUS       current
    DESCRIPTION
        "Cisco Firepower sw:AccessEp:peerPortId managed object property"
    ::= { cfprApSwAccessEpEntry 18 }

cfprApSwAccessEpPeerSlotId OBJECT-TYPE
    SYNTAX       Gauge32
    MAX-ACCESS   read-only
    STATUS       current
    DESCRIPTION
        "Cisco Firepower sw:AccessEp:peerSlotId managed object property"
    ::= { cfprApSwAccessEpEntry 19 }

cfprApSwAccessEpPortId OBJECT-TYPE
    SYNTAX       Gauge32
    MAX-ACCESS   read-only
    STATUS       current
    DESCRIPTION
        "Cisco Firepower sw:AccessEp:portId managed object property"
    ::= { cfprApSwAccessEpEntry 20 }

cfprApSwAccessEpSlotId OBJECT-TYPE
    SYNTAX       Gauge32
    MAX-ACCESS   read-only
    STATUS       current
    DESCRIPTION
        "Cisco Firepower sw:AccessEp:slotId managed object property"
    ::= { cfprApSwAccessEpEntry 21 }

cfprApSwAccessEpSwitchId OBJECT-TYPE
    SYNTAX       CfprApNetworkSwitchId
    MAX-ACCESS   read-only
    STATUS       current
    DESCRIPTION
        "Cisco Firepower sw:AccessEp:switchId managed object property"
    ::= { cfprApSwAccessEpEntry 22 }

cfprApSwAccessEpTransport OBJECT-TYPE
    SYNTAX       CfprApSwAccessEpTransport
    MAX-ACCESS   read-only
    STATUS       current
    DESCRIPTION
        "Cisco Firepower sw:AccessEp:transport managed object property"
    ::= { cfprApSwAccessEpEntry 23 }

cfprApSwAccessEpType OBJECT-TYPE
    SYNTAX       CfprApNetworkConnectionType
    MAX-ACCESS   read-only
    STATUS       current
    DESCRIPTION
        "Cisco Firepower sw:AccessEp:type managed object property"
    ::= { cfprApSwAccessEpEntry 24 }

cfprApSwCardEnvStatsTable OBJECT-TYPE
    SYNTAX           SEQUENCE OF CfprApSwCardEnvStatsEntry
    MAX-ACCESS       not-accessible
    STATUS           current
    DESCRIPTION
        "Cisco Firepower sw:CardEnvStats managed object table"
    ::= { cfprApSwObjects 6 }

cfprApSwCardEnvStatsEntry OBJECT-TYPE
    SYNTAX           CfprApSwCardEnvStatsEntry
    MAX-ACCESS       not-accessible
    STATUS           current
    DESCRIPTION
        "Entry for the cfprApSwCardEnvStatsTable table."
    INDEX { cfprApSwCardEnvStatsInstanceId }
    ::= { cfprApSwCardEnvStatsTable 1 }

CfprApSwCardEnvStatsEntry ::= SEQUENCE {
    cfprApSwCardEnvStatsInstanceId                                   CfprApManagedObjectId,
    cfprApSwCardEnvStatsDn                                           CfprApManagedObjectDn,
    cfprApSwCardEnvStatsRn                                           SnmpAdminString,
    cfprApSwCardEnvStatsSlotOutlet1                                  INTEGER,
    cfprApSwCardEnvStatsSlotOutlet1Avg                               INTEGER,
    cfprApSwCardEnvStatsSlotOutlet1Max                               INTEGER,
    cfprApSwCardEnvStatsSlotOutlet1Min                               INTEGER,
    cfprApSwCardEnvStatsSlotOutlet2                                  INTEGER,
    cfprApSwCardEnvStatsSlotOutlet2Avg                               INTEGER,
    cfprApSwCardEnvStatsSlotOutlet2Max                               INTEGER,
    cfprApSwCardEnvStatsSlotOutlet2Min                               INTEGER,
    cfprApSwCardEnvStatsSlotOutlet3                                  INTEGER,
    cfprApSwCardEnvStatsSlotOutlet3Avg                               INTEGER,
    cfprApSwCardEnvStatsSlotOutlet3Max                               INTEGER,
    cfprApSwCardEnvStatsSlotOutlet3Min                               INTEGER,
    cfprApSwCardEnvStatsIntervals                                    Gauge32,
    cfprApSwCardEnvStatsSuspect                                      TruthValue,
    cfprApSwCardEnvStatsThresholded                                  CfprApSwCardEnvStatsThresholded,
    cfprApSwCardEnvStatsTimeCollected                                DateAndTime,
    cfprApSwCardEnvStatsUpdate                                       Gauge32
}

cfprApSwCardEnvStatsInstanceId OBJECT-TYPE
    SYNTAX       CfprApManagedObjectId
    MAX-ACCESS   not-accessible
    STATUS       current
    DESCRIPTION
        "Instance identifier of the managed object."
    ::= { cfprApSwCardEnvStatsEntry 1 }

cfprApSwCardEnvStatsDn OBJECT-TYPE
    SYNTAX       CfprApManagedObjectDn
    MAX-ACCESS   read-only
    STATUS       current
    DESCRIPTION
        "Cisco Firepower sw:CardEnvStats:dn managed object property"
    ::= { cfprApSwCardEnvStatsEntry 2 }

cfprApSwCardEnvStatsRn OBJECT-TYPE
    SYNTAX       SnmpAdminString
    MAX-ACCESS   read-only
    STATUS       current
    DESCRIPTION
        "Cisco Firepower sw:CardEnvStats:rn managed object property"
    ::= { cfprApSwCardEnvStatsEntry 3 }

cfprApSwCardEnvStatsSlotOutlet1 OBJECT-TYPE
    SYNTAX       INTEGER
    MAX-ACCESS   read-only
    STATUS       current
    DESCRIPTION
        "Cisco Firepower sw:CardEnvStats:SlotOutlet1 managed
        object property"
    ::= { cfprApSwCardEnvStatsEntry 4 }

cfprApSwCardEnvStatsSlotOutlet1Avg OBJECT-TYPE
    SYNTAX       INTEGER
    MAX-ACCESS   read-only
    STATUS       current
    DESCRIPTION
        "Cisco Firepower sw:CardEnvStats:SlotOutlet1Avg
        managed object property"
    ::= { cfprApSwCardEnvStatsEntry 5 }

cfprApSwCardEnvStatsSlotOutlet1Max OBJECT-TYPE
    SYNTAX       INTEGER
    MAX-ACCESS   read-only
    STATUS       current
    DESCRIPTION
        "Cisco Firepower sw:CardEnvStats:SlotOutlet1Max
        managed object property"
    ::= { cfprApSwCardEnvStatsEntry 6 }

cfprApSwCardEnvStatsSlotOutlet1Min OBJECT-TYPE
    SYNTAX       INTEGER
    MAX-ACCESS   read-only
    STATUS       current
    DESCRIPTION
        "Cisco Firepower sw:CardEnvStats:SlotOutlet1Min
        managed object property"
    ::= { cfprApSwCardEnvStatsEntry 7 }

cfprApSwCardEnvStatsSlotOutlet2 OBJECT-TYPE
    SYNTAX       INTEGER
    MAX-ACCESS   read-only
    STATUS       current
    DESCRIPTION
        "Cisco Firepower sw:CardEnvStats:SlotOutlet2 managed
        object property"
    ::= { cfprApSwCardEnvStatsEntry 8 }

cfprApSwCardEnvStatsSlotOutlet2Avg OBJECT-TYPE
    SYNTAX       INTEGER
    MAX-ACCESS   read-only
    STATUS       current
    DESCRIPTION
        "Cisco Firepower sw:CardEnvStats:SlotOutlet2Avg
        managed object property"
    ::= { cfprApSwCardEnvStatsEntry 9 }

cfprApSwCardEnvStatsSlotOutlet2Max OBJECT-TYPE
    SYNTAX       INTEGER
    MAX-ACCESS   read-only
    STATUS       current
    DESCRIPTION
        "Cisco Firepower sw:CardEnvStats:SlotOutlet2Max
        managed object property"
    ::= { cfprApSwCardEnvStatsEntry 10 }

cfprApSwCardEnvStatsSlotOutlet2Min OBJECT-TYPE
    SYNTAX       INTEGER
    MAX-ACCESS   read-only
    STATUS       current
    DESCRIPTION
        "Cisco Firepower sw:CardEnvStats:SlotOutlet2Min
        managed object property"
    ::= { cfprApSwCardEnvStatsEntry 11 }

cfprApSwCardEnvStatsSlotOutlet3 OBJECT-TYPE
    SYNTAX       INTEGER
    MAX-ACCESS   read-only
    STATUS       current
    DESCRIPTION
        "Cisco Firepower sw:CardEnvStats:SlotOutlet3 managed
        object property"
    ::= { cfprApSwCardEnvStatsEntry 12 }

cfprApSwCardEnvStatsSlotOutlet3Avg OBJECT-TYPE
    SYNTAX       INTEGER
    MAX-ACCESS   read-only
    STATUS       current
    DESCRIPTION
        "Cisco Firepower sw:CardEnvStats:SlotOutlet3Avg
        managed object property"
    ::= { cfprApSwCardEnvStatsEntry 13 }

cfprApSwCardEnvStatsSlotOutlet3Max OBJECT-TYPE
    SYNTAX       INTEGER
    MAX-ACCESS   read-only
    STATUS       current
    DESCRIPTION
        "Cisco Firepower sw:CardEnvStats:SlotOutlet3Max
        managed object property"
    ::= { cfprApSwCardEnvStatsEntry 14 }

cfprApSwCardEnvStatsSlotOutlet3Min OBJECT-TYPE
    SYNTAX       INTEGER
    MAX-ACCESS   read-only
    STATUS       current
    DESCRIPTION
        "Cisco Firepower sw:CardEnvStats:SlotOutlet3Min
        managed object property"
    ::= { cfprApSwCardEnvStatsEntry 15 }

cfprApSwCardEnvStatsIntervals OBJECT-TYPE
    SYNTAX       Gauge32
    MAX-ACCESS   read-only
    STATUS       current
    DESCRIPTION
        "Cisco Firepower sw:CardEnvStats:intervals managed
        object property"
    ::= { cfprApSwCardEnvStatsEntry 16 }

cfprApSwCardEnvStatsSuspect OBJECT-TYPE
    SYNTAX       TruthValue
    MAX-ACCESS   read-only
    STATUS       current
    DESCRIPTION
        "Cisco Firepower sw:CardEnvStats:suspect managed object property"
    ::= { cfprApSwCardEnvStatsEntry 17 }

cfprApSwCardEnvStatsThresholded OBJECT-TYPE
    SYNTAX       CfprApSwCardEnvStatsThresholded
    MAX-ACCESS   read-only
    STATUS       current
    DESCRIPTION
        "Cisco Firepower sw:CardEnvStats:thresholded managed
        object property"
    ::= { cfprApSwCardEnvStatsEntry 18 }

cfprApSwCardEnvStatsTimeCollected OBJECT-TYPE
    SYNTAX       DateAndTime
    MAX-ACCESS   read-only
    STATUS       current
    DESCRIPTION
        "Cisco Firepower sw:CardEnvStats:timeCollected
        managed object property"
    ::= { cfprApSwCardEnvStatsEntry 19 }

cfprApSwCardEnvStatsUpdate OBJECT-TYPE
    SYNTAX       Gauge32
    MAX-ACCESS   read-only
    STATUS       current
    DESCRIPTION
        "Cisco Firepower sw:CardEnvStats:update managed object property"
    ::= { cfprApSwCardEnvStatsEntry 20 }

cfprApSwCardEnvStatsHistTable OBJECT-TYPE
    SYNTAX           SEQUENCE OF CfprApSwCardEnvStatsHistEntry
    MAX-ACCESS       not-accessible
    STATUS           current
    DESCRIPTION
        "Cisco Firepower sw:CardEnvStatsHist managed object table"
    ::= { cfprApSwObjects 7 }

cfprApSwCardEnvStatsHistEntry OBJECT-TYPE
    SYNTAX           CfprApSwCardEnvStatsHistEntry
    MAX-ACCESS       not-accessible
    STATUS           current
    DESCRIPTION
        "Entry for the cfprApSwCardEnvStatsHistTable table."
    INDEX { cfprApSwCardEnvStatsHistInstanceId }
    ::= { cfprApSwCardEnvStatsHistTable 1 }

CfprApSwCardEnvStatsHistEntry ::= SEQUENCE {
    cfprApSwCardEnvStatsHistInstanceId                               CfprApManagedObjectId,
    cfprApSwCardEnvStatsHistDn                                       CfprApManagedObjectDn,
    cfprApSwCardEnvStatsHistRn                                       SnmpAdminString,
    cfprApSwCardEnvStatsHistSlotOutlet1                              INTEGER,
    cfprApSwCardEnvStatsHistSlotOutlet1Avg                           INTEGER,
    cfprApSwCardEnvStatsHistSlotOutlet1Max                           INTEGER,
    cfprApSwCardEnvStatsHistSlotOutlet1Min                           INTEGER,
    cfprApSwCardEnvStatsHistSlotOutlet2                              INTEGER,
    cfprApSwCardEnvStatsHistSlotOutlet2Avg                           INTEGER,
    cfprApSwCardEnvStatsHistSlotOutlet2Max                           INTEGER,
    cfprApSwCardEnvStatsHistSlotOutlet2Min                           INTEGER,
    cfprApSwCardEnvStatsHistSlotOutlet3                              INTEGER,
    cfprApSwCardEnvStatsHistSlotOutlet3Avg                           INTEGER,
    cfprApSwCardEnvStatsHistSlotOutlet3Max                           INTEGER,
    cfprApSwCardEnvStatsHistSlotOutlet3Min                           INTEGER,
    cfprApSwCardEnvStatsHistId                                       Unsigned64,
    cfprApSwCardEnvStatsHistMostRecent                               TruthValue,
    cfprApSwCardEnvStatsHistSuspect                                  TruthValue,
    cfprApSwCardEnvStatsHistThresholded                              CfprApSwCardEnvStatsHistThresholded,
    cfprApSwCardEnvStatsHistTimeCollected                            DateAndTime
}

cfprApSwCardEnvStatsHistInstanceId OBJECT-TYPE
    SYNTAX       CfprApManagedObjectId
    MAX-ACCESS   not-accessible
    STATUS       current
    DESCRIPTION
        "Instance identifier of the managed object."
    ::= { cfprApSwCardEnvStatsHistEntry 1 }

cfprApSwCardEnvStatsHistDn OBJECT-TYPE
    SYNTAX       CfprApManagedObjectDn
    MAX-ACCESS   read-only
    STATUS       current
    DESCRIPTION
        "Cisco Firepower sw:CardEnvStatsHist:dn managed object property"
    ::= { cfprApSwCardEnvStatsHistEntry 2 }

cfprApSwCardEnvStatsHistRn OBJECT-TYPE
    SYNTAX       SnmpAdminString
    MAX-ACCESS   read-only
    STATUS       current
    DESCRIPTION
        "Cisco Firepower sw:CardEnvStatsHist:rn managed object property"
    ::= { cfprApSwCardEnvStatsHistEntry 3 }

cfprApSwCardEnvStatsHistSlotOutlet1 OBJECT-TYPE
    SYNTAX       INTEGER
    MAX-ACCESS   read-only
    STATUS       current
    DESCRIPTION
        "Cisco Firepower sw:CardEnvStatsHist:SlotOutlet1
        managed object property"
    ::= { cfprApSwCardEnvStatsHistEntry 4 }

cfprApSwCardEnvStatsHistSlotOutlet1Avg OBJECT-TYPE
    SYNTAX       INTEGER
    MAX-ACCESS   read-only
    STATUS       current
    DESCRIPTION
        "Cisco Firepower sw:CardEnvStatsHist:SlotOutlet1Avg
        managed object property"
    ::= { cfprApSwCardEnvStatsHistEntry 5 }

cfprApSwCardEnvStatsHistSlotOutlet1Max OBJECT-TYPE
    SYNTAX       INTEGER
    MAX-ACCESS   read-only
    STATUS       current
    DESCRIPTION
        "Cisco Firepower sw:CardEnvStatsHist:SlotOutlet1Max
        managed object property"
    ::= { cfprApSwCardEnvStatsHistEntry 6 }

cfprApSwCardEnvStatsHistSlotOutlet1Min OBJECT-TYPE
    SYNTAX       INTEGER
    MAX-ACCESS   read-only
    STATUS       current
    DESCRIPTION
        "Cisco Firepower sw:CardEnvStatsHist:SlotOutlet1Min
        managed object property"
    ::= { cfprApSwCardEnvStatsHistEntry 7 }

cfprApSwCardEnvStatsHistSlotOutlet2 OBJECT-TYPE
    SYNTAX       INTEGER
    MAX-ACCESS   read-only
    STATUS       current
    DESCRIPTION
        "Cisco Firepower sw:CardEnvStatsHist:SlotOutlet2
        managed object property"
    ::= { cfprApSwCardEnvStatsHistEntry 8 }

cfprApSwCardEnvStatsHistSlotOutlet2Avg OBJECT-TYPE
    SYNTAX       INTEGER
    MAX-ACCESS   read-only
    STATUS       current
    DESCRIPTION
        "Cisco Firepower sw:CardEnvStatsHist:SlotOutlet2Avg
        managed object property"
    ::= { cfprApSwCardEnvStatsHistEntry 9 }

cfprApSwCardEnvStatsHistSlotOutlet2Max OBJECT-TYPE
    SYNTAX       INTEGER
    MAX-ACCESS   read-only
    STATUS       current
    DESCRIPTION
        "Cisco Firepower sw:CardEnvStatsHist:SlotOutlet2Max
        managed object property"
    ::= { cfprApSwCardEnvStatsHistEntry 10 }

cfprApSwCardEnvStatsHistSlotOutlet2Min OBJECT-TYPE
    SYNTAX       INTEGER
    MAX-ACCESS   read-only
    STATUS       current
    DESCRIPTION
        "Cisco Firepower sw:CardEnvStatsHist:SlotOutlet2Min
        managed object property"
    ::= { cfprApSwCardEnvStatsHistEntry 11 }

cfprApSwCardEnvStatsHistSlotOutlet3 OBJECT-TYPE
    SYNTAX       INTEGER
    MAX-ACCESS   read-only
    STATUS       current
    DESCRIPTION
        "Cisco Firepower sw:CardEnvStatsHist:SlotOutlet3
        managed object property"
    ::= { cfprApSwCardEnvStatsHistEntry 12 }

cfprApSwCardEnvStatsHistSlotOutlet3Avg OBJECT-TYPE
    SYNTAX       INTEGER
    MAX-ACCESS   read-only
    STATUS       current
    DESCRIPTION
        "Cisco Firepower sw:CardEnvStatsHist:SlotOutlet3Avg
        managed object property"
    ::= { cfprApSwCardEnvStatsHistEntry 13 }

cfprApSwCardEnvStatsHistSlotOutlet3Max OBJECT-TYPE
    SYNTAX       INTEGER
    MAX-ACCESS   read-only
    STATUS       current
    DESCRIPTION
        "Cisco Firepower sw:CardEnvStatsHist:SlotOutlet3Max
        managed object property"
    ::= { cfprApSwCardEnvStatsHistEntry 14 }

cfprApSwCardEnvStatsHistSlotOutlet3Min OBJECT-TYPE
    SYNTAX       INTEGER
    MAX-ACCESS   read-only
    STATUS       current
    DESCRIPTION
        "Cisco Firepower sw:CardEnvStatsHist:SlotOutlet3Min
        managed object property"
    ::= { cfprApSwCardEnvStatsHistEntry 15 }

cfprApSwCardEnvStatsHistId OBJECT-TYPE
    SYNTAX       Unsigned64
    MAX-ACCESS   read-only
    STATUS       current
    DESCRIPTION
        "Cisco Firepower sw:CardEnvStatsHist:id managed object property"
    ::= { cfprApSwCardEnvStatsHistEntry 16 }

cfprApSwCardEnvStatsHistMostRecent OBJECT-TYPE
    SYNTAX       TruthValue
    MAX-ACCESS   read-only
    STATUS       current
    DESCRIPTION
        "Cisco Firepower sw:CardEnvStatsHist:mostRecent
        managed object property"
    ::= { cfprApSwCardEnvStatsHistEntry 17 }

cfprApSwCardEnvStatsHistSuspect OBJECT-TYPE
    SYNTAX       TruthValue
    MAX-ACCESS   read-only
    STATUS       current
    DESCRIPTION
        "Cisco Firepower sw:CardEnvStatsHist:suspect managed
        object property"
    ::= { cfprApSwCardEnvStatsHistEntry 18 }

cfprApSwCardEnvStatsHistThresholded OBJECT-TYPE
    SYNTAX       CfprApSwCardEnvStatsHistThresholded
    MAX-ACCESS   read-only
    STATUS       current
    DESCRIPTION
        "Cisco Firepower sw:CardEnvStatsHist:thresholded
        managed object property"
    ::= { cfprApSwCardEnvStatsHistEntry 19 }

cfprApSwCardEnvStatsHistTimeCollected OBJECT-TYPE
    SYNTAX       DateAndTime
    MAX-ACCESS   read-only
    STATUS       current
    DESCRIPTION
        "Cisco Firepower sw:CardEnvStatsHist:timeCollected
        managed object property"
    ::= { cfprApSwCardEnvStatsHistEntry 20 }

cfprApSwCmclanTable OBJECT-TYPE
    SYNTAX           SEQUENCE OF CfprApSwCmclanEntry
    MAX-ACCESS       not-accessible
    STATUS           current
    DESCRIPTION
        "Cisco Firepower sw:Cmclan managed object table"
    ::= { cfprApSwObjects 8 }

cfprApSwCmclanEntry OBJECT-TYPE
    SYNTAX           CfprApSwCmclanEntry
    MAX-ACCESS       not-accessible
    STATUS           current
    DESCRIPTION
        "Entry for the cfprApSwCmclanTable table."
    INDEX { cfprApSwCmclanInstanceId }
    ::= { cfprApSwCmclanTable 1 }

CfprApSwCmclanEntry ::= SEQUENCE {
    cfprApSwCmclanInstanceId                                         CfprApManagedObjectId,
    cfprApSwCmclanDn                                                 CfprApManagedObjectDn,
    cfprApSwCmclanRn                                                 SnmpAdminString,
    cfprApSwCmclanCimcIds                                            CfprApSwCimcId,
    cfprApSwCmclanEpDn                                               SnmpAdminString,
    cfprApSwCmclanId                                                 Gauge32,
    cfprApSwCmclanIfRole                                             CfprApNetworkPortRole,
    cfprApSwCmclanIfType                                             CfprApNetworkVnetEpIfType,
    cfprApSwCmclanLocale                                             CfprApNetworkLocale,
    cfprApSwCmclanName                                               SnmpAdminString,
    cfprApSwCmclanPeerDn                                             SnmpAdminString,
    cfprApSwCmclanTransport                                          CfprApNetworkTransport,
    cfprApSwCmclanType                                               CfprApNetworkConnectionType
}

cfprApSwCmclanInstanceId OBJECT-TYPE
    SYNTAX       CfprApManagedObjectId
    MAX-ACCESS   not-accessible
    STATUS       current
    DESCRIPTION
        "Instance identifier of the managed object."
    ::= { cfprApSwCmclanEntry 1 }

cfprApSwCmclanDn OBJECT-TYPE
    SYNTAX       CfprApManagedObjectDn
    MAX-ACCESS   read-only
    STATUS       current
    DESCRIPTION
        "Cisco Firepower sw:Cmclan:dn managed object property"
    ::= { cfprApSwCmclanEntry 2 }

cfprApSwCmclanRn OBJECT-TYPE
    SYNTAX       SnmpAdminString
    MAX-ACCESS   read-only
    STATUS       current
    DESCRIPTION
        "Cisco Firepower sw:Cmclan:rn managed object property"
    ::= { cfprApSwCmclanEntry 3 }

cfprApSwCmclanCimcIds OBJECT-TYPE
    SYNTAX       CfprApSwCimcId
    MAX-ACCESS   read-only
    STATUS       current
    DESCRIPTION
        "Cisco Firepower sw:Cmclan:cimcIds managed object property"
    ::= { cfprApSwCmclanEntry 4 }

cfprApSwCmclanEpDn OBJECT-TYPE
    SYNTAX       SnmpAdminString
    MAX-ACCESS   read-only
    STATUS       current
    DESCRIPTION
        "Cisco Firepower sw:Cmclan:epDn managed object property"
    ::= { cfprApSwCmclanEntry 5 }

cfprApSwCmclanId OBJECT-TYPE
    SYNTAX       Gauge32
    MAX-ACCESS   read-only
    STATUS       current
    DESCRIPTION
        "Cisco Firepower sw:Cmclan:id managed object property"
    ::= { cfprApSwCmclanEntry 6 }

cfprApSwCmclanIfRole OBJECT-TYPE
    SYNTAX       CfprApNetworkPortRole
    MAX-ACCESS   read-only
    STATUS       current
    DESCRIPTION
        "Cisco Firepower sw:Cmclan:ifRole managed object property"
    ::= { cfprApSwCmclanEntry 7 }

cfprApSwCmclanIfType OBJECT-TYPE
    SYNTAX       CfprApNetworkVnetEpIfType
    MAX-ACCESS   read-only
    STATUS       current
    DESCRIPTION
        "Cisco Firepower sw:Cmclan:ifType managed object property"
    ::= { cfprApSwCmclanEntry 8 }

cfprApSwCmclanLocale OBJECT-TYPE
    SYNTAX       CfprApNetworkLocale
    MAX-ACCESS   read-only
    STATUS       current
    DESCRIPTION
        "Cisco Firepower sw:Cmclan:locale managed object property"
    ::= { cfprApSwCmclanEntry 9 }

cfprApSwCmclanName OBJECT-TYPE
    SYNTAX       SnmpAdminString
    MAX-ACCESS   read-only
    STATUS       current
    DESCRIPTION
        "Cisco Firepower sw:Cmclan:name managed object property"
    ::= { cfprApSwCmclanEntry 10 }

cfprApSwCmclanPeerDn OBJECT-TYPE
    SYNTAX       SnmpAdminString
    MAX-ACCESS   read-only
    STATUS       current
    DESCRIPTION
        "Cisco Firepower sw:Cmclan:peerDn managed object property"
    ::= { cfprApSwCmclanEntry 11 }

cfprApSwCmclanTransport OBJECT-TYPE
    SYNTAX       CfprApNetworkTransport
    MAX-ACCESS   read-only
    STATUS       current
    DESCRIPTION
        "Cisco Firepower sw:Cmclan:transport managed object property"
    ::= { cfprApSwCmclanEntry 12 }

cfprApSwCmclanType OBJECT-TYPE
    SYNTAX       CfprApNetworkConnectionType
    MAX-ACCESS   read-only
    STATUS       current
    DESCRIPTION
        "Cisco Firepower sw:Cmclan:type managed object property"
    ::= { cfprApSwCmclanEntry 13 }

cfprApSwEnvStatsTable OBJECT-TYPE
    SYNTAX           SEQUENCE OF CfprApSwEnvStatsEntry
    MAX-ACCESS       not-accessible
    STATUS           current
    DESCRIPTION
        "Cisco Firepower sw:EnvStats managed object table"
    ::= { cfprApSwObjects 9 }

cfprApSwEnvStatsEntry OBJECT-TYPE
    SYNTAX           CfprApSwEnvStatsEntry
    MAX-ACCESS       not-accessible
    STATUS           current
    DESCRIPTION
        "Entry for the cfprApSwEnvStatsTable table."
    INDEX { cfprApSwEnvStatsInstanceId }
    ::= { cfprApSwEnvStatsTable 1 }

CfprApSwEnvStatsEntry ::= SEQUENCE {
    cfprApSwEnvStatsInstanceId                                       CfprApManagedObjectId,
    cfprApSwEnvStatsDn                                               CfprApManagedObjectDn,
    cfprApSwEnvStatsRn                                               SnmpAdminString,
    cfprApSwEnvStatsFanCtrlrInlet1                                   INTEGER,
    cfprApSwEnvStatsFanCtrlrInlet1Avg                                INTEGER,
    cfprApSwEnvStatsFanCtrlrInlet1Max                                INTEGER,
    cfprApSwEnvStatsFanCtrlrInlet1Min                                INTEGER,
    cfprApSwEnvStatsFanCtrlrInlet2                                   INTEGER,
    cfprApSwEnvStatsFanCtrlrInlet2Avg                                INTEGER,
    cfprApSwEnvStatsFanCtrlrInlet2Max                                INTEGER,
    cfprApSwEnvStatsFanCtrlrInlet2Min                                INTEGER,
    cfprApSwEnvStatsFanCtrlrInlet3                                   INTEGER,
    cfprApSwEnvStatsFanCtrlrInlet3Avg                                INTEGER,
    cfprApSwEnvStatsFanCtrlrInlet3Max                                INTEGER,
    cfprApSwEnvStatsFanCtrlrInlet3Min                                INTEGER,
    cfprApSwEnvStatsFanCtrlrInlet4                                   INTEGER,
    cfprApSwEnvStatsFanCtrlrInlet4Avg                                INTEGER,
    cfprApSwEnvStatsFanCtrlrInlet4Max                                INTEGER,
    cfprApSwEnvStatsFanCtrlrInlet4Min                                INTEGER,
    cfprApSwEnvStatsIntervals                                        Gauge32,
    cfprApSwEnvStatsMainBoardOutlet1                                 INTEGER,
    cfprApSwEnvStatsMainBoardOutlet1Avg                              INTEGER,
    cfprApSwEnvStatsMainBoardOutlet1Max                              INTEGER,
    cfprApSwEnvStatsMainBoardOutlet1Min                              INTEGER,
    cfprApSwEnvStatsMainBoardOutlet2                                 INTEGER,
    cfprApSwEnvStatsMainBoardOutlet2Avg                              INTEGER,
    cfprApSwEnvStatsMainBoardOutlet2Max                              INTEGER,
    cfprApSwEnvStatsMainBoardOutlet2Min                              INTEGER,
    cfprApSwEnvStatsPsuCtrlrInlet1                                   INTEGER,
    cfprApSwEnvStatsPsuCtrlrInlet1Avg                                INTEGER,
    cfprApSwEnvStatsPsuCtrlrInlet1Max                                INTEGER,
    cfprApSwEnvStatsPsuCtrlrInlet1Min                                INTEGER,
    cfprApSwEnvStatsPsuCtrlrInlet2                                   INTEGER,
    cfprApSwEnvStatsPsuCtrlrInlet2Avg                                INTEGER,
    cfprApSwEnvStatsPsuCtrlrInlet2Max                                INTEGER,
    cfprApSwEnvStatsPsuCtrlrInlet2Min                                INTEGER,
    cfprApSwEnvStatsSuspect                                          TruthValue,
    cfprApSwEnvStatsThresholded                                      CfprApSwEnvStatsThresholded,
    cfprApSwEnvStatsTimeCollected                                    DateAndTime,
    cfprApSwEnvStatsUpdate                                           Gauge32
}

cfprApSwEnvStatsInstanceId OBJECT-TYPE
    SYNTAX       CfprApManagedObjectId
    MAX-ACCESS   not-accessible
    STATUS       current
    DESCRIPTION
        "Instance identifier of the managed object."
    ::= { cfprApSwEnvStatsEntry 1 }

cfprApSwEnvStatsDn OBJECT-TYPE
    SYNTAX       CfprApManagedObjectDn
    MAX-ACCESS   read-only
    STATUS       current
    DESCRIPTION
        "Cisco Firepower sw:EnvStats:dn managed object property"
    ::= { cfprApSwEnvStatsEntry 2 }

cfprApSwEnvStatsRn OBJECT-TYPE
    SYNTAX       SnmpAdminString
    MAX-ACCESS   read-only
    STATUS       current
    DESCRIPTION
        "Cisco Firepower sw:EnvStats:rn managed object property"
    ::= { cfprApSwEnvStatsEntry 3 }

cfprApSwEnvStatsFanCtrlrInlet1 OBJECT-TYPE
    SYNTAX       INTEGER
    MAX-ACCESS   read-only
    STATUS       current
    DESCRIPTION
        "Cisco Firepower sw:EnvStats:fanCtrlrInlet1 managed
        object property"
    ::= { cfprApSwEnvStatsEntry 4 }

cfprApSwEnvStatsFanCtrlrInlet1Avg OBJECT-TYPE
    SYNTAX       INTEGER
    MAX-ACCESS   read-only
    STATUS       current
    DESCRIPTION
        "Cisco Firepower sw:EnvStats:fanCtrlrInlet1Avg
        managed object property"
    ::= { cfprApSwEnvStatsEntry 5 }

cfprApSwEnvStatsFanCtrlrInlet1Max OBJECT-TYPE
    SYNTAX       INTEGER
    MAX-ACCESS   read-only
    STATUS       current
    DESCRIPTION
        "Cisco Firepower sw:EnvStats:fanCtrlrInlet1Max
        managed object property"
    ::= { cfprApSwEnvStatsEntry 6 }

cfprApSwEnvStatsFanCtrlrInlet1Min OBJECT-TYPE
    SYNTAX       INTEGER
    MAX-ACCESS   read-only
    STATUS       current
    DESCRIPTION
        "Cisco Firepower sw:EnvStats:fanCtrlrInlet1Min
        managed object property"
    ::= { cfprApSwEnvStatsEntry 7 }

cfprApSwEnvStatsFanCtrlrInlet2 OBJECT-TYPE
    SYNTAX       INTEGER
    MAX-ACCESS   read-only
    STATUS       current
    DESCRIPTION
        "Cisco Firepower sw:EnvStats:fanCtrlrInlet2 managed
        object property"
    ::= { cfprApSwEnvStatsEntry 8 }

cfprApSwEnvStatsFanCtrlrInlet2Avg OBJECT-TYPE
    SYNTAX       INTEGER
    MAX-ACCESS   read-only
    STATUS       current
    DESCRIPTION
        "Cisco Firepower sw:EnvStats:fanCtrlrInlet2Avg
        managed object property"
    ::= { cfprApSwEnvStatsEntry 9 }

cfprApSwEnvStatsFanCtrlrInlet2Max OBJECT-TYPE
    SYNTAX       INTEGER
    MAX-ACCESS   read-only
    STATUS       current
    DESCRIPTION
        "Cisco Firepower sw:EnvStats:fanCtrlrInlet2Max
        managed object property"
    ::= { cfprApSwEnvStatsEntry 10 }

cfprApSwEnvStatsFanCtrlrInlet2Min OBJECT-TYPE
    SYNTAX       INTEGER
    MAX-ACCESS   read-only
    STATUS       current
    DESCRIPTION
        "Cisco Firepower sw:EnvStats:fanCtrlrInlet2Min
        managed object property"
    ::= { cfprApSwEnvStatsEntry 11 }

cfprApSwEnvStatsFanCtrlrInlet3 OBJECT-TYPE
    SYNTAX       INTEGER
    MAX-ACCESS   read-only
    STATUS       current
    DESCRIPTION
        "Cisco Firepower sw:EnvStats:fanCtrlrInlet3 managed
        object property"
    ::= { cfprApSwEnvStatsEntry 12 }

cfprApSwEnvStatsFanCtrlrInlet3Avg OBJECT-TYPE
    SYNTAX       INTEGER
    MAX-ACCESS   read-only
    STATUS       current
    DESCRIPTION
        "Cisco Firepower sw:EnvStats:fanCtrlrInlet3Avg
        managed object property"
    ::= { cfprApSwEnvStatsEntry 13 }

cfprApSwEnvStatsFanCtrlrInlet3Max OBJECT-TYPE
    SYNTAX       INTEGER
    MAX-ACCESS   read-only
    STATUS       current
    DESCRIPTION
        "Cisco Firepower sw:EnvStats:fanCtrlrInlet3Max
        managed object property"
    ::= { cfprApSwEnvStatsEntry 14 }

cfprApSwEnvStatsFanCtrlrInlet3Min OBJECT-TYPE
    SYNTAX       INTEGER
    MAX-ACCESS   read-only
    STATUS       current
    DESCRIPTION
        "Cisco Firepower sw:EnvStats:fanCtrlrInlet3Min
        managed object property"
    ::= { cfprApSwEnvStatsEntry 15 }

cfprApSwEnvStatsFanCtrlrInlet4 OBJECT-TYPE
    SYNTAX       INTEGER
    MAX-ACCESS   read-only
    STATUS       current
    DESCRIPTION
        "Cisco Firepower sw:EnvStats:fanCtrlrInlet4 managed
        object property"
    ::= { cfprApSwEnvStatsEntry 16 }

cfprApSwEnvStatsFanCtrlrInlet4Avg OBJECT-TYPE
    SYNTAX       INTEGER
    MAX-ACCESS   read-only
    STATUS       current
    DESCRIPTION
        "Cisco Firepower sw:EnvStats:fanCtrlrInlet4Avg
        managed object property"
    ::= { cfprApSwEnvStatsEntry 17 }

cfprApSwEnvStatsFanCtrlrInlet4Max OBJECT-TYPE
    SYNTAX       INTEGER
    MAX-ACCESS   read-only
    STATUS       current
    DESCRIPTION
        "Cisco Firepower sw:EnvStats:fanCtrlrInlet4Max
        managed object property"
    ::= { cfprApSwEnvStatsEntry 18 }

cfprApSwEnvStatsFanCtrlrInlet4Min OBJECT-TYPE
    SYNTAX       INTEGER
    MAX-ACCESS   read-only
    STATUS       current
    DESCRIPTION
        "Cisco Firepower sw:EnvStats:fanCtrlrInlet4Min
        managed object property"
    ::= { cfprApSwEnvStatsEntry 19 }

cfprApSwEnvStatsIntervals OBJECT-TYPE
    SYNTAX       Gauge32
    MAX-ACCESS   read-only
    STATUS       current
    DESCRIPTION
        "Cisco Firepower sw:EnvStats:intervals managed object property"
    ::= { cfprApSwEnvStatsEntry 20 }

cfprApSwEnvStatsMainBoardOutlet1 OBJECT-TYPE
    SYNTAX       INTEGER
    MAX-ACCESS   read-only
    STATUS       current
    DESCRIPTION
        "Cisco Firepower sw:EnvStats:mainBoardOutlet1 managed
        object property"
    ::= { cfprApSwEnvStatsEntry 21 }

cfprApSwEnvStatsMainBoardOutlet1Avg OBJECT-TYPE
    SYNTAX       INTEGER
    MAX-ACCESS   read-only
    STATUS       current
    DESCRIPTION
        "Cisco Firepower sw:EnvStats:mainBoardOutlet1Avg
        managed object property"
    ::= { cfprApSwEnvStatsEntry 22 }

cfprApSwEnvStatsMainBoardOutlet1Max OBJECT-TYPE
    SYNTAX       INTEGER
    MAX-ACCESS   read-only
    STATUS       current
    DESCRIPTION
        "Cisco Firepower sw:EnvStats:mainBoardOutlet1Max
        managed object property"
    ::= { cfprApSwEnvStatsEntry 23 }

cfprApSwEnvStatsMainBoardOutlet1Min OBJECT-TYPE
    SYNTAX       INTEGER
    MAX-ACCESS   read-only
    STATUS       current
    DESCRIPTION
        "Cisco Firepower sw:EnvStats:mainBoardOutlet1Min
        managed object property"
    ::= { cfprApSwEnvStatsEntry 24 }

cfprApSwEnvStatsMainBoardOutlet2 OBJECT-TYPE
    SYNTAX       INTEGER
    MAX-ACCESS   read-only
    STATUS       current
    DESCRIPTION
        "Cisco Firepower sw:EnvStats:mainBoardOutlet2 managed
        object property"
    ::= { cfprApSwEnvStatsEntry 25 }

cfprApSwEnvStatsMainBoardOutlet2Avg OBJECT-TYPE
    SYNTAX       INTEGER
    MAX-ACCESS   read-only
    STATUS       current
    DESCRIPTION
        "Cisco Firepower sw:EnvStats:mainBoardOutlet2Avg
        managed object property"
    ::= { cfprApSwEnvStatsEntry 26 }

cfprApSwEnvStatsMainBoardOutlet2Max OBJECT-TYPE
    SYNTAX       INTEGER
    MAX-ACCESS   read-only
    STATUS       current
    DESCRIPTION
        "Cisco Firepower sw:EnvStats:mainBoardOutlet2Max
        managed object property"
    ::= { cfprApSwEnvStatsEntry 27 }

cfprApSwEnvStatsMainBoardOutlet2Min OBJECT-TYPE
    SYNTAX       INTEGER
    MAX-ACCESS   read-only
    STATUS       current
    DESCRIPTION
        "Cisco Firepower sw:EnvStats:mainBoardOutlet2Min
        managed object property"
    ::= { cfprApSwEnvStatsEntry 28 }

cfprApSwEnvStatsPsuCtrlrInlet1 OBJECT-TYPE
    SYNTAX       INTEGER
    MAX-ACCESS   read-only
    STATUS       current
    DESCRIPTION
        "Cisco Firepower sw:EnvStats:psuCtrlrInlet1 managed
        object property"
    ::= { cfprApSwEnvStatsEntry 29 }

cfprApSwEnvStatsPsuCtrlrInlet1Avg OBJECT-TYPE
    SYNTAX       INTEGER
    MAX-ACCESS   read-only
    STATUS       current
    DESCRIPTION
        "Cisco Firepower sw:EnvStats:psuCtrlrInlet1Avg
        managed object property"
    ::= { cfprApSwEnvStatsEntry 30 }

cfprApSwEnvStatsPsuCtrlrInlet1Max OBJECT-TYPE
    SYNTAX       INTEGER
    MAX-ACCESS   read-only
    STATUS       current
    DESCRIPTION
        "Cisco Firepower sw:EnvStats:psuCtrlrInlet1Max
        managed object property"
    ::= { cfprApSwEnvStatsEntry 31 }

cfprApSwEnvStatsPsuCtrlrInlet1Min OBJECT-TYPE
    SYNTAX       INTEGER
    MAX-ACCESS   read-only
    STATUS       current
    DESCRIPTION
        "Cisco Firepower sw:EnvStats:psuCtrlrInlet1Min
        managed object property"
    ::= { cfprApSwEnvStatsEntry 32 }

cfprApSwEnvStatsPsuCtrlrInlet2 OBJECT-TYPE
    SYNTAX       INTEGER
    MAX-ACCESS   read-only
    STATUS       current
    DESCRIPTION
        "Cisco Firepower sw:EnvStats:psuCtrlrInlet2 managed
        object property"
    ::= { cfprApSwEnvStatsEntry 33 }

cfprApSwEnvStatsPsuCtrlrInlet2Avg OBJECT-TYPE
    SYNTAX       INTEGER
    MAX-ACCESS   read-only
    STATUS       current
    DESCRIPTION
        "Cisco Firepower sw:EnvStats:psuCtrlrInlet2Avg
        managed object property"
    ::= { cfprApSwEnvStatsEntry 34 }

cfprApSwEnvStatsPsuCtrlrInlet2Max OBJECT-TYPE
    SYNTAX       INTEGER
    MAX-ACCESS   read-only
    STATUS       current
    DESCRIPTION
        "Cisco Firepower sw:EnvStats:psuCtrlrInlet2Max
        managed object property"
    ::= { cfprApSwEnvStatsEntry 35 }

cfprApSwEnvStatsPsuCtrlrInlet2Min OBJECT-TYPE
    SYNTAX       INTEGER
    MAX-ACCESS   read-only
    STATUS       current
    DESCRIPTION
        "Cisco Firepower sw:EnvStats:psuCtrlrInlet2Min
        managed object property"
    ::= { cfprApSwEnvStatsEntry 36 }

cfprApSwEnvStatsSuspect OBJECT-TYPE
    SYNTAX       TruthValue
    MAX-ACCESS   read-only
    STATUS       current
    DESCRIPTION
        "Cisco Firepower sw:EnvStats:suspect managed object property"
    ::= { cfprApSwEnvStatsEntry 37 }

cfprApSwEnvStatsThresholded OBJECT-TYPE
    SYNTAX       CfprApSwEnvStatsThresholded
    MAX-ACCESS   read-only
    STATUS       current
    DESCRIPTION
        "Cisco Firepower sw:EnvStats:thresholded managed object property"
    ::= { cfprApSwEnvStatsEntry 38 }

cfprApSwEnvStatsTimeCollected OBJECT-TYPE
    SYNTAX       DateAndTime
    MAX-ACCESS   read-only
    STATUS       current
    DESCRIPTION
        "Cisco Firepower sw:EnvStats:timeCollected managed
        object property"
    ::= { cfprApSwEnvStatsEntry 39 }

cfprApSwEnvStatsUpdate OBJECT-TYPE
    SYNTAX       Gauge32
    MAX-ACCESS   read-only
    STATUS       current
    DESCRIPTION
        "Cisco Firepower sw:EnvStats:update managed object property"
    ::= { cfprApSwEnvStatsEntry 40 }

cfprApSwEnvStatsHistTable OBJECT-TYPE
    SYNTAX           SEQUENCE OF CfprApSwEnvStatsHistEntry
    MAX-ACCESS       not-accessible
    STATUS           current
    DESCRIPTION
        "Cisco Firepower sw:EnvStatsHist managed object table"
    ::= { cfprApSwObjects 10 }

cfprApSwEnvStatsHistEntry OBJECT-TYPE
    SYNTAX           CfprApSwEnvStatsHistEntry
    MAX-ACCESS       not-accessible
    STATUS           current
    DESCRIPTION
        "Entry for the cfprApSwEnvStatsHistTable table."
    INDEX { cfprApSwEnvStatsHistInstanceId }
    ::= { cfprApSwEnvStatsHistTable 1 }

CfprApSwEnvStatsHistEntry ::= SEQUENCE {
    cfprApSwEnvStatsHistInstanceId                                   CfprApManagedObjectId,
    cfprApSwEnvStatsHistDn                                           CfprApManagedObjectDn,
    cfprApSwEnvStatsHistRn                                           SnmpAdminString,
    cfprApSwEnvStatsHistFanCtrlrInlet1                               INTEGER,
    cfprApSwEnvStatsHistFanCtrlrInlet1Avg                            INTEGER,
    cfprApSwEnvStatsHistFanCtrlrInlet1Max                            INTEGER,
    cfprApSwEnvStatsHistFanCtrlrInlet1Min                            INTEGER,
    cfprApSwEnvStatsHistFanCtrlrInlet2                               INTEGER,
    cfprApSwEnvStatsHistFanCtrlrInlet2Avg                            INTEGER,
    cfprApSwEnvStatsHistFanCtrlrInlet2Max                            INTEGER,
    cfprApSwEnvStatsHistFanCtrlrInlet2Min                            INTEGER,
    cfprApSwEnvStatsHistFanCtrlrInlet3                               INTEGER,
    cfprApSwEnvStatsHistFanCtrlrInlet3Avg                            INTEGER,
    cfprApSwEnvStatsHistFanCtrlrInlet3Max                            INTEGER,
    cfprApSwEnvStatsHistFanCtrlrInlet3Min                            INTEGER,
    cfprApSwEnvStatsHistFanCtrlrInlet4                               INTEGER,
    cfprApSwEnvStatsHistFanCtrlrInlet4Avg                            INTEGER,
    cfprApSwEnvStatsHistFanCtrlrInlet4Max                            INTEGER,
    cfprApSwEnvStatsHistFanCtrlrInlet4Min                            INTEGER,
    cfprApSwEnvStatsHistId                                           Unsigned64,
    cfprApSwEnvStatsHistMainBoardOutlet1                             INTEGER,
    cfprApSwEnvStatsHistMainBoardOutlet1Avg                          INTEGER,
    cfprApSwEnvStatsHistMainBoardOutlet1Max                          INTEGER,
    cfprApSwEnvStatsHistMainBoardOutlet1Min                          INTEGER,
    cfprApSwEnvStatsHistMainBoardOutlet2                             INTEGER,
    cfprApSwEnvStatsHistMainBoardOutlet2Avg                          INTEGER,
    cfprApSwEnvStatsHistMainBoardOutlet2Max                          INTEGER,
    cfprApSwEnvStatsHistMainBoardOutlet2Min                          INTEGER,
    cfprApSwEnvStatsHistMostRecent                                   TruthValue,
    cfprApSwEnvStatsHistPsuCtrlrInlet1                               INTEGER,
    cfprApSwEnvStatsHistPsuCtrlrInlet1Avg                            INTEGER,
    cfprApSwEnvStatsHistPsuCtrlrInlet1Max                            INTEGER,
    cfprApSwEnvStatsHistPsuCtrlrInlet1Min                            INTEGER,
    cfprApSwEnvStatsHistPsuCtrlrInlet2                               INTEGER,
    cfprApSwEnvStatsHistPsuCtrlrInlet2Avg                            INTEGER,
    cfprApSwEnvStatsHistPsuCtrlrInlet2Max                            INTEGER,
    cfprApSwEnvStatsHistPsuCtrlrInlet2Min                            INTEGER,
    cfprApSwEnvStatsHistSuspect                                      TruthValue,
    cfprApSwEnvStatsHistThresholded                                  CfprApSwEnvStatsHistThresholded,
    cfprApSwEnvStatsHistTimeCollected                                DateAndTime
}

cfprApSwEnvStatsHistInstanceId OBJECT-TYPE
    SYNTAX       CfprApManagedObjectId
    MAX-ACCESS   not-accessible
    STATUS       current
    DESCRIPTION
        "Instance identifier of the managed object."
    ::= { cfprApSwEnvStatsHistEntry 1 }

cfprApSwEnvStatsHistDn OBJECT-TYPE
    SYNTAX       CfprApManagedObjectDn
    MAX-ACCESS   read-only
    STATUS       current
    DESCRIPTION
        "Cisco Firepower sw:EnvStatsHist:dn managed object property"
    ::= { cfprApSwEnvStatsHistEntry 2 }

cfprApSwEnvStatsHistRn OBJECT-TYPE
    SYNTAX       SnmpAdminString
    MAX-ACCESS   read-only
    STATUS       current
    DESCRIPTION
        "Cisco Firepower sw:EnvStatsHist:rn managed object property"
    ::= { cfprApSwEnvStatsHistEntry 3 }

cfprApSwEnvStatsHistFanCtrlrInlet1 OBJECT-TYPE
    SYNTAX       INTEGER
    MAX-ACCESS   read-only
    STATUS       current
    DESCRIPTION
        "Cisco Firepower sw:EnvStatsHist:fanCtrlrInlet1
        managed object property"
    ::= { cfprApSwEnvStatsHistEntry 4 }

cfprApSwEnvStatsHistFanCtrlrInlet1Avg OBJECT-TYPE
    SYNTAX       INTEGER
    MAX-ACCESS   read-only
    STATUS       current
    DESCRIPTION
        "Cisco Firepower sw:EnvStatsHist:fanCtrlrInlet1Avg
        managed object property"
    ::= { cfprApSwEnvStatsHistEntry 5 }

cfprApSwEnvStatsHistFanCtrlrInlet1Max OBJECT-TYPE
    SYNTAX       INTEGER
    MAX-ACCESS   read-only
    STATUS       current
    DESCRIPTION
        "Cisco Firepower sw:EnvStatsHist:fanCtrlrInlet1Max
        managed object property"
    ::= { cfprApSwEnvStatsHistEntry 6 }

cfprApSwEnvStatsHistFanCtrlrInlet1Min OBJECT-TYPE
    SYNTAX       INTEGER
    MAX-ACCESS   read-only
    STATUS       current
    DESCRIPTION
        "Cisco Firepower sw:EnvStatsHist:fanCtrlrInlet1Min
        managed object property"
    ::= { cfprApSwEnvStatsHistEntry 7 }

cfprApSwEnvStatsHistFanCtrlrInlet2 OBJECT-TYPE
    SYNTAX       INTEGER
    MAX-ACCESS   read-only
    STATUS       current
    DESCRIPTION
        "Cisco Firepower sw:EnvStatsHist:fanCtrlrInlet2
        managed object property"
    ::= { cfprApSwEnvStatsHistEntry 8 }

cfprApSwEnvStatsHistFanCtrlrInlet2Avg OBJECT-TYPE
    SYNTAX       INTEGER
    MAX-ACCESS   read-only
    STATUS       current
    DESCRIPTION
        "Cisco Firepower sw:EnvStatsHist:fanCtrlrInlet2Avg
        managed object property"
    ::= { cfprApSwEnvStatsHistEntry 9 }

cfprApSwEnvStatsHistFanCtrlrInlet2Max OBJECT-TYPE
    SYNTAX       INTEGER
    MAX-ACCESS   read-only
    STATUS       current
    DESCRIPTION
        "Cisco Firepower sw:EnvStatsHist:fanCtrlrInlet2Max
        managed object property"
    ::= { cfprApSwEnvStatsHistEntry 10 }

cfprApSwEnvStatsHistFanCtrlrInlet2Min OBJECT-TYPE
    SYNTAX       INTEGER
    MAX-ACCESS   read-only
    STATUS       current
    DESCRIPTION
        "Cisco Firepower sw:EnvStatsHist:fanCtrlrInlet2Min
        managed object property"
    ::= { cfprApSwEnvStatsHistEntry 11 }

cfprApSwEnvStatsHistFanCtrlrInlet3 OBJECT-TYPE
    SYNTAX       INTEGER
    MAX-ACCESS   read-only
    STATUS       current
    DESCRIPTION
        "Cisco Firepower sw:EnvStatsHist:fanCtrlrInlet3
        managed object property"
    ::= { cfprApSwEnvStatsHistEntry 12 }

cfprApSwEnvStatsHistFanCtrlrInlet3Avg OBJECT-TYPE
    SYNTAX       INTEGER
    MAX-ACCESS   read-only
    STATUS       current
    DESCRIPTION
        "Cisco Firepower sw:EnvStatsHist:fanCtrlrInlet3Avg
        managed object property"
    ::= { cfprApSwEnvStatsHistEntry 13 }

cfprApSwEnvStatsHistFanCtrlrInlet3Max OBJECT-TYPE
    SYNTAX       INTEGER
    MAX-ACCESS   read-only
    STATUS       current
    DESCRIPTION
        "Cisco Firepower sw:EnvStatsHist:fanCtrlrInlet3Max
        managed object property"
    ::= { cfprApSwEnvStatsHistEntry 14 }

cfprApSwEnvStatsHistFanCtrlrInlet3Min OBJECT-TYPE
    SYNTAX       INTEGER
    MAX-ACCESS   read-only
    STATUS       current
    DESCRIPTION
        "Cisco Firepower sw:EnvStatsHist:fanCtrlrInlet3Min
        managed object property"
    ::= { cfprApSwEnvStatsHistEntry 15 }

cfprApSwEnvStatsHistFanCtrlrInlet4 OBJECT-TYPE
    SYNTAX       INTEGER
    MAX-ACCESS   read-only
    STATUS       current
    DESCRIPTION
        "Cisco Firepower sw:EnvStatsHist:fanCtrlrInlet4
        managed object property"
    ::= { cfprApSwEnvStatsHistEntry 16 }

cfprApSwEnvStatsHistFanCtrlrInlet4Avg OBJECT-TYPE
    SYNTAX       INTEGER
    MAX-ACCESS   read-only
    STATUS       current
    DESCRIPTION
        "Cisco Firepower sw:EnvStatsHist:fanCtrlrInlet4Avg
        managed object property"
    ::= { cfprApSwEnvStatsHistEntry 17 }

cfprApSwEnvStatsHistFanCtrlrInlet4Max OBJECT-TYPE
    SYNTAX       INTEGER
    MAX-ACCESS   read-only
    STATUS       current
    DESCRIPTION
        "Cisco Firepower sw:EnvStatsHist:fanCtrlrInlet4Max
        managed object property"
    ::= { cfprApSwEnvStatsHistEntry 18 }

cfprApSwEnvStatsHistFanCtrlrInlet4Min OBJECT-TYPE
    SYNTAX       INTEGER
    MAX-ACCESS   read-only
    STATUS       current
    DESCRIPTION
        "Cisco Firepower sw:EnvStatsHist:fanCtrlrInlet4Min
        managed object property"
    ::= { cfprApSwEnvStatsHistEntry 19 }

cfprApSwEnvStatsHistId OBJECT-TYPE
    SYNTAX       Unsigned64
    MAX-ACCESS   read-only
    STATUS       current
    DESCRIPTION
        "Cisco Firepower sw:EnvStatsHist:id managed object property"
    ::= { cfprApSwEnvStatsHistEntry 20 }

cfprApSwEnvStatsHistMainBoardOutlet1 OBJECT-TYPE
    SYNTAX       INTEGER
    MAX-ACCESS   read-only
    STATUS       current
    DESCRIPTION
        "Cisco Firepower sw:EnvStatsHist:mainBoardOutlet1
        managed object property"
    ::= { cfprApSwEnvStatsHistEntry 21 }

cfprApSwEnvStatsHistMainBoardOutlet1Avg OBJECT-TYPE
    SYNTAX       INTEGER
    MAX-ACCESS   read-only
    STATUS       current
    DESCRIPTION
        "Cisco Firepower sw:EnvStatsHist:mainBoardOutlet1Avg
        managed object property"
    ::= { cfprApSwEnvStatsHistEntry 22 }

cfprApSwEnvStatsHistMainBoardOutlet1Max OBJECT-TYPE
    SYNTAX       INTEGER
    MAX-ACCESS   read-only
    STATUS       current
    DESCRIPTION
        "Cisco Firepower sw:EnvStatsHist:mainBoardOutlet1Max
        managed object property"
    ::= { cfprApSwEnvStatsHistEntry 23 }

cfprApSwEnvStatsHistMainBoardOutlet1Min OBJECT-TYPE
    SYNTAX       INTEGER
    MAX-ACCESS   read-only
    STATUS       current
    DESCRIPTION
        "Cisco Firepower sw:EnvStatsHist:mainBoardOutlet1Min
        managed object property"
    ::= { cfprApSwEnvStatsHistEntry 24 }

cfprApSwEnvStatsHistMainBoardOutlet2 OBJECT-TYPE
    SYNTAX       INTEGER
    MAX-ACCESS   read-only
    STATUS       current
    DESCRIPTION
        "Cisco Firepower sw:EnvStatsHist:mainBoardOutlet2
        managed object property"
    ::= { cfprApSwEnvStatsHistEntry 25 }

cfprApSwEnvStatsHistMainBoardOutlet2Avg OBJECT-TYPE
    SYNTAX       INTEGER
    MAX-ACCESS   read-only
    STATUS       current
    DESCRIPTION
        "Cisco Firepower sw:EnvStatsHist:mainBoardOutlet2Avg
        managed object property"
    ::= { cfprApSwEnvStatsHistEntry 26 }

cfprApSwEnvStatsHistMainBoardOutlet2Max OBJECT-TYPE
    SYNTAX       INTEGER
    MAX-ACCESS   read-only
    STATUS       current
    DESCRIPTION
        "Cisco Firepower sw:EnvStatsHist:mainBoardOutlet2Max
        managed object property"
    ::= { cfprApSwEnvStatsHistEntry 27 }

cfprApSwEnvStatsHistMainBoardOutlet2Min OBJECT-TYPE
    SYNTAX       INTEGER
    MAX-ACCESS   read-only
    STATUS       current
    DESCRIPTION
        "Cisco Firepower sw:EnvStatsHist:mainBoardOutlet2Min
        managed object property"
    ::= { cfprApSwEnvStatsHistEntry 28 }

cfprApSwEnvStatsHistMostRecent OBJECT-TYPE
    SYNTAX       TruthValue
    MAX-ACCESS   read-only
    STATUS       current
    DESCRIPTION
        "Cisco Firepower sw:EnvStatsHist:mostRecent managed
        object property"
    ::= { cfprApSwEnvStatsHistEntry 29 }

cfprApSwEnvStatsHistPsuCtrlrInlet1 OBJECT-TYPE
    SYNTAX       INTEGER
    MAX-ACCESS   read-only
    STATUS       current
    DESCRIPTION
        "Cisco Firepower sw:EnvStatsHist:psuCtrlrInlet1
        managed object property"
    ::= { cfprApSwEnvStatsHistEntry 30 }

cfprApSwEnvStatsHistPsuCtrlrInlet1Avg OBJECT-TYPE
    SYNTAX       INTEGER
    MAX-ACCESS   read-only
    STATUS       current
    DESCRIPTION
        "Cisco Firepower sw:EnvStatsHist:psuCtrlrInlet1Avg
        managed object property"
    ::= { cfprApSwEnvStatsHistEntry 31 }

cfprApSwEnvStatsHistPsuCtrlrInlet1Max OBJECT-TYPE
    SYNTAX       INTEGER
    MAX-ACCESS   read-only
    STATUS       current
    DESCRIPTION
        "Cisco Firepower sw:EnvStatsHist:psuCtrlrInlet1Max
        managed object property"
    ::= { cfprApSwEnvStatsHistEntry 32 }

cfprApSwEnvStatsHistPsuCtrlrInlet1Min OBJECT-TYPE
    SYNTAX       INTEGER
    MAX-ACCESS   read-only
    STATUS       current
    DESCRIPTION
        "Cisco Firepower sw:EnvStatsHist:psuCtrlrInlet1Min
        managed object property"
    ::= { cfprApSwEnvStatsHistEntry 33 }

cfprApSwEnvStatsHistPsuCtrlrInlet2 OBJECT-TYPE
    SYNTAX       INTEGER
    MAX-ACCESS   read-only
    STATUS       current
    DESCRIPTION
        "Cisco Firepower sw:EnvStatsHist:psuCtrlrInlet2
        managed object property"
    ::= { cfprApSwEnvStatsHistEntry 34 }

cfprApSwEnvStatsHistPsuCtrlrInlet2Avg OBJECT-TYPE
    SYNTAX       INTEGER
    MAX-ACCESS   read-only
    STATUS       current
    DESCRIPTION
        "Cisco Firepower sw:EnvStatsHist:psuCtrlrInlet2Avg
        managed object property"
    ::= { cfprApSwEnvStatsHistEntry 35 }

cfprApSwEnvStatsHistPsuCtrlrInlet2Max OBJECT-TYPE
    SYNTAX       INTEGER
    MAX-ACCESS   read-only
    STATUS       current
    DESCRIPTION
        "Cisco Firepower sw:EnvStatsHist:psuCtrlrInlet2Max
        managed object property"
    ::= { cfprApSwEnvStatsHistEntry 36 }

cfprApSwEnvStatsHistPsuCtrlrInlet2Min OBJECT-TYPE
    SYNTAX       INTEGER
    MAX-ACCESS   read-only
    STATUS       current
    DESCRIPTION
        "Cisco Firepower sw:EnvStatsHist:psuCtrlrInlet2Min
        managed object property"
    ::= { cfprApSwEnvStatsHistEntry 37 }

cfprApSwEnvStatsHistSuspect OBJECT-TYPE
    SYNTAX       TruthValue
    MAX-ACCESS   read-only
    STATUS       current
    DESCRIPTION
        "Cisco Firepower sw:EnvStatsHist:suspect managed object property"
    ::= { cfprApSwEnvStatsHistEntry 38 }

cfprApSwEnvStatsHistThresholded OBJECT-TYPE
    SYNTAX       CfprApSwEnvStatsHistThresholded
    MAX-ACCESS   read-only
    STATUS       current
    DESCRIPTION
        "Cisco Firepower sw:EnvStatsHist:thresholded managed
        object property"
    ::= { cfprApSwEnvStatsHistEntry 39 }

cfprApSwEnvStatsHistTimeCollected OBJECT-TYPE
    SYNTAX       DateAndTime
    MAX-ACCESS   read-only
    STATUS       current
    DESCRIPTION
        "Cisco Firepower sw:EnvStatsHist:timeCollected
        managed object property"
    ::= { cfprApSwEnvStatsHistEntry 40 }

cfprApSwEthEstcEpTable OBJECT-TYPE
    SYNTAX           SEQUENCE OF CfprApSwEthEstcEpEntry
    MAX-ACCESS       not-accessible
    STATUS           current
    DESCRIPTION
        "Cisco Firepower sw:EthEstcEp managed object table"
    ::= { cfprApSwObjects 11 }

cfprApSwEthEstcEpEntry OBJECT-TYPE
    SYNTAX           CfprApSwEthEstcEpEntry
    MAX-ACCESS       not-accessible
    STATUS           current
    DESCRIPTION
        "Entry for the cfprApSwEthEstcEpTable table."
    INDEX { cfprApSwEthEstcEpInstanceId }
    ::= { cfprApSwEthEstcEpTable 1 }

CfprApSwEthEstcEpEntry ::= SEQUENCE {
    cfprApSwEthEstcEpInstanceId                                      CfprApManagedObjectId,
    cfprApSwEthEstcEpDn                                              CfprApManagedObjectDn,
    cfprApSwEthEstcEpRn                                              SnmpAdminString,
    cfprApSwEthEstcEpAdminSpeed                                      CfprApPortEthSpeed,
    cfprApSwEthEstcEpAdminState                                      CfprApFabricAdminState,
    cfprApSwEthEstcEpAggrPortId                                      Gauge32,
    cfprApSwEthEstcEpBorderAggrPortId                                Gauge32,
    cfprApSwEthEstcEpBorderPortId                                    Gauge32,
    cfprApSwEthEstcEpBorderSlotId                                    Gauge32,
    cfprApSwEthEstcEpCdp                                             CfprApNwctrlAdminState,
    cfprApSwEthEstcEpChassisId                                       Gauge32,
    cfprApSwEthEstcEpCosValue                                        Gauge32,
    cfprApSwEthEstcEpEpDn                                            SnmpAdminString,
    cfprApSwEthEstcEpForgeMac                                        CfprApDpsecForgedTransmit,
    cfprApSwEthEstcEpIfRole                                          CfprApNetworkPortRole,
    cfprApSwEthEstcEpIfType                                          CfprApSwPIoEpIfType,
    cfprApSwEthEstcEpLc                                              CfprApSwPIoEpLc,
    cfprApSwEthEstcEpLocale                                          CfprApSwEstcEpLocale,
    cfprApSwEthEstcEpName                                            SnmpAdminString,
    cfprApSwEthEstcEpPcId                                            Gauge32,
    cfprApSwEthEstcEpPeerAggrPortId                                  Gauge32,
    cfprApSwEthEstcEpPeerChassisId                                   Gauge32,
    cfprApSwEthEstcEpPeerDn                                          SnmpAdminString,
    cfprApSwEthEstcEpPeerPortId                                      Gauge32,
    cfprApSwEthEstcEpPeerSlotId                                      Gauge32,
    cfprApSwEthEstcEpPinGroupName                                    SnmpAdminString,
    cfprApSwEthEstcEpPortId                                          Gauge32,
    cfprApSwEthEstcEpPortMode                                        CfprApFabricEthEstcPortMode,
    cfprApSwEthEstcEpPriorityFlowCtrl                                CfprApFlowctrlPriorityPause,
    cfprApSwEthEstcEpRecvFlowCtrl                                    CfprApFlowctrlFlowControl,
    cfprApSwEthEstcEpSendFlowCtrl                                    CfprApFlowctrlFlowControl,
    cfprApSwEthEstcEpSlotId                                          Gauge32,
    cfprApSwEthEstcEpSwitchId                                        CfprApNetworkSwitchId,
    cfprApSwEthEstcEpTransport                                       CfprApSwEthEstcEpTransport,
    cfprApSwEthEstcEpType                                            CfprApNetworkConnectionType,
    cfprApSwEthEstcEpUplinkFailAction                                CfprApNwctrlLinkFailAction
}

cfprApSwEthEstcEpInstanceId OBJECT-TYPE
    SYNTAX       CfprApManagedObjectId
    MAX-ACCESS   not-accessible
    STATUS       current
    DESCRIPTION
        "Instance identifier of the managed object."
    ::= { cfprApSwEthEstcEpEntry 1 }

cfprApSwEthEstcEpDn OBJECT-TYPE
    SYNTAX       CfprApManagedObjectDn
    MAX-ACCESS   read-only
    STATUS       current
    DESCRIPTION
        "Cisco Firepower sw:EthEstcEp:dn managed object property"
    ::= { cfprApSwEthEstcEpEntry 2 }

cfprApSwEthEstcEpRn OBJECT-TYPE
    SYNTAX       SnmpAdminString
    MAX-ACCESS   read-only
    STATUS       current
    DESCRIPTION
        "Cisco Firepower sw:EthEstcEp:rn managed object property"
    ::= { cfprApSwEthEstcEpEntry 3 }

cfprApSwEthEstcEpAdminSpeed OBJECT-TYPE
    SYNTAX       CfprApPortEthSpeed
    MAX-ACCESS   read-only
    STATUS       current
    DESCRIPTION
        "Cisco Firepower sw:EthEstcEp:adminSpeed managed object property"
    ::= { cfprApSwEthEstcEpEntry 4 }

cfprApSwEthEstcEpAdminState OBJECT-TYPE
    SYNTAX       CfprApFabricAdminState
    MAX-ACCESS   read-only
    STATUS       current
    DESCRIPTION
        "Cisco Firepower sw:EthEstcEp:adminState managed object property"
    ::= { cfprApSwEthEstcEpEntry 5 }

cfprApSwEthEstcEpAggrPortId OBJECT-TYPE
    SYNTAX       Gauge32
    MAX-ACCESS   read-only
    STATUS       current
    DESCRIPTION
        "Cisco Firepower sw:EthEstcEp:aggrPortId managed object property"
    ::= { cfprApSwEthEstcEpEntry 6 }

cfprApSwEthEstcEpBorderAggrPortId OBJECT-TYPE
    SYNTAX       Gauge32
    MAX-ACCESS   read-only
    STATUS       current
    DESCRIPTION
        "Cisco Firepower sw:EthEstcEp:borderAggrPortId
        managed object property"
    ::= { cfprApSwEthEstcEpEntry 7 }

cfprApSwEthEstcEpBorderPortId OBJECT-TYPE
    SYNTAX       Gauge32
    MAX-ACCESS   read-only
    STATUS       current
    DESCRIPTION
        "Cisco Firepower sw:EthEstcEp:borderPortId managed
        object property"
    ::= { cfprApSwEthEstcEpEntry 8 }

cfprApSwEthEstcEpBorderSlotId OBJECT-TYPE
    SYNTAX       Gauge32
    MAX-ACCESS   read-only
    STATUS       current
    DESCRIPTION
        "Cisco Firepower sw:EthEstcEp:borderSlotId managed
        object property"
    ::= { cfprApSwEthEstcEpEntry 9 }

cfprApSwEthEstcEpCdp OBJECT-TYPE
    SYNTAX       CfprApNwctrlAdminState
    MAX-ACCESS   read-only
    STATUS       current
    DESCRIPTION
        "Cisco Firepower sw:EthEstcEp:cdp managed object property"
    ::= { cfprApSwEthEstcEpEntry 10 }

cfprApSwEthEstcEpChassisId OBJECT-TYPE
    SYNTAX       Gauge32
    MAX-ACCESS   read-only
    STATUS       current
    DESCRIPTION
        "Cisco Firepower sw:EthEstcEp:chassisId managed object property"
    ::= { cfprApSwEthEstcEpEntry 11 }

cfprApSwEthEstcEpCosValue OBJECT-TYPE
    SYNTAX       Gauge32
    MAX-ACCESS   read-only
    STATUS       current
    DESCRIPTION
        "Cisco Firepower sw:EthEstcEp:cosValue managed object property"
    ::= { cfprApSwEthEstcEpEntry 12 }

cfprApSwEthEstcEpEpDn OBJECT-TYPE
    SYNTAX       SnmpAdminString
    MAX-ACCESS   read-only
    STATUS       current
    DESCRIPTION
        "Cisco Firepower sw:EthEstcEp:epDn managed object property"
    ::= { cfprApSwEthEstcEpEntry 13 }

cfprApSwEthEstcEpForgeMac OBJECT-TYPE
    SYNTAX       CfprApDpsecForgedTransmit
    MAX-ACCESS   read-only
    STATUS       current
    DESCRIPTION
        "Cisco Firepower sw:EthEstcEp:forgeMac managed object property"
    ::= { cfprApSwEthEstcEpEntry 14 }

cfprApSwEthEstcEpIfRole OBJECT-TYPE
    SYNTAX       CfprApNetworkPortRole
    MAX-ACCESS   read-only
    STATUS       current
    DESCRIPTION
        "Cisco Firepower sw:EthEstcEp:ifRole managed object property"
    ::= { cfprApSwEthEstcEpEntry 15 }

cfprApSwEthEstcEpIfType OBJECT-TYPE
    SYNTAX       CfprApSwPIoEpIfType
    MAX-ACCESS   read-only
    STATUS       current
    DESCRIPTION
        "Cisco Firepower sw:EthEstcEp:ifType managed object property"
    ::= { cfprApSwEthEstcEpEntry 16 }

cfprApSwEthEstcEpLc OBJECT-TYPE
    SYNTAX       CfprApSwPIoEpLc
    MAX-ACCESS   read-only
    STATUS       current
    DESCRIPTION
        "Cisco Firepower sw:EthEstcEp:lc managed object property"
    ::= { cfprApSwEthEstcEpEntry 17 }

cfprApSwEthEstcEpLocale OBJECT-TYPE
    SYNTAX       CfprApSwEstcEpLocale
    MAX-ACCESS   read-only
    STATUS       current
    DESCRIPTION
        "Cisco Firepower sw:EthEstcEp:locale managed object property"
    ::= { cfprApSwEthEstcEpEntry 18 }

cfprApSwEthEstcEpName OBJECT-TYPE
    SYNTAX       SnmpAdminString
    MAX-ACCESS   read-only
    STATUS       current
    DESCRIPTION
        "Cisco Firepower sw:EthEstcEp:name managed object property"
    ::= { cfprApSwEthEstcEpEntry 19 }

cfprApSwEthEstcEpPcId OBJECT-TYPE
    SYNTAX       Gauge32
    MAX-ACCESS   read-only
    STATUS       current
    DESCRIPTION
        "Cisco Firepower sw:EthEstcEp:pcId managed object property"
    ::= { cfprApSwEthEstcEpEntry 20 }

cfprApSwEthEstcEpPeerAggrPortId OBJECT-TYPE
    SYNTAX       Gauge32
    MAX-ACCESS   read-only
    STATUS       current
    DESCRIPTION
        "Cisco Firepower sw:EthEstcEp:peerAggrPortId managed
        object property"
    ::= { cfprApSwEthEstcEpEntry 21 }

cfprApSwEthEstcEpPeerChassisId OBJECT-TYPE
    SYNTAX       Gauge32
    MAX-ACCESS   read-only
    STATUS       current
    DESCRIPTION
        "Cisco Firepower sw:EthEstcEp:peerChassisId managed
        object property"
    ::= { cfprApSwEthEstcEpEntry 22 }

cfprApSwEthEstcEpPeerDn OBJECT-TYPE
    SYNTAX       SnmpAdminString
    MAX-ACCESS   read-only
    STATUS       current
    DESCRIPTION
        "Cisco Firepower sw:EthEstcEp:peerDn managed object property"
    ::= { cfprApSwEthEstcEpEntry 23 }

cfprApSwEthEstcEpPeerPortId OBJECT-TYPE
    SYNTAX       Gauge32
    MAX-ACCESS   read-only
    STATUS       current
    DESCRIPTION
        "Cisco Firepower sw:EthEstcEp:peerPortId managed object property"
    ::= { cfprApSwEthEstcEpEntry 24 }

cfprApSwEthEstcEpPeerSlotId OBJECT-TYPE
    SYNTAX       Gauge32
    MAX-ACCESS   read-only
    STATUS       current
    DESCRIPTION
        "Cisco Firepower sw:EthEstcEp:peerSlotId managed object property"
    ::= { cfprApSwEthEstcEpEntry 25 }

cfprApSwEthEstcEpPinGroupName OBJECT-TYPE
    SYNTAX       SnmpAdminString
    MAX-ACCESS   read-only
    STATUS       current
    DESCRIPTION
        "Cisco Firepower sw:EthEstcEp:pinGroupName managed
        object property"
    ::= { cfprApSwEthEstcEpEntry 26 }

cfprApSwEthEstcEpPortId OBJECT-TYPE
    SYNTAX       Gauge32
    MAX-ACCESS   read-only
    STATUS       current
    DESCRIPTION
        "Cisco Firepower sw:EthEstcEp:portId managed object property"
    ::= { cfprApSwEthEstcEpEntry 27 }

cfprApSwEthEstcEpPortMode OBJECT-TYPE
    SYNTAX       CfprApFabricEthEstcPortMode
    MAX-ACCESS   read-only
    STATUS       current
    DESCRIPTION
        "Cisco Firepower sw:EthEstcEp:portMode managed object property"
    ::= { cfprApSwEthEstcEpEntry 28 }

cfprApSwEthEstcEpPriorityFlowCtrl OBJECT-TYPE
    SYNTAX       CfprApFlowctrlPriorityPause
    MAX-ACCESS   read-only
    STATUS       current
    DESCRIPTION
        "Cisco Firepower sw:EthEstcEp:priorityFlowCtrl
        managed object property"
    ::= { cfprApSwEthEstcEpEntry 29 }

cfprApSwEthEstcEpRecvFlowCtrl OBJECT-TYPE
    SYNTAX       CfprApFlowctrlFlowControl
    MAX-ACCESS   read-only
    STATUS       current
    DESCRIPTION
        "Cisco Firepower sw:EthEstcEp:recvFlowCtrl managed
        object property"
    ::= { cfprApSwEthEstcEpEntry 30 }

cfprApSwEthEstcEpSendFlowCtrl OBJECT-TYPE
    SYNTAX       CfprApFlowctrlFlowControl
    MAX-ACCESS   read-only
    STATUS       current
    DESCRIPTION
        "Cisco Firepower sw:EthEstcEp:sendFlowCtrl managed
        object property"
    ::= { cfprApSwEthEstcEpEntry 31 }

cfprApSwEthEstcEpSlotId OBJECT-TYPE
    SYNTAX       Gauge32
    MAX-ACCESS   read-only
    STATUS       current
    DESCRIPTION
        "Cisco Firepower sw:EthEstcEp:slotId managed object property"
    ::= { cfprApSwEthEstcEpEntry 32 }

cfprApSwEthEstcEpSwitchId OBJECT-TYPE
    SYNTAX       CfprApNetworkSwitchId
    MAX-ACCESS   read-only
    STATUS       current
    DESCRIPTION
        "Cisco Firepower sw:EthEstcEp:switchId managed object property"
    ::= { cfprApSwEthEstcEpEntry 33 }

cfprApSwEthEstcEpTransport OBJECT-TYPE
    SYNTAX       CfprApSwEthEstcEpTransport
    MAX-ACCESS   read-only
    STATUS       current
    DESCRIPTION
        "Cisco Firepower sw:EthEstcEp:transport managed object property"
    ::= { cfprApSwEthEstcEpEntry 34 }

cfprApSwEthEstcEpType OBJECT-TYPE
    SYNTAX       CfprApNetworkConnectionType
    MAX-ACCESS   read-only
    STATUS       current
    DESCRIPTION
        "Cisco Firepower sw:EthEstcEp:type managed object property"
    ::= { cfprApSwEthEstcEpEntry 35 }

cfprApSwEthEstcEpUplinkFailAction OBJECT-TYPE
    SYNTAX       CfprApNwctrlLinkFailAction
    MAX-ACCESS   read-only
    STATUS       current
    DESCRIPTION
        "Cisco Firepower sw:EthEstcEp:uplinkFailAction
        managed object property"
    ::= { cfprApSwEthEstcEpEntry 36 }

cfprApSwEthEstcPcTable OBJECT-TYPE
    SYNTAX           SEQUENCE OF CfprApSwEthEstcPcEntry
    MAX-ACCESS       not-accessible
    STATUS           current
    DESCRIPTION
        "Cisco Firepower sw:EthEstcPc managed object table"
    ::= { cfprApSwObjects 12 }

cfprApSwEthEstcPcEntry OBJECT-TYPE
    SYNTAX           CfprApSwEthEstcPcEntry
    MAX-ACCESS       not-accessible
    STATUS           current
    DESCRIPTION
        "Entry for the cfprApSwEthEstcPcTable table."
    INDEX { cfprApSwEthEstcPcInstanceId }
    ::= { cfprApSwEthEstcPcTable 1 }

CfprApSwEthEstcPcEntry ::= SEQUENCE {
    cfprApSwEthEstcPcInstanceId                                      CfprApManagedObjectId,
    cfprApSwEthEstcPcDn                                              CfprApManagedObjectDn,
    cfprApSwEthEstcPcRn                                              SnmpAdminString,
    cfprApSwEthEstcPcAdminSpeed                                      CfprApPortEthSpeed,
    cfprApSwEthEstcPcAdminState                                      CfprApFabricAdminState,
    cfprApSwEthEstcPcBorderAggrPortId                                Gauge32,
    cfprApSwEthEstcPcBorderPortId                                    Gauge32,
    cfprApSwEthEstcPcBorderSlotId                                    Gauge32,
    cfprApSwEthEstcPcCdp                                             CfprApNwctrlAdminState,
    cfprApSwEthEstcPcCosValue                                        Gauge32,
    cfprApSwEthEstcPcEpDn                                            SnmpAdminString,
    cfprApSwEthEstcPcForgeMac                                        CfprApDpsecForgedTransmit,
    cfprApSwEthEstcPcIfRole                                          CfprApSwLanPcIfRole,
    cfprApSwEthEstcPcIfType                                          CfprApSwCIoEpIfType,
    cfprApSwEthEstcPcLacpFastTimer                                   TruthValue,
    cfprApSwEthEstcPcLacpSuspendIndividual                           TruthValue,
    cfprApSwEthEstcPcLocale                                          CfprApSwBorderPcLocale,
    cfprApSwEthEstcPcMonTrafDir                                      CfprApFabricTrafficDirection,
    cfprApSwEthEstcPcName                                            SnmpAdminString,
    cfprApSwEthEstcPcPeerDn                                          SnmpAdminString,
    cfprApSwEthEstcPcPortId                                          Gauge32,
    cfprApSwEthEstcPcPortMode                                        CfprApFabricEthEstcPortMode,
    cfprApSwEthEstcPcPriorityFlowCtrl                                CfprApFlowctrlPriorityPause,
    cfprApSwEthEstcPcProtocol                                        CfprApFabricEthPcProtocol,
    cfprApSwEthEstcPcRecvFlowCtrl                                    CfprApFlowctrlFlowControl,
    cfprApSwEthEstcPcSendFlowCtrl                                    CfprApFlowctrlFlowControl,
    cfprApSwEthEstcPcSwitchId                                        CfprApNetworkSwitchId,
    cfprApSwEthEstcPcTransport                                       CfprApSwEthEstcPcTransport,
    cfprApSwEthEstcPcType                                            CfprApSwLanPcType,
    cfprApSwEthEstcPcUplinkFailAction                                CfprApNwctrlLinkFailAction
}

cfprApSwEthEstcPcInstanceId OBJECT-TYPE
    SYNTAX       CfprApManagedObjectId
    MAX-ACCESS   not-accessible
    STATUS       current
    DESCRIPTION
        "Instance identifier of the managed object."
    ::= { cfprApSwEthEstcPcEntry 1 }

cfprApSwEthEstcPcDn OBJECT-TYPE
    SYNTAX       CfprApManagedObjectDn
    MAX-ACCESS   read-only
    STATUS       current
    DESCRIPTION
        "Cisco Firepower sw:EthEstcPc:dn managed object property"
    ::= { cfprApSwEthEstcPcEntry 2 }

cfprApSwEthEstcPcRn OBJECT-TYPE
    SYNTAX       SnmpAdminString
    MAX-ACCESS   read-only
    STATUS       current
    DESCRIPTION
        "Cisco Firepower sw:EthEstcPc:rn managed object property"
    ::= { cfprApSwEthEstcPcEntry 3 }

cfprApSwEthEstcPcAdminSpeed OBJECT-TYPE
    SYNTAX       CfprApPortEthSpeed
    MAX-ACCESS   read-only
    STATUS       current
    DESCRIPTION
        "Cisco Firepower sw:EthEstcPc:adminSpeed managed object property"
    ::= { cfprApSwEthEstcPcEntry 4 }

cfprApSwEthEstcPcAdminState OBJECT-TYPE
    SYNTAX       CfprApFabricAdminState
    MAX-ACCESS   read-only
    STATUS       current
    DESCRIPTION
        "Cisco Firepower sw:EthEstcPc:adminState managed object property"
    ::= { cfprApSwEthEstcPcEntry 5 }

cfprApSwEthEstcPcBorderAggrPortId OBJECT-TYPE
    SYNTAX       Gauge32
    MAX-ACCESS   read-only
    STATUS       current
    DESCRIPTION
        "Cisco Firepower sw:EthEstcPc:borderAggrPortId
        managed object property"
    ::= { cfprApSwEthEstcPcEntry 6 }

cfprApSwEthEstcPcBorderPortId OBJECT-TYPE
    SYNTAX       Gauge32
    MAX-ACCESS   read-only
    STATUS       current
    DESCRIPTION
        "Cisco Firepower sw:EthEstcPc:borderPortId managed
        object property"
    ::= { cfprApSwEthEstcPcEntry 7 }

cfprApSwEthEstcPcBorderSlotId OBJECT-TYPE
    SYNTAX       Gauge32
    MAX-ACCESS   read-only
    STATUS       current
    DESCRIPTION
        "Cisco Firepower sw:EthEstcPc:borderSlotId managed
        object property"
    ::= { cfprApSwEthEstcPcEntry 8 }

cfprApSwEthEstcPcCdp OBJECT-TYPE
    SYNTAX       CfprApNwctrlAdminState
    MAX-ACCESS   read-only
    STATUS       current
    DESCRIPTION
        "Cisco Firepower sw:EthEstcPc:cdp managed object property"
    ::= { cfprApSwEthEstcPcEntry 9 }

cfprApSwEthEstcPcCosValue OBJECT-TYPE
    SYNTAX       Gauge32
    MAX-ACCESS   read-only
    STATUS       current
    DESCRIPTION
        "Cisco Firepower sw:EthEstcPc:cosValue managed object property"
    ::= { cfprApSwEthEstcPcEntry 10 }

cfprApSwEthEstcPcEpDn OBJECT-TYPE
    SYNTAX       SnmpAdminString
    MAX-ACCESS   read-only
    STATUS       current
    DESCRIPTION
        "Cisco Firepower sw:EthEstcPc:epDn managed object property"
    ::= { cfprApSwEthEstcPcEntry 11 }

cfprApSwEthEstcPcForgeMac OBJECT-TYPE
    SYNTAX       CfprApDpsecForgedTransmit
    MAX-ACCESS   read-only
    STATUS       current
    DESCRIPTION
        "Cisco Firepower sw:EthEstcPc:forgeMac managed object property"
    ::= { cfprApSwEthEstcPcEntry 12 }

cfprApSwEthEstcPcIfRole OBJECT-TYPE
    SYNTAX       CfprApSwLanPcIfRole
    MAX-ACCESS   read-only
    STATUS       current
    DESCRIPTION
        "Cisco Firepower sw:EthEstcPc:ifRole managed object property"
    ::= { cfprApSwEthEstcPcEntry 13 }

cfprApSwEthEstcPcIfType OBJECT-TYPE
    SYNTAX       CfprApSwCIoEpIfType
    MAX-ACCESS   read-only
    STATUS       current
    DESCRIPTION
        "Cisco Firepower sw:EthEstcPc:ifType managed object property"
    ::= { cfprApSwEthEstcPcEntry 14 }

cfprApSwEthEstcPcLacpFastTimer OBJECT-TYPE
    SYNTAX       TruthValue
    MAX-ACCESS   read-only
    STATUS       current
    DESCRIPTION
        "Cisco Firepower sw:EthEstcPc:lacpFastTimer managed
        object property"
    ::= { cfprApSwEthEstcPcEntry 15 }

cfprApSwEthEstcPcLacpSuspendIndividual OBJECT-TYPE
    SYNTAX       TruthValue
    MAX-ACCESS   read-only
    STATUS       current
    DESCRIPTION
        "Cisco Firepower sw:EthEstcPc:lacpSuspendIndividual
        managed object property"
    ::= { cfprApSwEthEstcPcEntry 16 }

cfprApSwEthEstcPcLocale OBJECT-TYPE
    SYNTAX       CfprApSwBorderPcLocale
    MAX-ACCESS   read-only
    STATUS       current
    DESCRIPTION
        "Cisco Firepower sw:EthEstcPc:locale managed object property"
    ::= { cfprApSwEthEstcPcEntry 17 }

cfprApSwEthEstcPcMonTrafDir OBJECT-TYPE
    SYNTAX       CfprApFabricTrafficDirection
    MAX-ACCESS   read-only
    STATUS       current
    DESCRIPTION
        "Cisco Firepower sw:EthEstcPc:monTrafDir managed object property"
    ::= { cfprApSwEthEstcPcEntry 18 }

cfprApSwEthEstcPcName OBJECT-TYPE
    SYNTAX       SnmpAdminString
    MAX-ACCESS   read-only
    STATUS       current
    DESCRIPTION
        "Cisco Firepower sw:EthEstcPc:name managed object property"
    ::= { cfprApSwEthEstcPcEntry 19 }

cfprApSwEthEstcPcPeerDn OBJECT-TYPE
    SYNTAX       SnmpAdminString
    MAX-ACCESS   read-only
    STATUS       current
    DESCRIPTION
        "Cisco Firepower sw:EthEstcPc:peerDn managed object property"
    ::= { cfprApSwEthEstcPcEntry 20 }

cfprApSwEthEstcPcPortId OBJECT-TYPE
    SYNTAX       Gauge32
    MAX-ACCESS   read-only
    STATUS       current
    DESCRIPTION
        "Cisco Firepower sw:EthEstcPc:portId managed object property"
    ::= { cfprApSwEthEstcPcEntry 21 }

cfprApSwEthEstcPcPortMode OBJECT-TYPE
    SYNTAX       CfprApFabricEthEstcPortMode
    MAX-ACCESS   read-only
    STATUS       current
    DESCRIPTION
        "Cisco Firepower sw:EthEstcPc:portMode managed object property"
    ::= { cfprApSwEthEstcPcEntry 22 }

cfprApSwEthEstcPcPriorityFlowCtrl OBJECT-TYPE
    SYNTAX       CfprApFlowctrlPriorityPause
    MAX-ACCESS   read-only
    STATUS       current
    DESCRIPTION
        "Cisco Firepower sw:EthEstcPc:priorityFlowCtrl
        managed object property"
    ::= { cfprApSwEthEstcPcEntry 23 }

cfprApSwEthEstcPcProtocol OBJECT-TYPE
    SYNTAX       CfprApFabricEthPcProtocol
    MAX-ACCESS   read-only
    STATUS       current
    DESCRIPTION
        "Cisco Firepower sw:EthEstcPc:protocol managed object property"
    ::= { cfprApSwEthEstcPcEntry 24 }

cfprApSwEthEstcPcRecvFlowCtrl OBJECT-TYPE
    SYNTAX       CfprApFlowctrlFlowControl
    MAX-ACCESS   read-only
    STATUS       current
    DESCRIPTION
        "Cisco Firepower sw:EthEstcPc:recvFlowCtrl managed
        object property"
    ::= { cfprApSwEthEstcPcEntry 25 }

cfprApSwEthEstcPcSendFlowCtrl OBJECT-TYPE
    SYNTAX       CfprApFlowctrlFlowControl
    MAX-ACCESS   read-only
    STATUS       current
    DESCRIPTION
        "Cisco Firepower sw:EthEstcPc:sendFlowCtrl managed
        object property"
    ::= { cfprApSwEthEstcPcEntry 26 }

cfprApSwEthEstcPcSwitchId OBJECT-TYPE
    SYNTAX       CfprApNetworkSwitchId
    MAX-ACCESS   read-only
    STATUS       current
    DESCRIPTION
        "Cisco Firepower sw:EthEstcPc:switchId managed object property"
    ::= { cfprApSwEthEstcPcEntry 27 }

cfprApSwEthEstcPcTransport OBJECT-TYPE
    SYNTAX       CfprApSwEthEstcPcTransport
    MAX-ACCESS   read-only
    STATUS       current
    DESCRIPTION
        "Cisco Firepower sw:EthEstcPc:transport managed object property"
    ::= { cfprApSwEthEstcPcEntry 28 }

cfprApSwEthEstcPcType OBJECT-TYPE
    SYNTAX       CfprApSwLanPcType
    MAX-ACCESS   read-only
    STATUS       current
    DESCRIPTION
        "Cisco Firepower sw:EthEstcPc:type managed object property"
    ::= { cfprApSwEthEstcPcEntry 29 }

cfprApSwEthEstcPcUplinkFailAction OBJECT-TYPE
    SYNTAX       CfprApNwctrlLinkFailAction
    MAX-ACCESS   read-only
    STATUS       current
    DESCRIPTION
        "Cisco Firepower sw:EthEstcPc:uplinkFailAction
        managed object property"
    ::= { cfprApSwEthEstcPcEntry 30 }

cfprApSwEthLanBorderTable OBJECT-TYPE
    SYNTAX           SEQUENCE OF CfprApSwEthLanBorderEntry
    MAX-ACCESS       not-accessible
    STATUS           current
    DESCRIPTION
        "Cisco Firepower sw:EthLanBorder managed object table"
    ::= { cfprApSwObjects 13 }

cfprApSwEthLanBorderEntry OBJECT-TYPE
    SYNTAX           CfprApSwEthLanBorderEntry
    MAX-ACCESS       not-accessible
    STATUS           current
    DESCRIPTION
        "Entry for the cfprApSwEthLanBorderTable table."
    INDEX { cfprApSwEthLanBorderInstanceId }
    ::= { cfprApSwEthLanBorderTable 1 }

CfprApSwEthLanBorderEntry ::= SEQUENCE {
    cfprApSwEthLanBorderInstanceId                                   CfprApManagedObjectId,
    cfprApSwEthLanBorderDn                                           CfprApManagedObjectDn,
    cfprApSwEthLanBorderRn                                           SnmpAdminString,
    cfprApSwEthLanBorderDeployFlag                                   BITS,
    cfprApSwEthLanBorderFsmDescr                                     SnmpAdminString,
    cfprApSwEthLanBorderFsmFlags                                     SnmpAdminString,
    cfprApSwEthLanBorderFsmPrev                                      SnmpAdminString,
    cfprApSwEthLanBorderFsmProgr                                     Gauge32,
    cfprApSwEthLanBorderFsmRmtInvErrCode                             Gauge32,
    cfprApSwEthLanBorderFsmRmtInvErrDescr                            SnmpAdminString,
    cfprApSwEthLanBorderFsmRmtInvRslt                                CfprApConditionRemoteInvRslt,
    cfprApSwEthLanBorderFsmStageDescr                                SnmpAdminString,
    cfprApSwEthLanBorderFsmStamp                                     DateAndTime,
    cfprApSwEthLanBorderFsmStatus                                    SnmpAdminString,
    cfprApSwEthLanBorderFsmTry                                       Gauge32,
    cfprApSwEthLanBorderLocale                                       CfprApSwBorderDomainLocale,
    cfprApSwEthLanBorderName                                         SnmpAdminString,
    cfprApSwEthLanBorderSwitchId                                     CfprApNetworkSwitchId,
    cfprApSwEthLanBorderTransport                                    CfprApSwEthLanBorderTransport,
    cfprApSwEthLanBorderType                                         CfprApSwLanBorderType,
    cfprApSwEthLanBorderUdldMsgInterval                              Gauge32,
    cfprApSwEthLanBorderUdldRecoveryAction                           CfprApFabricRecoveryAction
}

cfprApSwEthLanBorderInstanceId OBJECT-TYPE
    SYNTAX       CfprApManagedObjectId
    MAX-ACCESS   not-accessible
    STATUS       current
    DESCRIPTION
        "Instance identifier of the managed object."
    ::= { cfprApSwEthLanBorderEntry 1 }

cfprApSwEthLanBorderDn OBJECT-TYPE
    SYNTAX       CfprApManagedObjectDn
    MAX-ACCESS   read-only
    STATUS       current
    DESCRIPTION
        "Cisco Firepower sw:EthLanBorder:dn managed object property"
    ::= { cfprApSwEthLanBorderEntry 2 }

cfprApSwEthLanBorderRn OBJECT-TYPE
    SYNTAX       SnmpAdminString
    MAX-ACCESS   read-only
    STATUS       current
    DESCRIPTION
        "Cisco Firepower sw:EthLanBorder:rn managed object property"
    ::= { cfprApSwEthLanBorderEntry 3 }

cfprApSwEthLanBorderDeployFlag OBJECT-TYPE
    SYNTAX       BITS
    MAX-ACCESS   read-only
    STATUS       current
    DESCRIPTION
        "Cisco Firepower sw:EthLanBorder:deployFlag managed
        object property"
    ::= { cfprApSwEthLanBorderEntry 4 }

cfprApSwEthLanBorderFsmDescr OBJECT-TYPE
    SYNTAX       SnmpAdminString
    MAX-ACCESS   read-only
    STATUS       current
    DESCRIPTION
        "Cisco Firepower sw:EthLanBorder:fsmDescr managed object property"
    ::= { cfprApSwEthLanBorderEntry 5 }

cfprApSwEthLanBorderFsmFlags OBJECT-TYPE
    SYNTAX       SnmpAdminString
    MAX-ACCESS   read-only
    STATUS       current
    DESCRIPTION
        "Cisco Firepower sw:EthLanBorder:fsmFlags managed object property"
    ::= { cfprApSwEthLanBorderEntry 6 }

cfprApSwEthLanBorderFsmPrev OBJECT-TYPE
    SYNTAX       SnmpAdminString
    MAX-ACCESS   read-only
    STATUS       current
    DESCRIPTION
        "Cisco Firepower sw:EthLanBorder:fsmPrev managed object property"
    ::= { cfprApSwEthLanBorderEntry 7 }

cfprApSwEthLanBorderFsmProgr OBJECT-TYPE
    SYNTAX       Gauge32
    MAX-ACCESS   read-only
    STATUS       current
    DESCRIPTION
        "Cisco Firepower sw:EthLanBorder:fsmProgr managed object property"
    ::= { cfprApSwEthLanBorderEntry 8 }

cfprApSwEthLanBorderFsmRmtInvErrCode OBJECT-TYPE
    SYNTAX       Gauge32
    MAX-ACCESS   read-only
    STATUS       current
    DESCRIPTION
        "Cisco Firepower sw:EthLanBorder:fsmRmtInvErrCode
        managed object property"
    ::= { cfprApSwEthLanBorderEntry 9 }

cfprApSwEthLanBorderFsmRmtInvErrDescr OBJECT-TYPE
    SYNTAX       SnmpAdminString
    MAX-ACCESS   read-only
    STATUS       current
    DESCRIPTION
        "Cisco Firepower sw:EthLanBorder:fsmRmtInvErrDescr
        managed object property"
    ::= { cfprApSwEthLanBorderEntry 10 }

cfprApSwEthLanBorderFsmRmtInvRslt OBJECT-TYPE
    SYNTAX       CfprApConditionRemoteInvRslt
    MAX-ACCESS   read-only
    STATUS       current
    DESCRIPTION
        "Cisco Firepower sw:EthLanBorder:fsmRmtInvRslt
        managed object property"
    ::= { cfprApSwEthLanBorderEntry 11 }

cfprApSwEthLanBorderFsmStageDescr OBJECT-TYPE
    SYNTAX       SnmpAdminString
    MAX-ACCESS   read-only
    STATUS       current
    DESCRIPTION
        "Cisco Firepower sw:EthLanBorder:fsmStageDescr
        managed object property"
    ::= { cfprApSwEthLanBorderEntry 12 }

cfprApSwEthLanBorderFsmStamp OBJECT-TYPE
    SYNTAX       DateAndTime
    MAX-ACCESS   read-only
    STATUS       current
    DESCRIPTION
        "Cisco Firepower sw:EthLanBorder:fsmStamp managed object property"
    ::= { cfprApSwEthLanBorderEntry 13 }

cfprApSwEthLanBorderFsmStatus OBJECT-TYPE
    SYNTAX       SnmpAdminString
    MAX-ACCESS   read-only
    STATUS       current
    DESCRIPTION
        "Cisco Firepower sw:EthLanBorder:fsmStatus managed
        object property"
    ::= { cfprApSwEthLanBorderEntry 14 }

cfprApSwEthLanBorderFsmTry OBJECT-TYPE
    SYNTAX       Gauge32
    MAX-ACCESS   read-only
    STATUS       current
    DESCRIPTION
        "Cisco Firepower sw:EthLanBorder:fsmTry managed object property"
    ::= { cfprApSwEthLanBorderEntry 15 }

cfprApSwEthLanBorderLocale OBJECT-TYPE
    SYNTAX       CfprApSwBorderDomainLocale
    MAX-ACCESS   read-only
    STATUS       current
    DESCRIPTION
        "Cisco Firepower sw:EthLanBorder:locale managed object property"
    ::= { cfprApSwEthLanBorderEntry 16 }

cfprApSwEthLanBorderName OBJECT-TYPE
    SYNTAX       SnmpAdminString
    MAX-ACCESS   read-only
    STATUS       current
    DESCRIPTION
        "Cisco Firepower sw:EthLanBorder:name managed object property"
    ::= { cfprApSwEthLanBorderEntry 17 }

cfprApSwEthLanBorderSwitchId OBJECT-TYPE
    SYNTAX       CfprApNetworkSwitchId
    MAX-ACCESS   read-only
    STATUS       current
    DESCRIPTION
        "Cisco Firepower sw:EthLanBorder:switchId managed object property"
    ::= { cfprApSwEthLanBorderEntry 18 }

cfprApSwEthLanBorderTransport OBJECT-TYPE
    SYNTAX       CfprApSwEthLanBorderTransport
    MAX-ACCESS   read-only
    STATUS       current
    DESCRIPTION
        "Cisco Firepower sw:EthLanBorder:transport managed
        object property"
    ::= { cfprApSwEthLanBorderEntry 19 }

cfprApSwEthLanBorderType OBJECT-TYPE
    SYNTAX       CfprApSwLanBorderType
    MAX-ACCESS   read-only
    STATUS       current
    DESCRIPTION
        "Cisco Firepower sw:EthLanBorder:type managed object property"
    ::= { cfprApSwEthLanBorderEntry 20 }

cfprApSwEthLanBorderUdldMsgInterval OBJECT-TYPE
    SYNTAX       Gauge32
    MAX-ACCESS   read-only
    STATUS       current
    DESCRIPTION
        "Cisco Firepower sw:EthLanBorder:udldMsgInterval
        managed object property"
    ::= { cfprApSwEthLanBorderEntry 21 }

cfprApSwEthLanBorderUdldRecoveryAction OBJECT-TYPE
    SYNTAX       CfprApFabricRecoveryAction
    MAX-ACCESS   read-only
    STATUS       current
    DESCRIPTION
        "Cisco Firepower sw:EthLanBorder:udldRecoveryAction
        managed object property"
    ::= { cfprApSwEthLanBorderEntry 22 }

cfprApSwEthLanBorderFsmTable OBJECT-TYPE
    SYNTAX           SEQUENCE OF CfprApSwEthLanBorderFsmEntry
    MAX-ACCESS       not-accessible
    STATUS           current
    DESCRIPTION
        "Cisco Firepower sw:EthLanBorderFsm managed object table"
    ::= { cfprApSwObjects 14 }

cfprApSwEthLanBorderFsmEntry OBJECT-TYPE
    SYNTAX           CfprApSwEthLanBorderFsmEntry
    MAX-ACCESS       not-accessible
    STATUS           current
    DESCRIPTION
        "Entry for the cfprApSwEthLanBorderFsmTable table."
    INDEX { cfprApSwEthLanBorderFsmInstanceId }
    ::= { cfprApSwEthLanBorderFsmTable 1 }

CfprApSwEthLanBorderFsmEntry ::= SEQUENCE {
    cfprApSwEthLanBorderFsmInstanceId                                CfprApManagedObjectId,
    cfprApSwEthLanBorderFsmDn                                        CfprApManagedObjectDn,
    cfprApSwEthLanBorderFsmRn                                        SnmpAdminString,
    cfprApSwEthLanBorderFsmCompletionTime                            DateAndTime,
    cfprApSwEthLanBorderFsmCurrentFsm                                CfprApSwEthLanBorderFsmCurrentFsm,
    cfprApSwEthLanBorderFsmDescrData                                 SnmpAdminString,
    cfprApSwEthLanBorderFsmFsmStatus                                 CfprApFsmFsmStageStatus,
    cfprApSwEthLanBorderFsmProgress                                  Gauge32,
    cfprApSwEthLanBorderFsmRmtErrCode                                Gauge32,
    cfprApSwEthLanBorderFsmRmtErrDescr                               SnmpAdminString,
    cfprApSwEthLanBorderFsmRmtRslt                                   CfprApConditionRemoteInvRslt
}

cfprApSwEthLanBorderFsmInstanceId OBJECT-TYPE
    SYNTAX       CfprApManagedObjectId
    MAX-ACCESS   not-accessible
    STATUS       current
    DESCRIPTION
        "Instance identifier of the managed object."
    ::= { cfprApSwEthLanBorderFsmEntry 1 }

cfprApSwEthLanBorderFsmDn OBJECT-TYPE
    SYNTAX       CfprApManagedObjectDn
    MAX-ACCESS   read-only
    STATUS       current
    DESCRIPTION
        "Cisco Firepower sw:EthLanBorderFsm:dn managed object property"
    ::= { cfprApSwEthLanBorderFsmEntry 2 }

cfprApSwEthLanBorderFsmRn OBJECT-TYPE
    SYNTAX       SnmpAdminString
    MAX-ACCESS   read-only
    STATUS       current
    DESCRIPTION
        "Cisco Firepower sw:EthLanBorderFsm:rn managed object property"
    ::= { cfprApSwEthLanBorderFsmEntry 3 }

cfprApSwEthLanBorderFsmCompletionTime OBJECT-TYPE
    SYNTAX       DateAndTime
    MAX-ACCESS   read-only
    STATUS       current
    DESCRIPTION
        "Cisco Firepower sw:EthLanBorderFsm:completionTime
        managed object property"
    ::= { cfprApSwEthLanBorderFsmEntry 4 }

cfprApSwEthLanBorderFsmCurrentFsm OBJECT-TYPE
    SYNTAX       CfprApSwEthLanBorderFsmCurrentFsm
    MAX-ACCESS   read-only
    STATUS       current
    DESCRIPTION
        "Cisco Firepower sw:EthLanBorderFsm:currentFsm
        managed object property"
    ::= { cfprApSwEthLanBorderFsmEntry 5 }

cfprApSwEthLanBorderFsmDescrData OBJECT-TYPE
    SYNTAX       SnmpAdminString
    MAX-ACCESS   read-only
    STATUS       current
    DESCRIPTION
        "Cisco Firepower sw:EthLanBorderFsm:descr managed object property"
    ::= { cfprApSwEthLanBorderFsmEntry 6 }

cfprApSwEthLanBorderFsmFsmStatus OBJECT-TYPE
    SYNTAX       CfprApFsmFsmStageStatus
    MAX-ACCESS   read-only
    STATUS       current
    DESCRIPTION
        "Cisco Firepower sw:EthLanBorderFsm:fsmStatus managed
        object property"
    ::= { cfprApSwEthLanBorderFsmEntry 7 }

cfprApSwEthLanBorderFsmProgress OBJECT-TYPE
    SYNTAX       Gauge32
    MAX-ACCESS   read-only
    STATUS       current
    DESCRIPTION
        "Cisco Firepower sw:EthLanBorderFsm:progress managed
        object property"
    ::= { cfprApSwEthLanBorderFsmEntry 8 }

cfprApSwEthLanBorderFsmRmtErrCode OBJECT-TYPE
    SYNTAX       Gauge32
    MAX-ACCESS   read-only
    STATUS       current
    DESCRIPTION
        "Cisco Firepower sw:EthLanBorderFsm:rmtErrCode
        managed object property"
    ::= { cfprApSwEthLanBorderFsmEntry 9 }

cfprApSwEthLanBorderFsmRmtErrDescr OBJECT-TYPE
    SYNTAX       SnmpAdminString
    MAX-ACCESS   read-only
    STATUS       current
    DESCRIPTION
        "Cisco Firepower sw:EthLanBorderFsm:rmtErrDescr
        managed object property"
    ::= { cfprApSwEthLanBorderFsmEntry 10 }

cfprApSwEthLanBorderFsmRmtRslt OBJECT-TYPE
    SYNTAX       CfprApConditionRemoteInvRslt
    MAX-ACCESS   read-only
    STATUS       current
    DESCRIPTION
        "Cisco Firepower sw:EthLanBorderFsm:rmtRslt managed
        object property"
    ::= { cfprApSwEthLanBorderFsmEntry 11 }

cfprApSwEthLanBorderFsmStageTable OBJECT-TYPE
    SYNTAX           SEQUENCE OF CfprApSwEthLanBorderFsmStageEntry
    MAX-ACCESS       not-accessible
    STATUS           current
    DESCRIPTION
        "Cisco Firepower sw:EthLanBorderFsmStage managed object table"
    ::= { cfprApSwObjects 15 }

cfprApSwEthLanBorderFsmStageEntry OBJECT-TYPE
    SYNTAX           CfprApSwEthLanBorderFsmStageEntry
    MAX-ACCESS       not-accessible
    STATUS           current
    DESCRIPTION
        "Entry for the cfprApSwEthLanBorderFsmStageTable table."
    INDEX { cfprApSwEthLanBorderFsmStageInstanceId }
    ::= { cfprApSwEthLanBorderFsmStageTable 1 }

CfprApSwEthLanBorderFsmStageEntry ::= SEQUENCE {
    cfprApSwEthLanBorderFsmStageInstanceId                           CfprApManagedObjectId,
    cfprApSwEthLanBorderFsmStageDn                                   CfprApManagedObjectDn,
    cfprApSwEthLanBorderFsmStageRn                                   SnmpAdminString,
    cfprApSwEthLanBorderFsmStageDescrData                            SnmpAdminString,
    cfprApSwEthLanBorderFsmStageLastUpdateTime                       DateAndTime,
    cfprApSwEthLanBorderFsmStageName                                 CfprApSwEthLanBorderFsmStageName,
    cfprApSwEthLanBorderFsmStageOrder                                Gauge32,
    cfprApSwEthLanBorderFsmStageRetry                                Gauge32,
    cfprApSwEthLanBorderFsmStageStageStatus                          CfprApFsmFsmStageStatus
}

cfprApSwEthLanBorderFsmStageInstanceId OBJECT-TYPE
    SYNTAX       CfprApManagedObjectId
    MAX-ACCESS   not-accessible
    STATUS       current
    DESCRIPTION
        "Instance identifier of the managed object."
    ::= { cfprApSwEthLanBorderFsmStageEntry 1 }

cfprApSwEthLanBorderFsmStageDn OBJECT-TYPE
    SYNTAX       CfprApManagedObjectDn
    MAX-ACCESS   read-only
    STATUS       current
    DESCRIPTION
        "Cisco Firepower sw:EthLanBorderFsmStage:dn managed
        object property"
    ::= { cfprApSwEthLanBorderFsmStageEntry 2 }

cfprApSwEthLanBorderFsmStageRn OBJECT-TYPE
    SYNTAX       SnmpAdminString
    MAX-ACCESS   read-only
    STATUS       current
    DESCRIPTION
        "Cisco Firepower sw:EthLanBorderFsmStage:rn managed
        object property"
    ::= { cfprApSwEthLanBorderFsmStageEntry 3 }

cfprApSwEthLanBorderFsmStageDescrData OBJECT-TYPE
    SYNTAX       SnmpAdminString
    MAX-ACCESS   read-only
    STATUS       current
    DESCRIPTION
        "Cisco Firepower sw:EthLanBorderFsmStage:descr
        managed object property"
    ::= { cfprApSwEthLanBorderFsmStageEntry 4 }

cfprApSwEthLanBorderFsmStageLastUpdateTime OBJECT-TYPE
    SYNTAX       DateAndTime
    MAX-ACCESS   read-only
    STATUS       current
    DESCRIPTION
        "Cisco Firepower sw:EthLanBorderFsmStage:lastUpdateTime
        managed object property"
    ::= { cfprApSwEthLanBorderFsmStageEntry 5 }

cfprApSwEthLanBorderFsmStageName OBJECT-TYPE
    SYNTAX       CfprApSwEthLanBorderFsmStageName
    MAX-ACCESS   read-only
    STATUS       current
    DESCRIPTION
        "Cisco Firepower sw:EthLanBorderFsmStage:name managed
        object property"
    ::= { cfprApSwEthLanBorderFsmStageEntry 6 }

cfprApSwEthLanBorderFsmStageOrder OBJECT-TYPE
    SYNTAX       Gauge32
    MAX-ACCESS   read-only
    STATUS       current
    DESCRIPTION
        "Cisco Firepower sw:EthLanBorderFsmStage:order
        managed object property"
    ::= { cfprApSwEthLanBorderFsmStageEntry 7 }

cfprApSwEthLanBorderFsmStageRetry OBJECT-TYPE
    SYNTAX       Gauge32
    MAX-ACCESS   read-only
    STATUS       current
    DESCRIPTION
        "Cisco Firepower sw:EthLanBorderFsmStage:retry
        managed object property"
    ::= { cfprApSwEthLanBorderFsmStageEntry 8 }

cfprApSwEthLanBorderFsmStageStageStatus OBJECT-TYPE
    SYNTAX       CfprApFsmFsmStageStatus
    MAX-ACCESS   read-only
    STATUS       current
    DESCRIPTION
        "Cisco Firepower sw:EthLanBorderFsmStage:stageStatus
        managed object property"
    ::= { cfprApSwEthLanBorderFsmStageEntry 9 }

cfprApSwEthLanBorderFsmTaskTable OBJECT-TYPE
    SYNTAX           SEQUENCE OF CfprApSwEthLanBorderFsmTaskEntry
    MAX-ACCESS       not-accessible
    STATUS           current
    DESCRIPTION
        "Cisco Firepower sw:EthLanBorderFsmTask managed object table"
    ::= { cfprApSwObjects 16 }

cfprApSwEthLanBorderFsmTaskEntry OBJECT-TYPE
    SYNTAX           CfprApSwEthLanBorderFsmTaskEntry
    MAX-ACCESS       not-accessible
    STATUS           current
    DESCRIPTION
        "Entry for the cfprApSwEthLanBorderFsmTaskTable table."
    INDEX { cfprApSwEthLanBorderFsmTaskInstanceId }
    ::= { cfprApSwEthLanBorderFsmTaskTable 1 }

CfprApSwEthLanBorderFsmTaskEntry ::= SEQUENCE {
    cfprApSwEthLanBorderFsmTaskInstanceId                            CfprApManagedObjectId,
    cfprApSwEthLanBorderFsmTaskDn                                    CfprApManagedObjectDn,
    cfprApSwEthLanBorderFsmTaskRn                                    SnmpAdminString,
    cfprApSwEthLanBorderFsmTaskCompletion                            CfprApFsmCompletion,
    cfprApSwEthLanBorderFsmTaskFlags                                 CfprApSwEthLanBorderFsmTaskFlags,
    cfprApSwEthLanBorderFsmTaskItem                                  CfprApSwEthLanBorderFsmTaskItem,
    cfprApSwEthLanBorderFsmTaskSeqId                                 Gauge32
}

cfprApSwEthLanBorderFsmTaskInstanceId OBJECT-TYPE
    SYNTAX       CfprApManagedObjectId
    MAX-ACCESS   not-accessible
    STATUS       current
    DESCRIPTION
        "Instance identifier of the managed object."
    ::= { cfprApSwEthLanBorderFsmTaskEntry 1 }

cfprApSwEthLanBorderFsmTaskDn OBJECT-TYPE
    SYNTAX       CfprApManagedObjectDn
    MAX-ACCESS   read-only
    STATUS       current
    DESCRIPTION
        "Cisco Firepower sw:EthLanBorderFsmTask:dn managed
        object property"
    ::= { cfprApSwEthLanBorderFsmTaskEntry 2 }

cfprApSwEthLanBorderFsmTaskRn OBJECT-TYPE
    SYNTAX       SnmpAdminString
    MAX-ACCESS   read-only
    STATUS       current
    DESCRIPTION
        "Cisco Firepower sw:EthLanBorderFsmTask:rn managed
        object property"
    ::= { cfprApSwEthLanBorderFsmTaskEntry 3 }

cfprApSwEthLanBorderFsmTaskCompletion OBJECT-TYPE
    SYNTAX       CfprApFsmCompletion
    MAX-ACCESS   read-only
    STATUS       current
    DESCRIPTION
        "Cisco Firepower sw:EthLanBorderFsmTask:completion
        managed object property"
    ::= { cfprApSwEthLanBorderFsmTaskEntry 4 }

cfprApSwEthLanBorderFsmTaskFlags OBJECT-TYPE
    SYNTAX       CfprApSwEthLanBorderFsmTaskFlags
    MAX-ACCESS   read-only
    STATUS       current
    DESCRIPTION
        "Cisco Firepower sw:EthLanBorderFsmTask:flags managed
        object property"
    ::= { cfprApSwEthLanBorderFsmTaskEntry 5 }

cfprApSwEthLanBorderFsmTaskItem OBJECT-TYPE
    SYNTAX       CfprApSwEthLanBorderFsmTaskItem
    MAX-ACCESS   read-only
    STATUS       current
    DESCRIPTION
        "Cisco Firepower sw:EthLanBorderFsmTask:item managed
        object property"
    ::= { cfprApSwEthLanBorderFsmTaskEntry 6 }

cfprApSwEthLanBorderFsmTaskSeqId OBJECT-TYPE
    SYNTAX       Gauge32
    MAX-ACCESS   read-only
    STATUS       current
    DESCRIPTION
        "Cisco Firepower sw:EthLanBorderFsmTask:seqId managed
        object property"
    ::= { cfprApSwEthLanBorderFsmTaskEntry 7 }

cfprApSwEthLanEpTable OBJECT-TYPE
    SYNTAX           SEQUENCE OF CfprApSwEthLanEpEntry
    MAX-ACCESS       not-accessible
    STATUS           current
    DESCRIPTION
        "Cisco Firepower sw:EthLanEp managed object table"
    ::= { cfprApSwObjects 17 }

cfprApSwEthLanEpEntry OBJECT-TYPE
    SYNTAX           CfprApSwEthLanEpEntry
    MAX-ACCESS       not-accessible
    STATUS           current
    DESCRIPTION
        "Entry for the cfprApSwEthLanEpTable table."
    INDEX { cfprApSwEthLanEpInstanceId }
    ::= { cfprApSwEthLanEpTable 1 }

CfprApSwEthLanEpEntry ::= SEQUENCE {
    cfprApSwEthLanEpInstanceId                                       CfprApManagedObjectId,
    cfprApSwEthLanEpDn                                               CfprApManagedObjectDn,
    cfprApSwEthLanEpRn                                               SnmpAdminString,
    cfprApSwEthLanEpAdminDuplex                                      CfprApPortDuplex,
    cfprApSwEthLanEpAdminSpeed                                       CfprApPortEthSpeed,
    cfprApSwEthLanEpAdminState                                       CfprApFabricAdminState,
    cfprApSwEthLanEpAggrPortId                                       Gauge32,
    cfprApSwEthLanEpAutoNeg                                          TruthValue,
    cfprApSwEthLanEpChassisId                                        Gauge32,
    cfprApSwEthLanEpDtagVlan                                         Gauge32,
    cfprApSwEthLanEpEpDn                                             SnmpAdminString,
    cfprApSwEthLanEpFabRole                                          CfprApSwFabricRole,
    cfprApSwEthLanEpIfRole                                           CfprApSwLanEpIfRole,
    cfprApSwEthLanEpIfType                                           CfprApSwPIoEpIfType,
    cfprApSwEthLanEpLc                                               CfprApSwPIoEpLc,
    cfprApSwEthLanEpLocale                                           CfprApSwBorderEpLocale,
    cfprApSwEthLanEpMtu                                              Gauge32,
    cfprApSwEthLanEpName                                             SnmpAdminString,
    cfprApSwEthLanEpPcId                                             Gauge32,
    cfprApSwEthLanEpPeerAggrPortId                                   Gauge32,
    cfprApSwEthLanEpPeerChassisId                                    Gauge32,
    cfprApSwEthLanEpPeerDn                                           SnmpAdminString,
    cfprApSwEthLanEpPeerPortId                                       Gauge32,
    cfprApSwEthLanEpPeerSlotId                                       Gauge32,
    cfprApSwEthLanEpPortId                                           Gauge32,
    cfprApSwEthLanEpPriorityFlowCtrl                                 CfprApFlowctrlPriorityPause,
    cfprApSwEthLanEpQosPrio                                          CfprApFabricQosPrio,
    cfprApSwEthLanEpRecvFlowCtrl                                     CfprApFlowctrlFlowControl,
    cfprApSwEthLanEpSendFlowCtrl                                     CfprApFlowctrlFlowControl,
    cfprApSwEthLanEpSlotId                                           Gauge32,
    cfprApSwEthLanEpSwitchId                                         CfprApNetworkSwitchId,
    cfprApSwEthLanEpTransport                                        CfprApSwEthLanEpTransport,
    cfprApSwEthLanEpType                                             CfprApSwLanEpType,
    cfprApSwEthLanEpUdldAdminState                                   CfprApSwEthLanEpUdldAdminState,
    cfprApSwEthLanEpUdldMode                                         CfprApSwEthLanEpUdldMode
}

cfprApSwEthLanEpInstanceId OBJECT-TYPE
    SYNTAX       CfprApManagedObjectId
    MAX-ACCESS   not-accessible
    STATUS       current
    DESCRIPTION
        "Instance identifier of the managed object."
    ::= { cfprApSwEthLanEpEntry 1 }

cfprApSwEthLanEpDn OBJECT-TYPE
    SYNTAX       CfprApManagedObjectDn
    MAX-ACCESS   read-only
    STATUS       current
    DESCRIPTION
        "Cisco Firepower sw:EthLanEp:dn managed object property"
    ::= { cfprApSwEthLanEpEntry 2 }

cfprApSwEthLanEpRn OBJECT-TYPE
    SYNTAX       SnmpAdminString
    MAX-ACCESS   read-only
    STATUS       current
    DESCRIPTION
        "Cisco Firepower sw:EthLanEp:rn managed object property"
    ::= { cfprApSwEthLanEpEntry 3 }

cfprApSwEthLanEpAdminDuplex OBJECT-TYPE
    SYNTAX       CfprApPortDuplex
    MAX-ACCESS   read-only
    STATUS       current
    DESCRIPTION
        "Cisco Firepower sw:EthLanEp:adminDuplex managed object property"
    ::= { cfprApSwEthLanEpEntry 4 }

cfprApSwEthLanEpAdminSpeed OBJECT-TYPE
    SYNTAX       CfprApPortEthSpeed
    MAX-ACCESS   read-only
    STATUS       current
    DESCRIPTION
        "Cisco Firepower sw:EthLanEp:adminSpeed managed object property"
    ::= { cfprApSwEthLanEpEntry 5 }

cfprApSwEthLanEpAdminState OBJECT-TYPE
    SYNTAX       CfprApFabricAdminState
    MAX-ACCESS   read-only
    STATUS       current
    DESCRIPTION
        "Cisco Firepower sw:EthLanEp:adminState managed object property"
    ::= { cfprApSwEthLanEpEntry 6 }

cfprApSwEthLanEpAggrPortId OBJECT-TYPE
    SYNTAX       Gauge32
    MAX-ACCESS   read-only
    STATUS       current
    DESCRIPTION
        "Cisco Firepower sw:EthLanEp:aggrPortId managed object property"
    ::= { cfprApSwEthLanEpEntry 7 }

cfprApSwEthLanEpAutoNeg OBJECT-TYPE
    SYNTAX       TruthValue
    MAX-ACCESS   read-only
    STATUS       current
    DESCRIPTION
        "Cisco Firepower sw:EthLanEp:autoNeg managed object property"
    ::= { cfprApSwEthLanEpEntry 8 }

cfprApSwEthLanEpChassisId OBJECT-TYPE
    SYNTAX       Gauge32
    MAX-ACCESS   read-only
    STATUS       current
    DESCRIPTION
        "Cisco Firepower sw:EthLanEp:chassisId managed object property"
    ::= { cfprApSwEthLanEpEntry 9 }

cfprApSwEthLanEpDtagVlan OBJECT-TYPE
    SYNTAX       Gauge32
    MAX-ACCESS   read-only
    STATUS       current
    DESCRIPTION
        "Cisco Firepower sw:EthLanEp:dtagVlan managed object property"
    ::= { cfprApSwEthLanEpEntry 10 }

cfprApSwEthLanEpEpDn OBJECT-TYPE
    SYNTAX       SnmpAdminString
    MAX-ACCESS   read-only
    STATUS       current
    DESCRIPTION
        "Cisco Firepower sw:EthLanEp:epDn managed object property"
    ::= { cfprApSwEthLanEpEntry 11 }

cfprApSwEthLanEpFabRole OBJECT-TYPE
    SYNTAX       CfprApSwFabricRole
    MAX-ACCESS   read-only
    STATUS       current
    DESCRIPTION
        "Cisco Firepower sw:EthLanEp:fabRole managed object property"
    ::= { cfprApSwEthLanEpEntry 12 }

cfprApSwEthLanEpIfRole OBJECT-TYPE
    SYNTAX       CfprApSwLanEpIfRole
    MAX-ACCESS   read-only
    STATUS       current
    DESCRIPTION
        "Cisco Firepower sw:EthLanEp:ifRole managed object property"
    ::= { cfprApSwEthLanEpEntry 14 }

cfprApSwEthLanEpIfType OBJECT-TYPE
    SYNTAX       CfprApSwPIoEpIfType
    MAX-ACCESS   read-only
    STATUS       current
    DESCRIPTION
        "Cisco Firepower sw:EthLanEp:ifType managed object property"
    ::= { cfprApSwEthLanEpEntry 15 }

cfprApSwEthLanEpLc OBJECT-TYPE
    SYNTAX       CfprApSwPIoEpLc
    MAX-ACCESS   read-only
    STATUS       current
    DESCRIPTION
        "Cisco Firepower sw:EthLanEp:lc managed object property"
    ::= { cfprApSwEthLanEpEntry 16 }

cfprApSwEthLanEpLocale OBJECT-TYPE
    SYNTAX       CfprApSwBorderEpLocale
    MAX-ACCESS   read-only
    STATUS       current
    DESCRIPTION
        "Cisco Firepower sw:EthLanEp:locale managed object property"
    ::= { cfprApSwEthLanEpEntry 17 }

cfprApSwEthLanEpMtu OBJECT-TYPE
    SYNTAX       Gauge32
    MAX-ACCESS   read-only
    STATUS       current
    DESCRIPTION
        "Cisco Firepower sw:EthLanEp:mtu managed object property"
    ::= { cfprApSwEthLanEpEntry 18 }

cfprApSwEthLanEpName OBJECT-TYPE
    SYNTAX       SnmpAdminString
    MAX-ACCESS   read-only
    STATUS       current
    DESCRIPTION
        "Cisco Firepower sw:EthLanEp:name managed object property"
    ::= { cfprApSwEthLanEpEntry 19 }

cfprApSwEthLanEpPcId OBJECT-TYPE
    SYNTAX       Gauge32
    MAX-ACCESS   read-only
    STATUS       current
    DESCRIPTION
        "Cisco Firepower sw:EthLanEp:pcId managed object property"
    ::= { cfprApSwEthLanEpEntry 20 }

cfprApSwEthLanEpPeerAggrPortId OBJECT-TYPE
    SYNTAX       Gauge32
    MAX-ACCESS   read-only
    STATUS       current
    DESCRIPTION
        "Cisco Firepower sw:EthLanEp:peerAggrPortId managed
        object property"
    ::= { cfprApSwEthLanEpEntry 21 }

cfprApSwEthLanEpPeerChassisId OBJECT-TYPE
    SYNTAX       Gauge32
    MAX-ACCESS   read-only
    STATUS       current
    DESCRIPTION
        "Cisco Firepower sw:EthLanEp:peerChassisId managed
        object property"
    ::= { cfprApSwEthLanEpEntry 22 }

cfprApSwEthLanEpPeerDn OBJECT-TYPE
    SYNTAX       SnmpAdminString
    MAX-ACCESS   read-only
    STATUS       current
    DESCRIPTION
        "Cisco Firepower sw:EthLanEp:peerDn managed object property"
    ::= { cfprApSwEthLanEpEntry 23 }

cfprApSwEthLanEpPeerPortId OBJECT-TYPE
    SYNTAX       Gauge32
    MAX-ACCESS   read-only
    STATUS       current
    DESCRIPTION
        "Cisco Firepower sw:EthLanEp:peerPortId managed object property"
    ::= { cfprApSwEthLanEpEntry 24 }

cfprApSwEthLanEpPeerSlotId OBJECT-TYPE
    SYNTAX       Gauge32
    MAX-ACCESS   read-only
    STATUS       current
    DESCRIPTION
        "Cisco Firepower sw:EthLanEp:peerSlotId managed object property"
    ::= { cfprApSwEthLanEpEntry 25 }

cfprApSwEthLanEpPortId OBJECT-TYPE
    SYNTAX       Gauge32
    MAX-ACCESS   read-only
    STATUS       current
    DESCRIPTION
        "Cisco Firepower sw:EthLanEp:portId managed object property"
    ::= { cfprApSwEthLanEpEntry 26 }

cfprApSwEthLanEpPriorityFlowCtrl OBJECT-TYPE
    SYNTAX       CfprApFlowctrlPriorityPause
    MAX-ACCESS   read-only
    STATUS       current
    DESCRIPTION
        "Cisco Firepower sw:EthLanEp:priorityFlowCtrl managed
        object property"
    ::= { cfprApSwEthLanEpEntry 27 }

cfprApSwEthLanEpQosPrio OBJECT-TYPE
    SYNTAX       CfprApFabricQosPrio
    MAX-ACCESS   read-only
    STATUS       current
    DESCRIPTION
        "Cisco Firepower sw:EthLanEp:qosPrio managed object property"
    ::= { cfprApSwEthLanEpEntry 28 }

cfprApSwEthLanEpRecvFlowCtrl OBJECT-TYPE
    SYNTAX       CfprApFlowctrlFlowControl
    MAX-ACCESS   read-only
    STATUS       current
    DESCRIPTION
        "Cisco Firepower sw:EthLanEp:recvFlowCtrl managed object property"
    ::= { cfprApSwEthLanEpEntry 29 }

cfprApSwEthLanEpSendFlowCtrl OBJECT-TYPE
    SYNTAX       CfprApFlowctrlFlowControl
    MAX-ACCESS   read-only
    STATUS       current
    DESCRIPTION
        "Cisco Firepower sw:EthLanEp:sendFlowCtrl managed object property"
    ::= { cfprApSwEthLanEpEntry 30 }

cfprApSwEthLanEpSlotId OBJECT-TYPE
    SYNTAX       Gauge32
    MAX-ACCESS   read-only
    STATUS       current
    DESCRIPTION
        "Cisco Firepower sw:EthLanEp:slotId managed object property"
    ::= { cfprApSwEthLanEpEntry 31 }

cfprApSwEthLanEpSwitchId OBJECT-TYPE
    SYNTAX       CfprApNetworkSwitchId
    MAX-ACCESS   read-only
    STATUS       current
    DESCRIPTION
        "Cisco Firepower sw:EthLanEp:switchId managed object property"
    ::= { cfprApSwEthLanEpEntry 32 }

cfprApSwEthLanEpTransport OBJECT-TYPE
    SYNTAX       CfprApSwEthLanEpTransport
    MAX-ACCESS   read-only
    STATUS       current
    DESCRIPTION
        "Cisco Firepower sw:EthLanEp:transport managed object property"
    ::= { cfprApSwEthLanEpEntry 33 }

cfprApSwEthLanEpType OBJECT-TYPE
    SYNTAX       CfprApSwLanEpType
    MAX-ACCESS   read-only
    STATUS       current
    DESCRIPTION
        "Cisco Firepower sw:EthLanEp:type managed object property"
    ::= { cfprApSwEthLanEpEntry 34 }

cfprApSwEthLanEpUdldAdminState OBJECT-TYPE
    SYNTAX       CfprApSwEthLanEpUdldAdminState
    MAX-ACCESS   read-only
    STATUS       current
    DESCRIPTION
        "Cisco Firepower sw:EthLanEp:udldAdminState managed
        object property"
    ::= { cfprApSwEthLanEpEntry 35 }

cfprApSwEthLanEpUdldMode OBJECT-TYPE
    SYNTAX       CfprApSwEthLanEpUdldMode
    MAX-ACCESS   read-only
    STATUS       current
    DESCRIPTION
        "Cisco Firepower sw:EthLanEp:udldMode managed object property"
    ::= { cfprApSwEthLanEpEntry 36 }

cfprApSwEthLanMonTable OBJECT-TYPE
    SYNTAX           SEQUENCE OF CfprApSwEthLanMonEntry
    MAX-ACCESS       not-accessible
    STATUS           current
    DESCRIPTION
        "Cisco Firepower sw:EthLanMon managed object table"
    ::= { cfprApSwObjects 22 }

cfprApSwEthLanMonEntry OBJECT-TYPE
    SYNTAX           CfprApSwEthLanMonEntry
    MAX-ACCESS       not-accessible
    STATUS           current
    DESCRIPTION
        "Entry for the cfprApSwEthLanMonTable table."
    INDEX { cfprApSwEthLanMonInstanceId }
    ::= { cfprApSwEthLanMonTable 1 }

CfprApSwEthLanMonEntry ::= SEQUENCE {
    cfprApSwEthLanMonInstanceId                                      CfprApManagedObjectId,
    cfprApSwEthLanMonDn                                              CfprApManagedObjectDn,
    cfprApSwEthLanMonRn                                              SnmpAdminString,
    cfprApSwEthLanMonLocale                                          CfprApSwMonDomainLocale,
    cfprApSwEthLanMonName                                            SnmpAdminString,
    cfprApSwEthLanMonSwitchId                                        CfprApNetworkSwitchId,
    cfprApSwEthLanMonTransport                                       CfprApSwEthLanMonTransport,
    cfprApSwEthLanMonType                                            CfprApSwLanMonType
}

cfprApSwEthLanMonInstanceId OBJECT-TYPE
    SYNTAX       CfprApManagedObjectId
    MAX-ACCESS   not-accessible
    STATUS       current
    DESCRIPTION
        "Instance identifier of the managed object."
    ::= { cfprApSwEthLanMonEntry 1 }

cfprApSwEthLanMonDn OBJECT-TYPE
    SYNTAX       CfprApManagedObjectDn
    MAX-ACCESS   read-only
    STATUS       current
    DESCRIPTION
        "Cisco Firepower sw:EthLanMon:dn managed object property"
    ::= { cfprApSwEthLanMonEntry 2 }

cfprApSwEthLanMonRn OBJECT-TYPE
    SYNTAX       SnmpAdminString
    MAX-ACCESS   read-only
    STATUS       current
    DESCRIPTION
        "Cisco Firepower sw:EthLanMon:rn managed object property"
    ::= { cfprApSwEthLanMonEntry 3 }

cfprApSwEthLanMonLocale OBJECT-TYPE
    SYNTAX       CfprApSwMonDomainLocale
    MAX-ACCESS   read-only
    STATUS       current
    DESCRIPTION
        "Cisco Firepower sw:EthLanMon:locale managed object property"
    ::= { cfprApSwEthLanMonEntry 4 }

cfprApSwEthLanMonName OBJECT-TYPE
    SYNTAX       SnmpAdminString
    MAX-ACCESS   read-only
    STATUS       current
    DESCRIPTION
        "Cisco Firepower sw:EthLanMon:name managed object property"
    ::= { cfprApSwEthLanMonEntry 5 }

cfprApSwEthLanMonSwitchId OBJECT-TYPE
    SYNTAX       CfprApNetworkSwitchId
    MAX-ACCESS   read-only
    STATUS       current
    DESCRIPTION
        "Cisco Firepower sw:EthLanMon:switchId managed object property"
    ::= { cfprApSwEthLanMonEntry 6 }

cfprApSwEthLanMonTransport OBJECT-TYPE
    SYNTAX       CfprApSwEthLanMonTransport
    MAX-ACCESS   read-only
    STATUS       current
    DESCRIPTION
        "Cisco Firepower sw:EthLanMon:transport managed object property"
    ::= { cfprApSwEthLanMonEntry 7 }

cfprApSwEthLanMonType OBJECT-TYPE
    SYNTAX       CfprApSwLanMonType
    MAX-ACCESS   read-only
    STATUS       current
    DESCRIPTION
        "Cisco Firepower sw:EthLanMon:type managed object property"
    ::= { cfprApSwEthLanMonEntry 8 }

cfprApSwEthLanPcTable OBJECT-TYPE
    SYNTAX           SEQUENCE OF CfprApSwEthLanPcEntry
    MAX-ACCESS       not-accessible
    STATUS           current
    DESCRIPTION
        "Cisco Firepower sw:EthLanPc managed object table"
    ::= { cfprApSwObjects 23 }

cfprApSwEthLanPcEntry OBJECT-TYPE
    SYNTAX           CfprApSwEthLanPcEntry
    MAX-ACCESS       not-accessible
    STATUS           current
    DESCRIPTION
        "Entry for the cfprApSwEthLanPcTable table."
    INDEX { cfprApSwEthLanPcInstanceId }
    ::= { cfprApSwEthLanPcTable 1 }

CfprApSwEthLanPcEntry ::= SEQUENCE {
    cfprApSwEthLanPcInstanceId                                       CfprApManagedObjectId,
    cfprApSwEthLanPcDn                                               CfprApManagedObjectDn,
    cfprApSwEthLanPcRn                                               SnmpAdminString,
    cfprApSwEthLanPcAdminDuplex                                      CfprApPortDuplex,
    cfprApSwEthLanPcAdminSpeed                                       CfprApPortEthSpeed,
    cfprApSwEthLanPcAdminState                                       CfprApFabricAdminState,
    cfprApSwEthLanPcAutoNeg                                          TruthValue,
    cfprApSwEthLanPcCluChassisId                                     Gauge32,
    cfprApSwEthLanPcClusterName                                      SnmpAdminString,
    cfprApSwEthLanPcDtagVlan                                         Gauge32,
    cfprApSwEthLanPcEpDn                                             SnmpAdminString,
    cfprApSwEthLanPcFabRole                                          CfprApSwFabricRole,
    cfprApSwEthLanPcIfRole                                           CfprApSwLanPcIfRole,
    cfprApSwEthLanPcIfType                                           CfprApSwCIoEpIfType,
    cfprApSwEthLanPcLacpDetach                                       CfprApSwAdminState,
    cfprApSwEthLanPcLacpFastTimer                                    TruthValue,
    cfprApSwEthLanPcLacpMode                                         CfprApFabricLacpMode,
    cfprApSwEthLanPcLacpSuspendIndividual                            TruthValue,
    cfprApSwEthLanPcLocale                                           CfprApSwBorderPcLocale,
    cfprApSwEthLanPcMonTrafDir                                       CfprApFabricTrafficDirection,
    cfprApSwEthLanPcMtu                                              Gauge32,
    cfprApSwEthLanPcName                                             SnmpAdminString,
    cfprApSwEthLanPcPeerDn                                           SnmpAdminString,
    cfprApSwEthLanPcPortId                                           Gauge32,
    cfprApSwEthLanPcPriorityFlowCtrl                                 CfprApFlowctrlPriorityPause,
    cfprApSwEthLanPcQosPrio                                          CfprApFabricQosPrio,
    cfprApSwEthLanPcRecvFlowCtrl                                     CfprApFlowctrlFlowControl,
    cfprApSwEthLanPcSendFlowCtrl                                     CfprApFlowctrlFlowControl,
    cfprApSwEthLanPcSpannedCluster                                   CfprApFabricSpannedCluster,
    cfprApSwEthLanPcSwitchId                                         CfprApNetworkSwitchId,
    cfprApSwEthLanPcTransport                                        CfprApSwEthLanPcTransport,
    cfprApSwEthLanPcType                                             CfprApSwLanPcType
}

cfprApSwEthLanPcInstanceId OBJECT-TYPE
    SYNTAX       CfprApManagedObjectId
    MAX-ACCESS   not-accessible
    STATUS       current
    DESCRIPTION
        "Instance identifier of the managed object."
    ::= { cfprApSwEthLanPcEntry 1 }

cfprApSwEthLanPcDn OBJECT-TYPE
    SYNTAX       CfprApManagedObjectDn
    MAX-ACCESS   read-only
    STATUS       current
    DESCRIPTION
        "Cisco Firepower sw:EthLanPc:dn managed object property"
    ::= { cfprApSwEthLanPcEntry 2 }

cfprApSwEthLanPcRn OBJECT-TYPE
    SYNTAX       SnmpAdminString
    MAX-ACCESS   read-only
    STATUS       current
    DESCRIPTION
        "Cisco Firepower sw:EthLanPc:rn managed object property"
    ::= { cfprApSwEthLanPcEntry 3 }

cfprApSwEthLanPcAdminDuplex OBJECT-TYPE
    SYNTAX       CfprApPortDuplex
    MAX-ACCESS   read-only
    STATUS       current
    DESCRIPTION
        "Cisco Firepower sw:EthLanPc:adminDuplex managed object property"
    ::= { cfprApSwEthLanPcEntry 4 }

cfprApSwEthLanPcAdminSpeed OBJECT-TYPE
    SYNTAX       CfprApPortEthSpeed
    MAX-ACCESS   read-only
    STATUS       current
    DESCRIPTION
        "Cisco Firepower sw:EthLanPc:adminSpeed managed object property"
    ::= { cfprApSwEthLanPcEntry 5 }

cfprApSwEthLanPcAdminState OBJECT-TYPE
    SYNTAX       CfprApFabricAdminState
    MAX-ACCESS   read-only
    STATUS       current
    DESCRIPTION
        "Cisco Firepower sw:EthLanPc:adminState managed object property"
    ::= { cfprApSwEthLanPcEntry 6 }

cfprApSwEthLanPcAutoNeg OBJECT-TYPE
    SYNTAX       TruthValue
    MAX-ACCESS   read-only
    STATUS       current
    DESCRIPTION
        "Cisco Firepower sw:EthLanPc:autoNeg managed object property"
    ::= { cfprApSwEthLanPcEntry 7 }

cfprApSwEthLanPcCluChassisId OBJECT-TYPE
    SYNTAX       Gauge32
    MAX-ACCESS   read-only
    STATUS       current
    DESCRIPTION
        "Cisco Firepower sw:EthLanPc:cluChassisId managed object property"
    ::= { cfprApSwEthLanPcEntry 8 }

cfprApSwEthLanPcClusterName OBJECT-TYPE
    SYNTAX       SnmpAdminString
    MAX-ACCESS   read-only
    STATUS       current
    DESCRIPTION
        "Cisco Firepower sw:EthLanPc:clusterName managed object property"
    ::= { cfprApSwEthLanPcEntry 9 }

cfprApSwEthLanPcDtagVlan OBJECT-TYPE
    SYNTAX       Gauge32
    MAX-ACCESS   read-only
    STATUS       current
    DESCRIPTION
        "Cisco Firepower sw:EthLanPc:dtagVlan managed object property"
    ::= { cfprApSwEthLanPcEntry 10 }

cfprApSwEthLanPcEpDn OBJECT-TYPE
    SYNTAX       SnmpAdminString
    MAX-ACCESS   read-only
    STATUS       current
    DESCRIPTION
        "Cisco Firepower sw:EthLanPc:epDn managed object property"
    ::= { cfprApSwEthLanPcEntry 11 }

cfprApSwEthLanPcFabRole OBJECT-TYPE
    SYNTAX       CfprApSwFabricRole
    MAX-ACCESS   read-only
    STATUS       current
    DESCRIPTION
        "Cisco Firepower sw:EthLanPc:fabRole managed object property"
    ::= { cfprApSwEthLanPcEntry 12 }

cfprApSwEthLanPcIfRole OBJECT-TYPE
    SYNTAX       CfprApSwLanPcIfRole
    MAX-ACCESS   read-only
    STATUS       current
    DESCRIPTION
        "Cisco Firepower sw:EthLanPc:ifRole managed object property"
    ::= { cfprApSwEthLanPcEntry 14 }

cfprApSwEthLanPcIfType OBJECT-TYPE
    SYNTAX       CfprApSwCIoEpIfType
    MAX-ACCESS   read-only
    STATUS       current
    DESCRIPTION
        "Cisco Firepower sw:EthLanPc:ifType managed object property"
    ::= { cfprApSwEthLanPcEntry 15 }

cfprApSwEthLanPcLacpDetach OBJECT-TYPE
    SYNTAX       CfprApSwAdminState
    MAX-ACCESS   read-only
    STATUS       current
    DESCRIPTION
        "Cisco Firepower sw:EthLanPc:lacpDetach managed object property"
    ::= { cfprApSwEthLanPcEntry 16 }

cfprApSwEthLanPcLacpFastTimer OBJECT-TYPE
    SYNTAX       TruthValue
    MAX-ACCESS   read-only
    STATUS       current
    DESCRIPTION
        "Cisco Firepower sw:EthLanPc:lacpFastTimer managed
        object property"
    ::= { cfprApSwEthLanPcEntry 17 }

cfprApSwEthLanPcLacpMode OBJECT-TYPE
    SYNTAX       CfprApFabricLacpMode
    MAX-ACCESS   read-only
    STATUS       current
    DESCRIPTION
        "Cisco Firepower sw:EthLanPc:lacpMode managed object property"
    ::= { cfprApSwEthLanPcEntry 18 }

cfprApSwEthLanPcLacpSuspendIndividual OBJECT-TYPE
    SYNTAX       TruthValue
    MAX-ACCESS   read-only
    STATUS       current
    DESCRIPTION
        "Cisco Firepower sw:EthLanPc:lacpSuspendIndividual
        managed object property"
    ::= { cfprApSwEthLanPcEntry 19 }

cfprApSwEthLanPcLocale OBJECT-TYPE
    SYNTAX       CfprApSwBorderPcLocale
    MAX-ACCESS   read-only
    STATUS       current
    DESCRIPTION
        "Cisco Firepower sw:EthLanPc:locale managed object property"
    ::= { cfprApSwEthLanPcEntry 20 }

cfprApSwEthLanPcMonTrafDir OBJECT-TYPE
    SYNTAX       CfprApFabricTrafficDirection
    MAX-ACCESS   read-only
    STATUS       current
    DESCRIPTION
        "Cisco Firepower sw:EthLanPc:monTrafDir managed object property"
    ::= { cfprApSwEthLanPcEntry 21 }

cfprApSwEthLanPcMtu OBJECT-TYPE
    SYNTAX       Gauge32
    MAX-ACCESS   read-only
    STATUS       current
    DESCRIPTION
        "Cisco Firepower sw:EthLanPc:mtu managed object property"
    ::= { cfprApSwEthLanPcEntry 22 }

cfprApSwEthLanPcName OBJECT-TYPE
    SYNTAX       SnmpAdminString
    MAX-ACCESS   read-only
    STATUS       current
    DESCRIPTION
        "Cisco Firepower sw:EthLanPc:name managed object property"
    ::= { cfprApSwEthLanPcEntry 23 }

cfprApSwEthLanPcPeerDn OBJECT-TYPE
    SYNTAX       SnmpAdminString
    MAX-ACCESS   read-only
    STATUS       current
    DESCRIPTION
        "Cisco Firepower sw:EthLanPc:peerDn managed object property"
    ::= { cfprApSwEthLanPcEntry 24 }

cfprApSwEthLanPcPortId OBJECT-TYPE
    SYNTAX       Gauge32
    MAX-ACCESS   read-only
    STATUS       current
    DESCRIPTION
        "Cisco Firepower sw:EthLanPc:portId managed object property"
    ::= { cfprApSwEthLanPcEntry 25 }

cfprApSwEthLanPcPriorityFlowCtrl OBJECT-TYPE
    SYNTAX       CfprApFlowctrlPriorityPause
    MAX-ACCESS   read-only
    STATUS       current
    DESCRIPTION
        "Cisco Firepower sw:EthLanPc:priorityFlowCtrl managed
        object property"
    ::= { cfprApSwEthLanPcEntry 26 }

cfprApSwEthLanPcQosPrio OBJECT-TYPE
    SYNTAX       CfprApFabricQosPrio
    MAX-ACCESS   read-only
    STATUS       current
    DESCRIPTION
        "Cisco Firepower sw:EthLanPc:qosPrio managed object property"
    ::= { cfprApSwEthLanPcEntry 27 }

cfprApSwEthLanPcRecvFlowCtrl OBJECT-TYPE
    SYNTAX       CfprApFlowctrlFlowControl
    MAX-ACCESS   read-only
    STATUS       current
    DESCRIPTION
        "Cisco Firepower sw:EthLanPc:recvFlowCtrl managed object property"
    ::= { cfprApSwEthLanPcEntry 28 }

cfprApSwEthLanPcSendFlowCtrl OBJECT-TYPE
    SYNTAX       CfprApFlowctrlFlowControl
    MAX-ACCESS   read-only
    STATUS       current
    DESCRIPTION
        "Cisco Firepower sw:EthLanPc:sendFlowCtrl managed object property"
    ::= { cfprApSwEthLanPcEntry 29 }

cfprApSwEthLanPcSpannedCluster OBJECT-TYPE
    SYNTAX       CfprApFabricSpannedCluster
    MAX-ACCESS   read-only
    STATUS       current
    DESCRIPTION
        "Cisco Firepower sw:EthLanPc:spannedCluster managed
        object property"
    ::= { cfprApSwEthLanPcEntry 30 }

cfprApSwEthLanPcSwitchId OBJECT-TYPE
    SYNTAX       CfprApNetworkSwitchId
    MAX-ACCESS   read-only
    STATUS       current
    DESCRIPTION
        "Cisco Firepower sw:EthLanPc:switchId managed object property"
    ::= { cfprApSwEthLanPcEntry 31 }

cfprApSwEthLanPcTransport OBJECT-TYPE
    SYNTAX       CfprApSwEthLanPcTransport
    MAX-ACCESS   read-only
    STATUS       current
    DESCRIPTION
        "Cisco Firepower sw:EthLanPc:transport managed object property"
    ::= { cfprApSwEthLanPcEntry 32 }

cfprApSwEthLanPcType OBJECT-TYPE
    SYNTAX       CfprApSwLanPcType
    MAX-ACCESS   read-only
    STATUS       current
    DESCRIPTION
        "Cisco Firepower sw:EthLanPc:type managed object property"
    ::= { cfprApSwEthLanPcEntry 33 }

cfprApSwEthMonTable OBJECT-TYPE
    SYNTAX           SEQUENCE OF CfprApSwEthMonEntry
    MAX-ACCESS       not-accessible
    STATUS           current
    DESCRIPTION
        "Cisco Firepower sw:EthMon managed object table"
    ::= { cfprApSwObjects 24 }

cfprApSwEthMonEntry OBJECT-TYPE
    SYNTAX           CfprApSwEthMonEntry
    MAX-ACCESS       not-accessible
    STATUS           current
    DESCRIPTION
        "Entry for the cfprApSwEthMonTable table."
    INDEX { cfprApSwEthMonInstanceId }
    ::= { cfprApSwEthMonTable 1 }

CfprApSwEthMonEntry ::= SEQUENCE {
    cfprApSwEthMonInstanceId                                         CfprApManagedObjectId,
    cfprApSwEthMonDn                                                 CfprApManagedObjectDn,
    cfprApSwEthMonRn                                                 SnmpAdminString,
    cfprApSwEthMonAdminState                                         CfprApSwMonAdminState,
    cfprApSwEthMonFsmDescr                                           SnmpAdminString,
    cfprApSwEthMonFsmPrev                                            SnmpAdminString,
    cfprApSwEthMonFsmProgr                                           Gauge32,
    cfprApSwEthMonFsmRmtInvErrCode                                   Gauge32,
    cfprApSwEthMonFsmRmtInvErrDescr                                  SnmpAdminString,
    cfprApSwEthMonFsmRmtInvRslt                                      CfprApConditionRemoteInvRslt,
    cfprApSwEthMonFsmStageDescr                                      SnmpAdminString,
    cfprApSwEthMonFsmStamp                                           DateAndTime,
    cfprApSwEthMonFsmStatus                                          SnmpAdminString,
    cfprApSwEthMonFsmTry                                             Gauge32,
    cfprApSwEthMonHasLastDest                                        TruthValue,
    cfprApSwEthMonLifeCycle                                          CfprApSwMonLifeCycle,
    cfprApSwEthMonName                                               SnmpAdminString,
    cfprApSwEthMonPeerDn                                             SnmpAdminString,
    cfprApSwEthMonSession                                            Gauge32,
    cfprApSwEthMonSwitchId                                           CfprApNetworkSwitchId,
    cfprApSwEthMonTransport                                          CfprApSwEthMonTransport,
    cfprApSwEthMonType                                               CfprApSwEthMonType
}

cfprApSwEthMonInstanceId OBJECT-TYPE
    SYNTAX       CfprApManagedObjectId
    MAX-ACCESS   not-accessible
    STATUS       current
    DESCRIPTION
        "Instance identifier of the managed object."
    ::= { cfprApSwEthMonEntry 1 }

cfprApSwEthMonDn OBJECT-TYPE
    SYNTAX       CfprApManagedObjectDn
    MAX-ACCESS   read-only
    STATUS       current
    DESCRIPTION
        "Cisco Firepower sw:EthMon:dn managed object property"
    ::= { cfprApSwEthMonEntry 2 }

cfprApSwEthMonRn OBJECT-TYPE
    SYNTAX       SnmpAdminString
    MAX-ACCESS   read-only
    STATUS       current
    DESCRIPTION
        "Cisco Firepower sw:EthMon:rn managed object property"
    ::= { cfprApSwEthMonEntry 3 }

cfprApSwEthMonAdminState OBJECT-TYPE
    SYNTAX       CfprApSwMonAdminState
    MAX-ACCESS   read-only
    STATUS       current
    DESCRIPTION
        "Cisco Firepower sw:EthMon:adminState managed object property"
    ::= { cfprApSwEthMonEntry 4 }

cfprApSwEthMonFsmDescr OBJECT-TYPE
    SYNTAX       SnmpAdminString
    MAX-ACCESS   read-only
    STATUS       current
    DESCRIPTION
        "Cisco Firepower sw:EthMon:fsmDescr managed object property"
    ::= { cfprApSwEthMonEntry 5 }

cfprApSwEthMonFsmPrev OBJECT-TYPE
    SYNTAX       SnmpAdminString
    MAX-ACCESS   read-only
    STATUS       current
    DESCRIPTION
        "Cisco Firepower sw:EthMon:fsmPrev managed object property"
    ::= { cfprApSwEthMonEntry 6 }

cfprApSwEthMonFsmProgr OBJECT-TYPE
    SYNTAX       Gauge32
    MAX-ACCESS   read-only
    STATUS       current
    DESCRIPTION
        "Cisco Firepower sw:EthMon:fsmProgr managed object property"
    ::= { cfprApSwEthMonEntry 7 }

cfprApSwEthMonFsmRmtInvErrCode OBJECT-TYPE
    SYNTAX       Gauge32
    MAX-ACCESS   read-only
    STATUS       current
    DESCRIPTION
        "Cisco Firepower sw:EthMon:fsmRmtInvErrCode managed
        object property"
    ::= { cfprApSwEthMonEntry 8 }

cfprApSwEthMonFsmRmtInvErrDescr OBJECT-TYPE
    SYNTAX       SnmpAdminString
    MAX-ACCESS   read-only
    STATUS       current
    DESCRIPTION
        "Cisco Firepower sw:EthMon:fsmRmtInvErrDescr managed
        object property"
    ::= { cfprApSwEthMonEntry 9 }

cfprApSwEthMonFsmRmtInvRslt OBJECT-TYPE
    SYNTAX       CfprApConditionRemoteInvRslt
    MAX-ACCESS   read-only
    STATUS       current
    DESCRIPTION
        "Cisco Firepower sw:EthMon:fsmRmtInvRslt managed object property"
    ::= { cfprApSwEthMonEntry 10 }

cfprApSwEthMonFsmStageDescr OBJECT-TYPE
    SYNTAX       SnmpAdminString
    MAX-ACCESS   read-only
    STATUS       current
    DESCRIPTION
        "Cisco Firepower sw:EthMon:fsmStageDescr managed object property"
    ::= { cfprApSwEthMonEntry 11 }

cfprApSwEthMonFsmStamp OBJECT-TYPE
    SYNTAX       DateAndTime
    MAX-ACCESS   read-only
    STATUS       current
    DESCRIPTION
        "Cisco Firepower sw:EthMon:fsmStamp managed object property"
    ::= { cfprApSwEthMonEntry 12 }

cfprApSwEthMonFsmStatus OBJECT-TYPE
    SYNTAX       SnmpAdminString
    MAX-ACCESS   read-only
    STATUS       current
    DESCRIPTION
        "Cisco Firepower sw:EthMon:fsmStatus managed object property"
    ::= { cfprApSwEthMonEntry 13 }

cfprApSwEthMonFsmTry OBJECT-TYPE
    SYNTAX       Gauge32
    MAX-ACCESS   read-only
    STATUS       current
    DESCRIPTION
        "Cisco Firepower sw:EthMon:fsmTry managed object property"
    ::= { cfprApSwEthMonEntry 14 }

cfprApSwEthMonHasLastDest OBJECT-TYPE
    SYNTAX       TruthValue
    MAX-ACCESS   read-only
    STATUS       current
    DESCRIPTION
        "Cisco Firepower sw:EthMon:hasLastDest managed object property"
    ::= { cfprApSwEthMonEntry 15 }

cfprApSwEthMonLifeCycle OBJECT-TYPE
    SYNTAX       CfprApSwMonLifeCycle
    MAX-ACCESS   read-only
    STATUS       current
    DESCRIPTION
        "Cisco Firepower sw:EthMon:lifeCycle managed object property"
    ::= { cfprApSwEthMonEntry 16 }

cfprApSwEthMonName OBJECT-TYPE
    SYNTAX       SnmpAdminString
    MAX-ACCESS   read-only
    STATUS       current
    DESCRIPTION
        "Cisco Firepower sw:EthMon:name managed object property"
    ::= { cfprApSwEthMonEntry 17 }

cfprApSwEthMonPeerDn OBJECT-TYPE
    SYNTAX       SnmpAdminString
    MAX-ACCESS   read-only
    STATUS       current
    DESCRIPTION
        "Cisco Firepower sw:EthMon:peerDn managed object property"
    ::= { cfprApSwEthMonEntry 18 }

cfprApSwEthMonSession OBJECT-TYPE
    SYNTAX       Gauge32
    MAX-ACCESS   read-only
    STATUS       current
    DESCRIPTION
        "Cisco Firepower sw:EthMon:session managed object property"
    ::= { cfprApSwEthMonEntry 19 }

cfprApSwEthMonSwitchId OBJECT-TYPE
    SYNTAX       CfprApNetworkSwitchId
    MAX-ACCESS   read-only
    STATUS       current
    DESCRIPTION
        "Cisco Firepower sw:EthMon:switchId managed object property"
    ::= { cfprApSwEthMonEntry 20 }

cfprApSwEthMonTransport OBJECT-TYPE
    SYNTAX       CfprApSwEthMonTransport
    MAX-ACCESS   read-only
    STATUS       current
    DESCRIPTION
        "Cisco Firepower sw:EthMon:transport managed object property"
    ::= { cfprApSwEthMonEntry 21 }

cfprApSwEthMonType OBJECT-TYPE
    SYNTAX       CfprApSwEthMonType
    MAX-ACCESS   read-only
    STATUS       current
    DESCRIPTION
        "Cisco Firepower sw:EthMon:type managed object property"
    ::= { cfprApSwEthMonEntry 22 }

cfprApSwEthMonDestEpTable OBJECT-TYPE
    SYNTAX           SEQUENCE OF CfprApSwEthMonDestEpEntry
    MAX-ACCESS       not-accessible
    STATUS           current
    DESCRIPTION
        "Cisco Firepower sw:EthMonDestEp managed object table"
    ::= { cfprApSwObjects 25 }

cfprApSwEthMonDestEpEntry OBJECT-TYPE
    SYNTAX           CfprApSwEthMonDestEpEntry
    MAX-ACCESS       not-accessible
    STATUS           current
    DESCRIPTION
        "Entry for the cfprApSwEthMonDestEpTable table."
    INDEX { cfprApSwEthMonDestEpInstanceId }
    ::= { cfprApSwEthMonDestEpTable 1 }

CfprApSwEthMonDestEpEntry ::= SEQUENCE {
    cfprApSwEthMonDestEpInstanceId                                   CfprApManagedObjectId,
    cfprApSwEthMonDestEpDn                                           CfprApManagedObjectDn,
    cfprApSwEthMonDestEpRn                                           SnmpAdminString,
    cfprApSwEthMonDestEpAdminSpeed                                   CfprApPortEthSpeed,
    cfprApSwEthMonDestEpAdminState                                   CfprApFabricAdminState,
    cfprApSwEthMonDestEpAggrPortId                                   Gauge32,
    cfprApSwEthMonDestEpChassisId                                    Gauge32,
    cfprApSwEthMonDestEpEpDn                                         SnmpAdminString,
    cfprApSwEthMonDestEpIfRole                                       CfprApNetworkPortRole,
    cfprApSwEthMonDestEpIfType                                       CfprApSwPIoEpIfType,
    cfprApSwEthMonDestEpLc                                           CfprApSwPIoEpLc,
    cfprApSwEthMonDestEpLocale                                       CfprApNetworkLocale,
    cfprApSwEthMonDestEpName                                         SnmpAdminString,
    cfprApSwEthMonDestEpPeerAggrPortId                               Gauge32,
    cfprApSwEthMonDestEpPeerChassisId                                Gauge32,
    cfprApSwEthMonDestEpPeerDn                                       SnmpAdminString,
    cfprApSwEthMonDestEpPeerPortId                                   Gauge32,
    cfprApSwEthMonDestEpPeerSlotId                                   Gauge32,
    cfprApSwEthMonDestEpPortId                                       Gauge32,
    cfprApSwEthMonDestEpSlotId                                       Gauge32,
    cfprApSwEthMonDestEpSwitchId                                     CfprApNetworkSwitchId,
    cfprApSwEthMonDestEpTransport                                    CfprApSwEthMonDestEpTransport,
    cfprApSwEthMonDestEpType                                         CfprApNetworkConnectionType
}

cfprApSwEthMonDestEpInstanceId OBJECT-TYPE
    SYNTAX       CfprApManagedObjectId
    MAX-ACCESS   not-accessible
    STATUS       current
    DESCRIPTION
        "Instance identifier of the managed object."
    ::= { cfprApSwEthMonDestEpEntry 1 }

cfprApSwEthMonDestEpDn OBJECT-TYPE
    SYNTAX       CfprApManagedObjectDn
    MAX-ACCESS   read-only
    STATUS       current
    DESCRIPTION
        "Cisco Firepower sw:EthMonDestEp:dn managed object property"
    ::= { cfprApSwEthMonDestEpEntry 2 }

cfprApSwEthMonDestEpRn OBJECT-TYPE
    SYNTAX       SnmpAdminString
    MAX-ACCESS   read-only
    STATUS       current
    DESCRIPTION
        "Cisco Firepower sw:EthMonDestEp:rn managed object property"
    ::= { cfprApSwEthMonDestEpEntry 3 }

cfprApSwEthMonDestEpAdminSpeed OBJECT-TYPE
    SYNTAX       CfprApPortEthSpeed
    MAX-ACCESS   read-only
    STATUS       current
    DESCRIPTION
        "Cisco Firepower sw:EthMonDestEp:adminSpeed managed
        object property"
    ::= { cfprApSwEthMonDestEpEntry 4 }

cfprApSwEthMonDestEpAdminState OBJECT-TYPE
    SYNTAX       CfprApFabricAdminState
    MAX-ACCESS   read-only
    STATUS       current
    DESCRIPTION
        "Cisco Firepower sw:EthMonDestEp:adminState managed
        object property"
    ::= { cfprApSwEthMonDestEpEntry 5 }

cfprApSwEthMonDestEpAggrPortId OBJECT-TYPE
    SYNTAX       Gauge32
    MAX-ACCESS   read-only
    STATUS       current
    DESCRIPTION
        "Cisco Firepower sw:EthMonDestEp:aggrPortId managed
        object property"
    ::= { cfprApSwEthMonDestEpEntry 6 }

cfprApSwEthMonDestEpChassisId OBJECT-TYPE
    SYNTAX       Gauge32
    MAX-ACCESS   read-only
    STATUS       current
    DESCRIPTION
        "Cisco Firepower sw:EthMonDestEp:chassisId managed
        object property"
    ::= { cfprApSwEthMonDestEpEntry 7 }

cfprApSwEthMonDestEpEpDn OBJECT-TYPE
    SYNTAX       SnmpAdminString
    MAX-ACCESS   read-only
    STATUS       current
    DESCRIPTION
        "Cisco Firepower sw:EthMonDestEp:epDn managed object property"
    ::= { cfprApSwEthMonDestEpEntry 8 }

cfprApSwEthMonDestEpIfRole OBJECT-TYPE
    SYNTAX       CfprApNetworkPortRole
    MAX-ACCESS   read-only
    STATUS       current
    DESCRIPTION
        "Cisco Firepower sw:EthMonDestEp:ifRole managed object property"
    ::= { cfprApSwEthMonDestEpEntry 9 }

cfprApSwEthMonDestEpIfType OBJECT-TYPE
    SYNTAX       CfprApSwPIoEpIfType
    MAX-ACCESS   read-only
    STATUS       current
    DESCRIPTION
        "Cisco Firepower sw:EthMonDestEp:ifType managed object property"
    ::= { cfprApSwEthMonDestEpEntry 10 }

cfprApSwEthMonDestEpLc OBJECT-TYPE
    SYNTAX       CfprApSwPIoEpLc
    MAX-ACCESS   read-only
    STATUS       current
    DESCRIPTION
        "Cisco Firepower sw:EthMonDestEp:lc managed object property"
    ::= { cfprApSwEthMonDestEpEntry 11 }

cfprApSwEthMonDestEpLocale OBJECT-TYPE
    SYNTAX       CfprApNetworkLocale
    MAX-ACCESS   read-only
    STATUS       current
    DESCRIPTION
        "Cisco Firepower sw:EthMonDestEp:locale managed object property"
    ::= { cfprApSwEthMonDestEpEntry 12 }

cfprApSwEthMonDestEpName OBJECT-TYPE
    SYNTAX       SnmpAdminString
    MAX-ACCESS   read-only
    STATUS       current
    DESCRIPTION
        "Cisco Firepower sw:EthMonDestEp:name managed object property"
    ::= { cfprApSwEthMonDestEpEntry 13 }

cfprApSwEthMonDestEpPeerAggrPortId OBJECT-TYPE
    SYNTAX       Gauge32
    MAX-ACCESS   read-only
    STATUS       current
    DESCRIPTION
        "Cisco Firepower sw:EthMonDestEp:peerAggrPortId
        managed object property"
    ::= { cfprApSwEthMonDestEpEntry 14 }

cfprApSwEthMonDestEpPeerChassisId OBJECT-TYPE
    SYNTAX       Gauge32
    MAX-ACCESS   read-only
    STATUS       current
    DESCRIPTION
        "Cisco Firepower sw:EthMonDestEp:peerChassisId
        managed object property"
    ::= { cfprApSwEthMonDestEpEntry 15 }

cfprApSwEthMonDestEpPeerDn OBJECT-TYPE
    SYNTAX       SnmpAdminString
    MAX-ACCESS   read-only
    STATUS       current
    DESCRIPTION
        "Cisco Firepower sw:EthMonDestEp:peerDn managed object property"
    ::= { cfprApSwEthMonDestEpEntry 16 }

cfprApSwEthMonDestEpPeerPortId OBJECT-TYPE
    SYNTAX       Gauge32
    MAX-ACCESS   read-only
    STATUS       current
    DESCRIPTION
        "Cisco Firepower sw:EthMonDestEp:peerPortId managed
        object property"
    ::= { cfprApSwEthMonDestEpEntry 17 }

cfprApSwEthMonDestEpPeerSlotId OBJECT-TYPE
    SYNTAX       Gauge32
    MAX-ACCESS   read-only
    STATUS       current
    DESCRIPTION
        "Cisco Firepower sw:EthMonDestEp:peerSlotId managed
        object property"
    ::= { cfprApSwEthMonDestEpEntry 18 }

cfprApSwEthMonDestEpPortId OBJECT-TYPE
    SYNTAX       Gauge32
    MAX-ACCESS   read-only
    STATUS       current
    DESCRIPTION
        "Cisco Firepower sw:EthMonDestEp:portId managed object property"
    ::= { cfprApSwEthMonDestEpEntry 19 }

cfprApSwEthMonDestEpSlotId OBJECT-TYPE
    SYNTAX       Gauge32
    MAX-ACCESS   read-only
    STATUS       current
    DESCRIPTION
        "Cisco Firepower sw:EthMonDestEp:slotId managed object property"
    ::= { cfprApSwEthMonDestEpEntry 20 }

cfprApSwEthMonDestEpSwitchId OBJECT-TYPE
    SYNTAX       CfprApNetworkSwitchId
    MAX-ACCESS   read-only
    STATUS       current
    DESCRIPTION
        "Cisco Firepower sw:EthMonDestEp:switchId managed object property"
    ::= { cfprApSwEthMonDestEpEntry 21 }

cfprApSwEthMonDestEpTransport OBJECT-TYPE
    SYNTAX       CfprApSwEthMonDestEpTransport
    MAX-ACCESS   read-only
    STATUS       current
    DESCRIPTION
        "Cisco Firepower sw:EthMonDestEp:transport managed
        object property"
    ::= { cfprApSwEthMonDestEpEntry 22 }

cfprApSwEthMonDestEpType OBJECT-TYPE
    SYNTAX       CfprApNetworkConnectionType
    MAX-ACCESS   read-only
    STATUS       current
    DESCRIPTION
        "Cisco Firepower sw:EthMonDestEp:type managed object property"
    ::= { cfprApSwEthMonDestEpEntry 23 }

cfprApSwEthMonFsmTable OBJECT-TYPE
    SYNTAX           SEQUENCE OF CfprApSwEthMonFsmEntry
    MAX-ACCESS       not-accessible
    STATUS           current
    DESCRIPTION
        "Cisco Firepower sw:EthMonFsm managed object table"
    ::= { cfprApSwObjects 26 }

cfprApSwEthMonFsmEntry OBJECT-TYPE
    SYNTAX           CfprApSwEthMonFsmEntry
    MAX-ACCESS       not-accessible
    STATUS           current
    DESCRIPTION
        "Entry for the cfprApSwEthMonFsmTable table."
    INDEX { cfprApSwEthMonFsmInstanceId }
    ::= { cfprApSwEthMonFsmTable 1 }

CfprApSwEthMonFsmEntry ::= SEQUENCE {
    cfprApSwEthMonFsmInstanceId                                      CfprApManagedObjectId,
    cfprApSwEthMonFsmDn                                              CfprApManagedObjectDn,
    cfprApSwEthMonFsmRn                                              SnmpAdminString,
    cfprApSwEthMonFsmCompletionTime                                  DateAndTime,
    cfprApSwEthMonFsmCurrentFsm                                      CfprApSwEthMonFsmCurrentFsm,
    cfprApSwEthMonFsmDescrData                                       SnmpAdminString,
    cfprApSwEthMonFsmFsmStatus                                       CfprApFsmFsmStageStatus,
    cfprApSwEthMonFsmProgress                                        Gauge32,
    cfprApSwEthMonFsmRmtErrCode                                      Gauge32,
    cfprApSwEthMonFsmRmtErrDescr                                     SnmpAdminString,
    cfprApSwEthMonFsmRmtRslt                                         CfprApConditionRemoteInvRslt
}

cfprApSwEthMonFsmInstanceId OBJECT-TYPE
    SYNTAX       CfprApManagedObjectId
    MAX-ACCESS   not-accessible
    STATUS       current
    DESCRIPTION
        "Instance identifier of the managed object."
    ::= { cfprApSwEthMonFsmEntry 1 }

cfprApSwEthMonFsmDn OBJECT-TYPE
    SYNTAX       CfprApManagedObjectDn
    MAX-ACCESS   read-only
    STATUS       current
    DESCRIPTION
        "Cisco Firepower sw:EthMonFsm:dn managed object property"
    ::= { cfprApSwEthMonFsmEntry 2 }

cfprApSwEthMonFsmRn OBJECT-TYPE
    SYNTAX       SnmpAdminString
    MAX-ACCESS   read-only
    STATUS       current
    DESCRIPTION
        "Cisco Firepower sw:EthMonFsm:rn managed object property"
    ::= { cfprApSwEthMonFsmEntry 3 }

cfprApSwEthMonFsmCompletionTime OBJECT-TYPE
    SYNTAX       DateAndTime
    MAX-ACCESS   read-only
    STATUS       current
    DESCRIPTION
        "Cisco Firepower sw:EthMonFsm:completionTime managed
        object property"
    ::= { cfprApSwEthMonFsmEntry 4 }

cfprApSwEthMonFsmCurrentFsm OBJECT-TYPE
    SYNTAX       CfprApSwEthMonFsmCurrentFsm
    MAX-ACCESS   read-only
    STATUS       current
    DESCRIPTION
        "Cisco Firepower sw:EthMonFsm:currentFsm managed object property"
    ::= { cfprApSwEthMonFsmEntry 5 }

cfprApSwEthMonFsmDescrData OBJECT-TYPE
    SYNTAX       SnmpAdminString
    MAX-ACCESS   read-only
    STATUS       current
    DESCRIPTION
        "Cisco Firepower sw:EthMonFsm:descr managed object property"
    ::= { cfprApSwEthMonFsmEntry 6 }

cfprApSwEthMonFsmFsmStatus OBJECT-TYPE
    SYNTAX       CfprApFsmFsmStageStatus
    MAX-ACCESS   read-only
    STATUS       current
    DESCRIPTION
        "Cisco Firepower sw:EthMonFsm:fsmStatus managed object property"
    ::= { cfprApSwEthMonFsmEntry 7 }

cfprApSwEthMonFsmProgress OBJECT-TYPE
    SYNTAX       Gauge32
    MAX-ACCESS   read-only
    STATUS       current
    DESCRIPTION
        "Cisco Firepower sw:EthMonFsm:progress managed object property"
    ::= { cfprApSwEthMonFsmEntry 8 }

cfprApSwEthMonFsmRmtErrCode OBJECT-TYPE
    SYNTAX       Gauge32
    MAX-ACCESS   read-only
    STATUS       current
    DESCRIPTION
        "Cisco Firepower sw:EthMonFsm:rmtErrCode managed object property"
    ::= { cfprApSwEthMonFsmEntry 9 }

cfprApSwEthMonFsmRmtErrDescr OBJECT-TYPE
    SYNTAX       SnmpAdminString
    MAX-ACCESS   read-only
    STATUS       current
    DESCRIPTION
        "Cisco Firepower sw:EthMonFsm:rmtErrDescr managed object property"
    ::= { cfprApSwEthMonFsmEntry 10 }

cfprApSwEthMonFsmRmtRslt OBJECT-TYPE
    SYNTAX       CfprApConditionRemoteInvRslt
    MAX-ACCESS   read-only
    STATUS       current
    DESCRIPTION
        "Cisco Firepower sw:EthMonFsm:rmtRslt managed object property"
    ::= { cfprApSwEthMonFsmEntry 11 }

cfprApSwEthMonFsmStageTable OBJECT-TYPE
    SYNTAX           SEQUENCE OF CfprApSwEthMonFsmStageEntry
    MAX-ACCESS       not-accessible
    STATUS           current
    DESCRIPTION
        "Cisco Firepower sw:EthMonFsmStage managed object table"
    ::= { cfprApSwObjects 27 }

cfprApSwEthMonFsmStageEntry OBJECT-TYPE
    SYNTAX           CfprApSwEthMonFsmStageEntry
    MAX-ACCESS       not-accessible
    STATUS           current
    DESCRIPTION
        "Entry for the cfprApSwEthMonFsmStageTable table."
    INDEX { cfprApSwEthMonFsmStageInstanceId }
    ::= { cfprApSwEthMonFsmStageTable 1 }

CfprApSwEthMonFsmStageEntry ::= SEQUENCE {
    cfprApSwEthMonFsmStageInstanceId                                 CfprApManagedObjectId,
    cfprApSwEthMonFsmStageDn                                         CfprApManagedObjectDn,
    cfprApSwEthMonFsmStageRn                                         SnmpAdminString,
    cfprApSwEthMonFsmStageDescrData                                  SnmpAdminString,
    cfprApSwEthMonFsmStageLastUpdateTime                             DateAndTime,
    cfprApSwEthMonFsmStageName                                       CfprApSwEthMonFsmStageName,
    cfprApSwEthMonFsmStageOrder                                      Gauge32,
    cfprApSwEthMonFsmStageRetry                                      Gauge32,
    cfprApSwEthMonFsmStageStageStatus                                CfprApFsmFsmStageStatus
}

cfprApSwEthMonFsmStageInstanceId OBJECT-TYPE
    SYNTAX       CfprApManagedObjectId
    MAX-ACCESS   not-accessible
    STATUS       current
    DESCRIPTION
        "Instance identifier of the managed object."
    ::= { cfprApSwEthMonFsmStageEntry 1 }

cfprApSwEthMonFsmStageDn OBJECT-TYPE
    SYNTAX       CfprApManagedObjectDn
    MAX-ACCESS   read-only
    STATUS       current
    DESCRIPTION
        "Cisco Firepower sw:EthMonFsmStage:dn managed object property"
    ::= { cfprApSwEthMonFsmStageEntry 2 }

cfprApSwEthMonFsmStageRn OBJECT-TYPE
    SYNTAX       SnmpAdminString
    MAX-ACCESS   read-only
    STATUS       current
    DESCRIPTION
        "Cisco Firepower sw:EthMonFsmStage:rn managed object property"
    ::= { cfprApSwEthMonFsmStageEntry 3 }

cfprApSwEthMonFsmStageDescrData OBJECT-TYPE
    SYNTAX       SnmpAdminString
    MAX-ACCESS   read-only
    STATUS       current
    DESCRIPTION
        "Cisco Firepower sw:EthMonFsmStage:descr managed object property"
    ::= { cfprApSwEthMonFsmStageEntry 4 }

cfprApSwEthMonFsmStageLastUpdateTime OBJECT-TYPE
    SYNTAX       DateAndTime
    MAX-ACCESS   read-only
    STATUS       current
    DESCRIPTION
        "Cisco Firepower sw:EthMonFsmStage:lastUpdateTime
        managed object property"
    ::= { cfprApSwEthMonFsmStageEntry 5 }

cfprApSwEthMonFsmStageName OBJECT-TYPE
    SYNTAX       CfprApSwEthMonFsmStageName
    MAX-ACCESS   read-only
    STATUS       current
    DESCRIPTION
        "Cisco Firepower sw:EthMonFsmStage:name managed object property"
    ::= { cfprApSwEthMonFsmStageEntry 6 }

cfprApSwEthMonFsmStageOrder OBJECT-TYPE
    SYNTAX       Gauge32
    MAX-ACCESS   read-only
    STATUS       current
    DESCRIPTION
        "Cisco Firepower sw:EthMonFsmStage:order managed object property"
    ::= { cfprApSwEthMonFsmStageEntry 7 }

cfprApSwEthMonFsmStageRetry OBJECT-TYPE
    SYNTAX       Gauge32
    MAX-ACCESS   read-only
    STATUS       current
    DESCRIPTION
        "Cisco Firepower sw:EthMonFsmStage:retry managed object property"
    ::= { cfprApSwEthMonFsmStageEntry 8 }

cfprApSwEthMonFsmStageStageStatus OBJECT-TYPE
    SYNTAX       CfprApFsmFsmStageStatus
    MAX-ACCESS   read-only
    STATUS       current
    DESCRIPTION
        "Cisco Firepower sw:EthMonFsmStage:stageStatus
        managed object property"
    ::= { cfprApSwEthMonFsmStageEntry 9 }

cfprApSwEthMonFsmTaskTable OBJECT-TYPE
    SYNTAX           SEQUENCE OF CfprApSwEthMonFsmTaskEntry
    MAX-ACCESS       not-accessible
    STATUS           current
    DESCRIPTION
        "Cisco Firepower sw:EthMonFsmTask managed object table"
    ::= { cfprApSwObjects 28 }

cfprApSwEthMonFsmTaskEntry OBJECT-TYPE
    SYNTAX           CfprApSwEthMonFsmTaskEntry
    MAX-ACCESS       not-accessible
    STATUS           current
    DESCRIPTION
        "Entry for the cfprApSwEthMonFsmTaskTable table."
    INDEX { cfprApSwEthMonFsmTaskInstanceId }
    ::= { cfprApSwEthMonFsmTaskTable 1 }

CfprApSwEthMonFsmTaskEntry ::= SEQUENCE {
    cfprApSwEthMonFsmTaskInstanceId                                  CfprApManagedObjectId,
    cfprApSwEthMonFsmTaskDn                                          CfprApManagedObjectDn,
    cfprApSwEthMonFsmTaskRn                                          SnmpAdminString,
    cfprApSwEthMonFsmTaskCompletion                                  CfprApFsmCompletion,
    cfprApSwEthMonFsmTaskFlags                                       CfprApFsmFlags,
    cfprApSwEthMonFsmTaskItem                                        CfprApSwEthMonFsmTaskItem,
    cfprApSwEthMonFsmTaskSeqId                                       Gauge32
}

cfprApSwEthMonFsmTaskInstanceId OBJECT-TYPE
    SYNTAX       CfprApManagedObjectId
    MAX-ACCESS   not-accessible
    STATUS       current
    DESCRIPTION
        "Instance identifier of the managed object."
    ::= { cfprApSwEthMonFsmTaskEntry 1 }

cfprApSwEthMonFsmTaskDn OBJECT-TYPE
    SYNTAX       CfprApManagedObjectDn
    MAX-ACCESS   read-only
    STATUS       current
    DESCRIPTION
        "Cisco Firepower sw:EthMonFsmTask:dn managed object property"
    ::= { cfprApSwEthMonFsmTaskEntry 2 }

cfprApSwEthMonFsmTaskRn OBJECT-TYPE
    SYNTAX       SnmpAdminString
    MAX-ACCESS   read-only
    STATUS       current
    DESCRIPTION
        "Cisco Firepower sw:EthMonFsmTask:rn managed object property"
    ::= { cfprApSwEthMonFsmTaskEntry 3 }

cfprApSwEthMonFsmTaskCompletion OBJECT-TYPE
    SYNTAX       CfprApFsmCompletion
    MAX-ACCESS   read-only
    STATUS       current
    DESCRIPTION
        "Cisco Firepower sw:EthMonFsmTask:completion managed
        object property"
    ::= { cfprApSwEthMonFsmTaskEntry 4 }

cfprApSwEthMonFsmTaskFlags OBJECT-TYPE
    SYNTAX       CfprApFsmFlags
    MAX-ACCESS   read-only
    STATUS       current
    DESCRIPTION
        "Cisco Firepower sw:EthMonFsmTask:flags managed object property"
    ::= { cfprApSwEthMonFsmTaskEntry 5 }

cfprApSwEthMonFsmTaskItem OBJECT-TYPE
    SYNTAX       CfprApSwEthMonFsmTaskItem
    MAX-ACCESS   read-only
    STATUS       current
    DESCRIPTION
        "Cisco Firepower sw:EthMonFsmTask:item managed object property"
    ::= { cfprApSwEthMonFsmTaskEntry 6 }

cfprApSwEthMonFsmTaskSeqId OBJECT-TYPE
    SYNTAX       Gauge32
    MAX-ACCESS   read-only
    STATUS       current
    DESCRIPTION
        "Cisco Firepower sw:EthMonFsmTask:seqId managed object property"
    ::= { cfprApSwEthMonFsmTaskEntry 7 }

cfprApSwEthMonSrcEpTable OBJECT-TYPE
    SYNTAX           SEQUENCE OF CfprApSwEthMonSrcEpEntry
    MAX-ACCESS       not-accessible
    STATUS           current
    DESCRIPTION
        "Cisco Firepower sw:EthMonSrcEp managed object table"
    ::= { cfprApSwObjects 29 }

cfprApSwEthMonSrcEpEntry OBJECT-TYPE
    SYNTAX           CfprApSwEthMonSrcEpEntry
    MAX-ACCESS       not-accessible
    STATUS           current
    DESCRIPTION
        "Entry for the cfprApSwEthMonSrcEpTable table."
    INDEX { cfprApSwEthMonSrcEpInstanceId }
    ::= { cfprApSwEthMonSrcEpTable 1 }

CfprApSwEthMonSrcEpEntry ::= SEQUENCE {
    cfprApSwEthMonSrcEpInstanceId                                    CfprApManagedObjectId,
    cfprApSwEthMonSrcEpDn                                            CfprApManagedObjectDn,
    cfprApSwEthMonSrcEpRn                                            SnmpAdminString,
    cfprApSwEthMonSrcEpAdminState                                    CfprApFabricAdminState,
    cfprApSwEthMonSrcEpAggrPortId                                    Gauge32,
    cfprApSwEthMonSrcEpChassisId                                     Gauge32,
    cfprApSwEthMonSrcEpEpDn                                          SnmpAdminString,
    cfprApSwEthMonSrcEpIfRole                                        CfprApNetworkPortRole,
    cfprApSwEthMonSrcEpIfType                                        CfprApSwPIoEpIfType,
    cfprApSwEthMonSrcEpLc                                            CfprApSwPIoEpLc,
    cfprApSwEthMonSrcEpLocale                                        CfprApSwMonSrcEpLocale,
    cfprApSwEthMonSrcEpMonTrafDir                                    CfprApFabricTrafficDirection,
    cfprApSwEthMonSrcEpName                                          SnmpAdminString,
    cfprApSwEthMonSrcEpPeerAggrPortId                                Gauge32,
    cfprApSwEthMonSrcEpPeerChassisId                                 Gauge32,
    cfprApSwEthMonSrcEpPeerDn                                        SnmpAdminString,
    cfprApSwEthMonSrcEpPeerPortId                                    Gauge32,
    cfprApSwEthMonSrcEpPeerSlotId                                    Gauge32,
    cfprApSwEthMonSrcEpPortId                                        Gauge32,
    cfprApSwEthMonSrcEpSlotId                                        Gauge32,
    cfprApSwEthMonSrcEpSwitchId                                      CfprApNetworkSwitchId,
    cfprApSwEthMonSrcEpTransport                                     CfprApSwEthMonSrcEpTransport,
    cfprApSwEthMonSrcEpType                                          CfprApNetworkConnectionType
}

cfprApSwEthMonSrcEpInstanceId OBJECT-TYPE
    SYNTAX       CfprApManagedObjectId
    MAX-ACCESS   not-accessible
    STATUS       current
    DESCRIPTION
        "Instance identifier of the managed object."
    ::= { cfprApSwEthMonSrcEpEntry 1 }

cfprApSwEthMonSrcEpDn OBJECT-TYPE
    SYNTAX       CfprApManagedObjectDn
    MAX-ACCESS   read-only
    STATUS       current
    DESCRIPTION
        "Cisco Firepower sw:EthMonSrcEp:dn managed object property"
    ::= { cfprApSwEthMonSrcEpEntry 2 }

cfprApSwEthMonSrcEpRn OBJECT-TYPE
    SYNTAX       SnmpAdminString
    MAX-ACCESS   read-only
    STATUS       current
    DESCRIPTION
        "Cisco Firepower sw:EthMonSrcEp:rn managed object property"
    ::= { cfprApSwEthMonSrcEpEntry 3 }

cfprApSwEthMonSrcEpAdminState OBJECT-TYPE
    SYNTAX       CfprApFabricAdminState
    MAX-ACCESS   read-only
    STATUS       current
    DESCRIPTION
        "Cisco Firepower sw:EthMonSrcEp:adminState managed
        object property"
    ::= { cfprApSwEthMonSrcEpEntry 4 }

cfprApSwEthMonSrcEpAggrPortId OBJECT-TYPE
    SYNTAX       Gauge32
    MAX-ACCESS   read-only
    STATUS       current
    DESCRIPTION
        "Cisco Firepower sw:EthMonSrcEp:aggrPortId managed
        object property"
    ::= { cfprApSwEthMonSrcEpEntry 5 }

cfprApSwEthMonSrcEpChassisId OBJECT-TYPE
    SYNTAX       Gauge32
    MAX-ACCESS   read-only
    STATUS       current
    DESCRIPTION
        "Cisco Firepower sw:EthMonSrcEp:chassisId managed object property"
    ::= { cfprApSwEthMonSrcEpEntry 6 }

cfprApSwEthMonSrcEpEpDn OBJECT-TYPE
    SYNTAX       SnmpAdminString
    MAX-ACCESS   read-only
    STATUS       current
    DESCRIPTION
        "Cisco Firepower sw:EthMonSrcEp:epDn managed object property"
    ::= { cfprApSwEthMonSrcEpEntry 7 }

cfprApSwEthMonSrcEpIfRole OBJECT-TYPE
    SYNTAX       CfprApNetworkPortRole
    MAX-ACCESS   read-only
    STATUS       current
    DESCRIPTION
        "Cisco Firepower sw:EthMonSrcEp:ifRole managed object property"
    ::= { cfprApSwEthMonSrcEpEntry 8 }

cfprApSwEthMonSrcEpIfType OBJECT-TYPE
    SYNTAX       CfprApSwPIoEpIfType
    MAX-ACCESS   read-only
    STATUS       current
    DESCRIPTION
        "Cisco Firepower sw:EthMonSrcEp:ifType managed object property"
    ::= { cfprApSwEthMonSrcEpEntry 9 }

cfprApSwEthMonSrcEpLc OBJECT-TYPE
    SYNTAX       CfprApSwPIoEpLc
    MAX-ACCESS   read-only
    STATUS       current
    DESCRIPTION
        "Cisco Firepower sw:EthMonSrcEp:lc managed object property"
    ::= { cfprApSwEthMonSrcEpEntry 10 }

cfprApSwEthMonSrcEpLocale OBJECT-TYPE
    SYNTAX       CfprApSwMonSrcEpLocale
    MAX-ACCESS   read-only
    STATUS       current
    DESCRIPTION
        "Cisco Firepower sw:EthMonSrcEp:locale managed object property"
    ::= { cfprApSwEthMonSrcEpEntry 11 }

cfprApSwEthMonSrcEpMonTrafDir OBJECT-TYPE
    SYNTAX       CfprApFabricTrafficDirection
    MAX-ACCESS   read-only
    STATUS       current
    DESCRIPTION
        "Cisco Firepower sw:EthMonSrcEp:monTrafDir managed
        object property"
    ::= { cfprApSwEthMonSrcEpEntry 12 }

cfprApSwEthMonSrcEpName OBJECT-TYPE
    SYNTAX       SnmpAdminString
    MAX-ACCESS   read-only
    STATUS       current
    DESCRIPTION
        "Cisco Firepower sw:EthMonSrcEp:name managed object property"
    ::= { cfprApSwEthMonSrcEpEntry 13 }

cfprApSwEthMonSrcEpPeerAggrPortId OBJECT-TYPE
    SYNTAX       Gauge32
    MAX-ACCESS   read-only
    STATUS       current
    DESCRIPTION
        "Cisco Firepower sw:EthMonSrcEp:peerAggrPortId
        managed object property"
    ::= { cfprApSwEthMonSrcEpEntry 14 }

cfprApSwEthMonSrcEpPeerChassisId OBJECT-TYPE
    SYNTAX       Gauge32
    MAX-ACCESS   read-only
    STATUS       current
    DESCRIPTION
        "Cisco Firepower sw:EthMonSrcEp:peerChassisId managed
        object property"
    ::= { cfprApSwEthMonSrcEpEntry 15 }

cfprApSwEthMonSrcEpPeerDn OBJECT-TYPE
    SYNTAX       SnmpAdminString
    MAX-ACCESS   read-only
    STATUS       current
    DESCRIPTION
        "Cisco Firepower sw:EthMonSrcEp:peerDn managed object property"
    ::= { cfprApSwEthMonSrcEpEntry 16 }

cfprApSwEthMonSrcEpPeerPortId OBJECT-TYPE
    SYNTAX       Gauge32
    MAX-ACCESS   read-only
    STATUS       current
    DESCRIPTION
        "Cisco Firepower sw:EthMonSrcEp:peerPortId managed
        object property"
    ::= { cfprApSwEthMonSrcEpEntry 17 }

cfprApSwEthMonSrcEpPeerSlotId OBJECT-TYPE
    SYNTAX       Gauge32
    MAX-ACCESS   read-only
    STATUS       current
    DESCRIPTION
        "Cisco Firepower sw:EthMonSrcEp:peerSlotId managed
        object property"
    ::= { cfprApSwEthMonSrcEpEntry 18 }

cfprApSwEthMonSrcEpPortId OBJECT-TYPE
    SYNTAX       Gauge32
    MAX-ACCESS   read-only
    STATUS       current
    DESCRIPTION
        "Cisco Firepower sw:EthMonSrcEp:portId managed object property"
    ::= { cfprApSwEthMonSrcEpEntry 19 }

cfprApSwEthMonSrcEpSlotId OBJECT-TYPE
    SYNTAX       Gauge32
    MAX-ACCESS   read-only
    STATUS       current
    DESCRIPTION
        "Cisco Firepower sw:EthMonSrcEp:slotId managed object property"
    ::= { cfprApSwEthMonSrcEpEntry 20 }

cfprApSwEthMonSrcEpSwitchId OBJECT-TYPE
    SYNTAX       CfprApNetworkSwitchId
    MAX-ACCESS   read-only
    STATUS       current
    DESCRIPTION
        "Cisco Firepower sw:EthMonSrcEp:switchId managed object property"
    ::= { cfprApSwEthMonSrcEpEntry 21 }

cfprApSwEthMonSrcEpTransport OBJECT-TYPE
    SYNTAX       CfprApSwEthMonSrcEpTransport
    MAX-ACCESS   read-only
    STATUS       current
    DESCRIPTION
        "Cisco Firepower sw:EthMonSrcEp:transport managed object property"
    ::= { cfprApSwEthMonSrcEpEntry 22 }

cfprApSwEthMonSrcEpType OBJECT-TYPE
    SYNTAX       CfprApNetworkConnectionType
    MAX-ACCESS   read-only
    STATUS       current
    DESCRIPTION
        "Cisco Firepower sw:EthMonSrcEp:type managed object property"
    ::= { cfprApSwEthMonSrcEpEntry 23 }

cfprApSwEthTargetEpTable OBJECT-TYPE
    SYNTAX           SEQUENCE OF CfprApSwEthTargetEpEntry
    MAX-ACCESS       not-accessible
    STATUS           current
    DESCRIPTION
        "Cisco Firepower sw:EthTargetEp managed object table"
    ::= { cfprApSwObjects 30 }

cfprApSwEthTargetEpEntry OBJECT-TYPE
    SYNTAX           CfprApSwEthTargetEpEntry
    MAX-ACCESS       not-accessible
    STATUS           current
    DESCRIPTION
        "Entry for the cfprApSwEthTargetEpTable table."
    INDEX { cfprApSwEthTargetEpInstanceId }
    ::= { cfprApSwEthTargetEpTable 1 }

CfprApSwEthTargetEpEntry ::= SEQUENCE {
    cfprApSwEthTargetEpInstanceId                                    CfprApManagedObjectId,
    cfprApSwEthTargetEpDn                                            CfprApManagedObjectDn,
    cfprApSwEthTargetEpRn                                            SnmpAdminString,
    cfprApSwEthTargetEpAdminState                                    CfprApSwEthTargetEpAdminState,
    cfprApSwEthTargetEpAggrPortId                                    Gauge32,
    cfprApSwEthTargetEpChassisId                                     Gauge32,
    cfprApSwEthTargetEpEpDn                                          SnmpAdminString,
    cfprApSwEthTargetEpFltAggr                                       Unsigned64,
    cfprApSwEthTargetEpIfRole                                        CfprApNetworkPortRole,
    cfprApSwEthTargetEpIfType                                        CfprApFabricPIoEpIfType,
    cfprApSwEthTargetEpLicGP                                         Unsigned64,
    cfprApSwEthTargetEpLicState                                      CfprApLicenseState,
    cfprApSwEthTargetEpLocale                                        CfprApFabricExternalEpLocale,
    cfprApSwEthTargetEpMacAddress                                    MacAddress,
    cfprApSwEthTargetEpName                                          SnmpAdminString,
    cfprApSwEthTargetEpOperState                                     CfprApFabricPIoEpOperState,
    cfprApSwEthTargetEpOperStateReason                               SnmpAdminString,
    cfprApSwEthTargetEpPeerAggrPortId                                Gauge32,
    cfprApSwEthTargetEpPeerChassisId                                 Gauge32,
    cfprApSwEthTargetEpPeerDn                                        SnmpAdminString,
    cfprApSwEthTargetEpPeerPortId                                    Gauge32,
    cfprApSwEthTargetEpPeerSlotId                                    Gauge32,
    cfprApSwEthTargetEpPortId                                        CfprApFabricPIoEpPortId,
    cfprApSwEthTargetEpSlotId                                        CfprApFabricPIoEpSlotId,
    cfprApSwEthTargetEpSwitchId                                      CfprApNetworkSwitchId,
    cfprApSwEthTargetEpTransport                                     CfprApSwEthTargetEpTransport,
    cfprApSwEthTargetEpType                                          CfprApSwTargetEpType,
    cfprApSwEthTargetEpWarnings                                      CfprApFabricWarnings
}

cfprApSwEthTargetEpInstanceId OBJECT-TYPE
    SYNTAX       CfprApManagedObjectId
    MAX-ACCESS   not-accessible
    STATUS       current
    DESCRIPTION
        "Instance identifier of the managed object."
    ::= { cfprApSwEthTargetEpEntry 1 }

cfprApSwEthTargetEpDn OBJECT-TYPE
    SYNTAX       CfprApManagedObjectDn
    MAX-ACCESS   read-only
    STATUS       current
    DESCRIPTION
        "Cisco Firepower sw:EthTargetEp:dn managed object property"
    ::= { cfprApSwEthTargetEpEntry 2 }

cfprApSwEthTargetEpRn OBJECT-TYPE
    SYNTAX       SnmpAdminString
    MAX-ACCESS   read-only
    STATUS       current
    DESCRIPTION
        "Cisco Firepower sw:EthTargetEp:rn managed object property"
    ::= { cfprApSwEthTargetEpEntry 3 }

cfprApSwEthTargetEpAdminState OBJECT-TYPE
    SYNTAX       CfprApSwEthTargetEpAdminState
    MAX-ACCESS   read-only
    STATUS       current
    DESCRIPTION
        "Cisco Firepower sw:EthTargetEp:adminState managed
        object property"
    ::= { cfprApSwEthTargetEpEntry 4 }

cfprApSwEthTargetEpAggrPortId OBJECT-TYPE
    SYNTAX       Gauge32
    MAX-ACCESS   read-only
    STATUS       current
    DESCRIPTION
        "Cisco Firepower sw:EthTargetEp:aggrPortId managed
        object property"
    ::= { cfprApSwEthTargetEpEntry 5 }

cfprApSwEthTargetEpChassisId OBJECT-TYPE
    SYNTAX       Gauge32
    MAX-ACCESS   read-only
    STATUS       current
    DESCRIPTION
        "Cisco Firepower sw:EthTargetEp:chassisId managed object property"
    ::= { cfprApSwEthTargetEpEntry 6 }

cfprApSwEthTargetEpEpDn OBJECT-TYPE
    SYNTAX       SnmpAdminString
    MAX-ACCESS   read-only
    STATUS       current
    DESCRIPTION
        "Cisco Firepower sw:EthTargetEp:epDn managed object property"
    ::= { cfprApSwEthTargetEpEntry 7 }

cfprApSwEthTargetEpFltAggr OBJECT-TYPE
    SYNTAX       Unsigned64
    MAX-ACCESS   read-only
    STATUS       current
    DESCRIPTION
        "Cisco Firepower sw:EthTargetEp:fltAggr managed object property"
    ::= { cfprApSwEthTargetEpEntry 8 }

cfprApSwEthTargetEpIfRole OBJECT-TYPE
    SYNTAX       CfprApNetworkPortRole
    MAX-ACCESS   read-only
    STATUS       current
    DESCRIPTION
        "Cisco Firepower sw:EthTargetEp:ifRole managed object property"
    ::= { cfprApSwEthTargetEpEntry 9 }

cfprApSwEthTargetEpIfType OBJECT-TYPE
    SYNTAX       CfprApFabricPIoEpIfType
    MAX-ACCESS   read-only
    STATUS       current
    DESCRIPTION
        "Cisco Firepower sw:EthTargetEp:ifType managed object property"
    ::= { cfprApSwEthTargetEpEntry 10 }

cfprApSwEthTargetEpLicGP OBJECT-TYPE
    SYNTAX       Unsigned64
    MAX-ACCESS   read-only
    STATUS       current
    DESCRIPTION
        "Cisco Firepower sw:EthTargetEp:licGP managed object property"
    ::= { cfprApSwEthTargetEpEntry 11 }

cfprApSwEthTargetEpLicState OBJECT-TYPE
    SYNTAX       CfprApLicenseState
    MAX-ACCESS   read-only
    STATUS       current
    DESCRIPTION
        "Cisco Firepower sw:EthTargetEp:licState managed object property"
    ::= { cfprApSwEthTargetEpEntry 12 }

cfprApSwEthTargetEpLocale OBJECT-TYPE
    SYNTAX       CfprApFabricExternalEpLocale
    MAX-ACCESS   read-only
    STATUS       current
    DESCRIPTION
        "Cisco Firepower sw:EthTargetEp:locale managed object property"
    ::= { cfprApSwEthTargetEpEntry 13 }

cfprApSwEthTargetEpMacAddress OBJECT-TYPE
    SYNTAX       MacAddress
    MAX-ACCESS   read-only
    STATUS       current
    DESCRIPTION
        "Cisco Firepower sw:EthTargetEp:macAddress managed
        object property"
    ::= { cfprApSwEthTargetEpEntry 14 }

cfprApSwEthTargetEpName OBJECT-TYPE
    SYNTAX       SnmpAdminString
    MAX-ACCESS   read-only
    STATUS       current
    DESCRIPTION
        "Cisco Firepower sw:EthTargetEp:name managed object property"
    ::= { cfprApSwEthTargetEpEntry 15 }

cfprApSwEthTargetEpOperState OBJECT-TYPE
    SYNTAX       CfprApFabricPIoEpOperState
    MAX-ACCESS   read-only
    STATUS       current
    DESCRIPTION
        "Cisco Firepower sw:EthTargetEp:operState managed object property"
    ::= { cfprApSwEthTargetEpEntry 16 }

cfprApSwEthTargetEpOperStateReason OBJECT-TYPE
    SYNTAX       SnmpAdminString
    MAX-ACCESS   read-only
    STATUS       current
    DESCRIPTION
        "Cisco Firepower sw:EthTargetEp:operStateReason
        managed object property"
    ::= { cfprApSwEthTargetEpEntry 17 }

cfprApSwEthTargetEpPeerAggrPortId OBJECT-TYPE
    SYNTAX       Gauge32
    MAX-ACCESS   read-only
    STATUS       current
    DESCRIPTION
        "Cisco Firepower sw:EthTargetEp:peerAggrPortId
        managed object property"
    ::= { cfprApSwEthTargetEpEntry 18 }

cfprApSwEthTargetEpPeerChassisId OBJECT-TYPE
    SYNTAX       Gauge32
    MAX-ACCESS   read-only
    STATUS       current
    DESCRIPTION
        "Cisco Firepower sw:EthTargetEp:peerChassisId managed
        object property"
    ::= { cfprApSwEthTargetEpEntry 19 }

cfprApSwEthTargetEpPeerDn OBJECT-TYPE
    SYNTAX       SnmpAdminString
    MAX-ACCESS   read-only
    STATUS       current
    DESCRIPTION
        "Cisco Firepower sw:EthTargetEp:peerDn managed object property"
    ::= { cfprApSwEthTargetEpEntry 20 }

cfprApSwEthTargetEpPeerPortId OBJECT-TYPE
    SYNTAX       Gauge32
    MAX-ACCESS   read-only
    STATUS       current
    DESCRIPTION
        "Cisco Firepower sw:EthTargetEp:peerPortId managed
        object property"
    ::= { cfprApSwEthTargetEpEntry 21 }

cfprApSwEthTargetEpPeerSlotId OBJECT-TYPE
    SYNTAX       Gauge32
    MAX-ACCESS   read-only
    STATUS       current
    DESCRIPTION
        "Cisco Firepower sw:EthTargetEp:peerSlotId managed
        object property"
    ::= { cfprApSwEthTargetEpEntry 22 }

cfprApSwEthTargetEpPortId OBJECT-TYPE
    SYNTAX       CfprApFabricPIoEpPortId
    MAX-ACCESS   read-only
    STATUS       current
    DESCRIPTION
        "Cisco Firepower sw:EthTargetEp:portId managed object property"
    ::= { cfprApSwEthTargetEpEntry 23 }

cfprApSwEthTargetEpSlotId OBJECT-TYPE
    SYNTAX       CfprApFabricPIoEpSlotId
    MAX-ACCESS   read-only
    STATUS       current
    DESCRIPTION
        "Cisco Firepower sw:EthTargetEp:slotId managed object property"
    ::= { cfprApSwEthTargetEpEntry 24 }

cfprApSwEthTargetEpSwitchId OBJECT-TYPE
    SYNTAX       CfprApNetworkSwitchId
    MAX-ACCESS   read-only
    STATUS       current
    DESCRIPTION
        "Cisco Firepower sw:EthTargetEp:switchId managed object property"
    ::= { cfprApSwEthTargetEpEntry 25 }

cfprApSwEthTargetEpTransport OBJECT-TYPE
    SYNTAX       CfprApSwEthTargetEpTransport
    MAX-ACCESS   read-only
    STATUS       current
    DESCRIPTION
        "Cisco Firepower sw:EthTargetEp:transport managed object property"
    ::= { cfprApSwEthTargetEpEntry 26 }

cfprApSwEthTargetEpType OBJECT-TYPE
    SYNTAX       CfprApSwTargetEpType
    MAX-ACCESS   read-only
    STATUS       current
    DESCRIPTION
        "Cisco Firepower sw:EthTargetEp:type managed object property"
    ::= { cfprApSwEthTargetEpEntry 27 }

cfprApSwEthTargetEpWarnings OBJECT-TYPE
    SYNTAX       CfprApFabricWarnings
    MAX-ACCESS   read-only
    STATUS       current
    DESCRIPTION
        "Cisco Firepower sw:EthTargetEp:warnings managed object property"
    ::= { cfprApSwEthTargetEpEntry 28 }

cfprApSwExtUtilityTable OBJECT-TYPE
    SYNTAX           SEQUENCE OF CfprApSwExtUtilityEntry
    MAX-ACCESS       not-accessible
    STATUS           current
    DESCRIPTION
        "Cisco Firepower sw:ExtUtility managed object table"
    ::= { cfprApSwObjects 31 }

cfprApSwExtUtilityEntry OBJECT-TYPE
    SYNTAX           CfprApSwExtUtilityEntry
    MAX-ACCESS       not-accessible
    STATUS           current
    DESCRIPTION
        "Entry for the cfprApSwExtUtilityTable table."
    INDEX { cfprApSwExtUtilityInstanceId }
    ::= { cfprApSwExtUtilityTable 1 }

CfprApSwExtUtilityEntry ::= SEQUENCE {
    cfprApSwExtUtilityInstanceId                                     CfprApManagedObjectId,
    cfprApSwExtUtilityDn                                             CfprApManagedObjectDn,
    cfprApSwExtUtilityRn                                             SnmpAdminString,
    cfprApSwExtUtilityConfMode                                       CfprApSwConfMode,
    cfprApSwExtUtilityFsmDescr                                       SnmpAdminString,
    cfprApSwExtUtilityFsmPrev                                        SnmpAdminString,
    cfprApSwExtUtilityFsmProgr                                       Gauge32,
    cfprApSwExtUtilityFsmRmtInvErrCode                               Gauge32,
    cfprApSwExtUtilityFsmRmtInvErrDescr                              SnmpAdminString,
    cfprApSwExtUtilityFsmRmtInvRslt                                  CfprApConditionRemoteInvRslt,
    cfprApSwExtUtilityFsmStageDescr                                  SnmpAdminString,
    cfprApSwExtUtilityFsmStamp                                       DateAndTime,
    cfprApSwExtUtilityFsmStatus                                      SnmpAdminString,
    cfprApSwExtUtilityFsmTry                                         Gauge32,
    cfprApSwExtUtilitySwitchId                                       CfprApNetworkSwitchId
}

cfprApSwExtUtilityInstanceId OBJECT-TYPE
    SYNTAX       CfprApManagedObjectId
    MAX-ACCESS   not-accessible
    STATUS       current
    DESCRIPTION
        "Instance identifier of the managed object."
    ::= { cfprApSwExtUtilityEntry 1 }

cfprApSwExtUtilityDn OBJECT-TYPE
    SYNTAX       CfprApManagedObjectDn
    MAX-ACCESS   read-only
    STATUS       current
    DESCRIPTION
        "Cisco Firepower sw:ExtUtility:dn managed object property"
    ::= { cfprApSwExtUtilityEntry 2 }

cfprApSwExtUtilityRn OBJECT-TYPE
    SYNTAX       SnmpAdminString
    MAX-ACCESS   read-only
    STATUS       current
    DESCRIPTION
        "Cisco Firepower sw:ExtUtility:rn managed object property"
    ::= { cfprApSwExtUtilityEntry 3 }

cfprApSwExtUtilityConfMode OBJECT-TYPE
    SYNTAX       CfprApSwConfMode
    MAX-ACCESS   read-only
    STATUS       current
    DESCRIPTION
        "Cisco Firepower sw:ExtUtility:confMode managed object property"
    ::= { cfprApSwExtUtilityEntry 4 }

cfprApSwExtUtilityFsmDescr OBJECT-TYPE
    SYNTAX       SnmpAdminString
    MAX-ACCESS   read-only
    STATUS       current
    DESCRIPTION
        "Cisco Firepower sw:ExtUtility:fsmDescr managed object property"
    ::= { cfprApSwExtUtilityEntry 5 }

cfprApSwExtUtilityFsmPrev OBJECT-TYPE
    SYNTAX       SnmpAdminString
    MAX-ACCESS   read-only
    STATUS       current
    DESCRIPTION
        "Cisco Firepower sw:ExtUtility:fsmPrev managed object property"
    ::= { cfprApSwExtUtilityEntry 6 }

cfprApSwExtUtilityFsmProgr OBJECT-TYPE
    SYNTAX       Gauge32
    MAX-ACCESS   read-only
    STATUS       current
    DESCRIPTION
        "Cisco Firepower sw:ExtUtility:fsmProgr managed object property"
    ::= { cfprApSwExtUtilityEntry 7 }

cfprApSwExtUtilityFsmRmtInvErrCode OBJECT-TYPE
    SYNTAX       Gauge32
    MAX-ACCESS   read-only
    STATUS       current
    DESCRIPTION
        "Cisco Firepower sw:ExtUtility:fsmRmtInvErrCode
        managed object property"
    ::= { cfprApSwExtUtilityEntry 8 }

cfprApSwExtUtilityFsmRmtInvErrDescr OBJECT-TYPE
    SYNTAX       SnmpAdminString
    MAX-ACCESS   read-only
    STATUS       current
    DESCRIPTION
        "Cisco Firepower sw:ExtUtility:fsmRmtInvErrDescr
        managed object property"
    ::= { cfprApSwExtUtilityEntry 9 }

cfprApSwExtUtilityFsmRmtInvRslt OBJECT-TYPE
    SYNTAX       CfprApConditionRemoteInvRslt
    MAX-ACCESS   read-only
    STATUS       current
    DESCRIPTION
        "Cisco Firepower sw:ExtUtility:fsmRmtInvRslt managed
        object property"
    ::= { cfprApSwExtUtilityEntry 10 }

cfprApSwExtUtilityFsmStageDescr OBJECT-TYPE
    SYNTAX       SnmpAdminString
    MAX-ACCESS   read-only
    STATUS       current
    DESCRIPTION
        "Cisco Firepower sw:ExtUtility:fsmStageDescr managed
        object property"
    ::= { cfprApSwExtUtilityEntry 11 }

cfprApSwExtUtilityFsmStamp OBJECT-TYPE
    SYNTAX       DateAndTime
    MAX-ACCESS   read-only
    STATUS       current
    DESCRIPTION
        "Cisco Firepower sw:ExtUtility:fsmStamp managed object property"
    ::= { cfprApSwExtUtilityEntry 12 }

cfprApSwExtUtilityFsmStatus OBJECT-TYPE
    SYNTAX       SnmpAdminString
    MAX-ACCESS   read-only
    STATUS       current
    DESCRIPTION
        "Cisco Firepower sw:ExtUtility:fsmStatus managed object property"
    ::= { cfprApSwExtUtilityEntry 13 }

cfprApSwExtUtilityFsmTry OBJECT-TYPE
    SYNTAX       Gauge32
    MAX-ACCESS   read-only
    STATUS       current
    DESCRIPTION
        "Cisco Firepower sw:ExtUtility:fsmTry managed object property"
    ::= { cfprApSwExtUtilityEntry 14 }

cfprApSwExtUtilitySwitchId OBJECT-TYPE
    SYNTAX       CfprApNetworkSwitchId
    MAX-ACCESS   read-only
    STATUS       current
    DESCRIPTION
        "Cisco Firepower sw:ExtUtility:switchId managed object property"
    ::= { cfprApSwExtUtilityEntry 15 }

cfprApSwExtUtilityFsmTable OBJECT-TYPE
    SYNTAX           SEQUENCE OF CfprApSwExtUtilityFsmEntry
    MAX-ACCESS       not-accessible
    STATUS           current
    DESCRIPTION
        "Cisco Firepower sw:ExtUtilityFsm managed object table"
    ::= { cfprApSwObjects 32 }

cfprApSwExtUtilityFsmEntry OBJECT-TYPE
    SYNTAX           CfprApSwExtUtilityFsmEntry
    MAX-ACCESS       not-accessible
    STATUS           current
    DESCRIPTION
        "Entry for the cfprApSwExtUtilityFsmTable table."
    INDEX { cfprApSwExtUtilityFsmInstanceId }
    ::= { cfprApSwExtUtilityFsmTable 1 }

CfprApSwExtUtilityFsmEntry ::= SEQUENCE {
    cfprApSwExtUtilityFsmInstanceId                                  CfprApManagedObjectId,
    cfprApSwExtUtilityFsmDn                                          CfprApManagedObjectDn,
    cfprApSwExtUtilityFsmRn                                          SnmpAdminString,
    cfprApSwExtUtilityFsmCompletionTime                              DateAndTime,
    cfprApSwExtUtilityFsmCurrentFsm                                  CfprApSwExtUtilityFsmCurrentFsm,
    cfprApSwExtUtilityFsmDescrData                                   SnmpAdminString,
    cfprApSwExtUtilityFsmFsmStatus                                   CfprApFsmFsmStageStatus,
    cfprApSwExtUtilityFsmProgress                                    Gauge32,
    cfprApSwExtUtilityFsmRmtErrCode                                  Gauge32,
    cfprApSwExtUtilityFsmRmtErrDescr                                 SnmpAdminString,
    cfprApSwExtUtilityFsmRmtRslt                                     CfprApConditionRemoteInvRslt
}

cfprApSwExtUtilityFsmInstanceId OBJECT-TYPE
    SYNTAX       CfprApManagedObjectId
    MAX-ACCESS   not-accessible
    STATUS       current
    DESCRIPTION
        "Instance identifier of the managed object."
    ::= { cfprApSwExtUtilityFsmEntry 1 }

cfprApSwExtUtilityFsmDn OBJECT-TYPE
    SYNTAX       CfprApManagedObjectDn
    MAX-ACCESS   read-only
    STATUS       current
    DESCRIPTION
        "Cisco Firepower sw:ExtUtilityFsm:dn managed object property"
    ::= { cfprApSwExtUtilityFsmEntry 2 }

cfprApSwExtUtilityFsmRn OBJECT-TYPE
    SYNTAX       SnmpAdminString
    MAX-ACCESS   read-only
    STATUS       current
    DESCRIPTION
        "Cisco Firepower sw:ExtUtilityFsm:rn managed object property"
    ::= { cfprApSwExtUtilityFsmEntry 3 }

cfprApSwExtUtilityFsmCompletionTime OBJECT-TYPE
    SYNTAX       DateAndTime
    MAX-ACCESS   read-only
    STATUS       current
    DESCRIPTION
        "Cisco Firepower sw:ExtUtilityFsm:completionTime
        managed object property"
    ::= { cfprApSwExtUtilityFsmEntry 4 }

cfprApSwExtUtilityFsmCurrentFsm OBJECT-TYPE
    SYNTAX       CfprApSwExtUtilityFsmCurrentFsm
    MAX-ACCESS   read-only
    STATUS       current
    DESCRIPTION
        "Cisco Firepower sw:ExtUtilityFsm:currentFsm managed
        object property"
    ::= { cfprApSwExtUtilityFsmEntry 5 }

cfprApSwExtUtilityFsmDescrData OBJECT-TYPE
    SYNTAX       SnmpAdminString
    MAX-ACCESS   read-only
    STATUS       current
    DESCRIPTION
        "Cisco Firepower sw:ExtUtilityFsm:descr managed object property"
    ::= { cfprApSwExtUtilityFsmEntry 6 }

cfprApSwExtUtilityFsmFsmStatus OBJECT-TYPE
    SYNTAX       CfprApFsmFsmStageStatus
    MAX-ACCESS   read-only
    STATUS       current
    DESCRIPTION
        "Cisco Firepower sw:ExtUtilityFsm:fsmStatus managed
        object property"
    ::= { cfprApSwExtUtilityFsmEntry 7 }

cfprApSwExtUtilityFsmProgress OBJECT-TYPE
    SYNTAX       Gauge32
    MAX-ACCESS   read-only
    STATUS       current
    DESCRIPTION
        "Cisco Firepower sw:ExtUtilityFsm:progress managed
        object property"
    ::= { cfprApSwExtUtilityFsmEntry 8 }

cfprApSwExtUtilityFsmRmtErrCode OBJECT-TYPE
    SYNTAX       Gauge32
    MAX-ACCESS   read-only
    STATUS       current
    DESCRIPTION
        "Cisco Firepower sw:ExtUtilityFsm:rmtErrCode managed
        object property"
    ::= { cfprApSwExtUtilityFsmEntry 9 }

cfprApSwExtUtilityFsmRmtErrDescr OBJECT-TYPE
    SYNTAX       SnmpAdminString
    MAX-ACCESS   read-only
    STATUS       current
    DESCRIPTION
        "Cisco Firepower sw:ExtUtilityFsm:rmtErrDescr managed
        object property"
    ::= { cfprApSwExtUtilityFsmEntry 10 }

cfprApSwExtUtilityFsmRmtRslt OBJECT-TYPE
    SYNTAX       CfprApConditionRemoteInvRslt
    MAX-ACCESS   read-only
    STATUS       current
    DESCRIPTION
        "Cisco Firepower sw:ExtUtilityFsm:rmtRslt managed object property"
    ::= { cfprApSwExtUtilityFsmEntry 11 }

cfprApSwExtUtilityFsmStageTable OBJECT-TYPE
    SYNTAX           SEQUENCE OF CfprApSwExtUtilityFsmStageEntry
    MAX-ACCESS       not-accessible
    STATUS           current
    DESCRIPTION
        "Cisco Firepower sw:ExtUtilityFsmStage managed object table"
    ::= { cfprApSwObjects 33 }

cfprApSwExtUtilityFsmStageEntry OBJECT-TYPE
    SYNTAX           CfprApSwExtUtilityFsmStageEntry
    MAX-ACCESS       not-accessible
    STATUS           current
    DESCRIPTION
        "Entry for the cfprApSwExtUtilityFsmStageTable table."
    INDEX { cfprApSwExtUtilityFsmStageInstanceId }
    ::= { cfprApSwExtUtilityFsmStageTable 1 }

CfprApSwExtUtilityFsmStageEntry ::= SEQUENCE {
    cfprApSwExtUtilityFsmStageInstanceId                             CfprApManagedObjectId,
    cfprApSwExtUtilityFsmStageDn                                     CfprApManagedObjectDn,
    cfprApSwExtUtilityFsmStageRn                                     SnmpAdminString,
    cfprApSwExtUtilityFsmStageDescrData                              SnmpAdminString,
    cfprApSwExtUtilityFsmStageLastUpdateTime                         DateAndTime,
    cfprApSwExtUtilityFsmStageName                                   CfprApSwExtUtilityFsmStageName,
    cfprApSwExtUtilityFsmStageOrder                                  Gauge32,
    cfprApSwExtUtilityFsmStageRetry                                  Gauge32,
    cfprApSwExtUtilityFsmStageStageStatus                            CfprApFsmFsmStageStatus
}

cfprApSwExtUtilityFsmStageInstanceId OBJECT-TYPE
    SYNTAX       CfprApManagedObjectId
    MAX-ACCESS   not-accessible
    STATUS       current
    DESCRIPTION
        "Instance identifier of the managed object."
    ::= { cfprApSwExtUtilityFsmStageEntry 1 }

cfprApSwExtUtilityFsmStageDn OBJECT-TYPE
    SYNTAX       CfprApManagedObjectDn
    MAX-ACCESS   read-only
    STATUS       current
    DESCRIPTION
        "Cisco Firepower sw:ExtUtilityFsmStage:dn managed object property"
    ::= { cfprApSwExtUtilityFsmStageEntry 2 }

cfprApSwExtUtilityFsmStageRn OBJECT-TYPE
    SYNTAX       SnmpAdminString
    MAX-ACCESS   read-only
    STATUS       current
    DESCRIPTION
        "Cisco Firepower sw:ExtUtilityFsmStage:rn managed object property"
    ::= { cfprApSwExtUtilityFsmStageEntry 3 }

cfprApSwExtUtilityFsmStageDescrData OBJECT-TYPE
    SYNTAX       SnmpAdminString
    MAX-ACCESS   read-only
    STATUS       current
    DESCRIPTION
        "Cisco Firepower sw:ExtUtilityFsmStage:descr managed
        object property"
    ::= { cfprApSwExtUtilityFsmStageEntry 4 }

cfprApSwExtUtilityFsmStageLastUpdateTime OBJECT-TYPE
    SYNTAX       DateAndTime
    MAX-ACCESS   read-only
    STATUS       current
    DESCRIPTION
        "Cisco Firepower sw:ExtUtilityFsmStage:lastUpdateTime
        managed object property"
    ::= { cfprApSwExtUtilityFsmStageEntry 5 }

cfprApSwExtUtilityFsmStageName OBJECT-TYPE
    SYNTAX       CfprApSwExtUtilityFsmStageName
    MAX-ACCESS   read-only
    STATUS       current
    DESCRIPTION
        "Cisco Firepower sw:ExtUtilityFsmStage:name managed
        object property"
    ::= { cfprApSwExtUtilityFsmStageEntry 6 }

cfprApSwExtUtilityFsmStageOrder OBJECT-TYPE
    SYNTAX       Gauge32
    MAX-ACCESS   read-only
    STATUS       current
    DESCRIPTION
        "Cisco Firepower sw:ExtUtilityFsmStage:order managed
        object property"
    ::= { cfprApSwExtUtilityFsmStageEntry 7 }

cfprApSwExtUtilityFsmStageRetry OBJECT-TYPE
    SYNTAX       Gauge32
    MAX-ACCESS   read-only
    STATUS       current
    DESCRIPTION
        "Cisco Firepower sw:ExtUtilityFsmStage:retry managed
        object property"
    ::= { cfprApSwExtUtilityFsmStageEntry 8 }

cfprApSwExtUtilityFsmStageStageStatus OBJECT-TYPE
    SYNTAX       CfprApFsmFsmStageStatus
    MAX-ACCESS   read-only
    STATUS       current
    DESCRIPTION
        "Cisco Firepower sw:ExtUtilityFsmStage:stageStatus
        managed object property"
    ::= { cfprApSwExtUtilityFsmStageEntry 9 }

cfprApSwExtUtilityFsmTaskTable OBJECT-TYPE
    SYNTAX           SEQUENCE OF CfprApSwExtUtilityFsmTaskEntry
    MAX-ACCESS       not-accessible
    STATUS           current
    DESCRIPTION
        "Cisco Firepower sw:ExtUtilityFsmTask managed object table"
    ::= { cfprApSwObjects 34 }

cfprApSwExtUtilityFsmTaskEntry OBJECT-TYPE
    SYNTAX           CfprApSwExtUtilityFsmTaskEntry
    MAX-ACCESS       not-accessible
    STATUS           current
    DESCRIPTION
        "Entry for the cfprApSwExtUtilityFsmTaskTable table."
    INDEX { cfprApSwExtUtilityFsmTaskInstanceId }
    ::= { cfprApSwExtUtilityFsmTaskTable 1 }

CfprApSwExtUtilityFsmTaskEntry ::= SEQUENCE {
    cfprApSwExtUtilityFsmTaskInstanceId                              CfprApManagedObjectId,
    cfprApSwExtUtilityFsmTaskDn                                      CfprApManagedObjectDn,
    cfprApSwExtUtilityFsmTaskRn                                      SnmpAdminString,
    cfprApSwExtUtilityFsmTaskCompletion                              CfprApFsmCompletion,
    cfprApSwExtUtilityFsmTaskFlags                                   CfprApFsmFlags,
    cfprApSwExtUtilityFsmTaskItem                                    CfprApSwExtUtilityFsmTaskItem,
    cfprApSwExtUtilityFsmTaskSeqId                                   Gauge32
}

cfprApSwExtUtilityFsmTaskInstanceId OBJECT-TYPE
    SYNTAX       CfprApManagedObjectId
    MAX-ACCESS   not-accessible
    STATUS       current
    DESCRIPTION
        "Instance identifier of the managed object."
    ::= { cfprApSwExtUtilityFsmTaskEntry 1 }

cfprApSwExtUtilityFsmTaskDn OBJECT-TYPE
    SYNTAX       CfprApManagedObjectDn
    MAX-ACCESS   read-only
    STATUS       current
    DESCRIPTION
        "Cisco Firepower sw:ExtUtilityFsmTask:dn managed object property"
    ::= { cfprApSwExtUtilityFsmTaskEntry 2 }

cfprApSwExtUtilityFsmTaskRn OBJECT-TYPE
    SYNTAX       SnmpAdminString
    MAX-ACCESS   read-only
    STATUS       current
    DESCRIPTION
        "Cisco Firepower sw:ExtUtilityFsmTask:rn managed object property"
    ::= { cfprApSwExtUtilityFsmTaskEntry 3 }

cfprApSwExtUtilityFsmTaskCompletion OBJECT-TYPE
    SYNTAX       CfprApFsmCompletion
    MAX-ACCESS   read-only
    STATUS       current
    DESCRIPTION
        "Cisco Firepower sw:ExtUtilityFsmTask:completion
        managed object property"
    ::= { cfprApSwExtUtilityFsmTaskEntry 4 }

cfprApSwExtUtilityFsmTaskFlags OBJECT-TYPE
    SYNTAX       CfprApFsmFlags
    MAX-ACCESS   read-only
    STATUS       current
    DESCRIPTION
        "Cisco Firepower sw:ExtUtilityFsmTask:flags managed
        object property"
    ::= { cfprApSwExtUtilityFsmTaskEntry 5 }

cfprApSwExtUtilityFsmTaskItem OBJECT-TYPE
    SYNTAX       CfprApSwExtUtilityFsmTaskItem
    MAX-ACCESS   read-only
    STATUS       current
    DESCRIPTION
        "Cisco Firepower sw:ExtUtilityFsmTask:item managed
        object property"
    ::= { cfprApSwExtUtilityFsmTaskEntry 6 }

cfprApSwExtUtilityFsmTaskSeqId OBJECT-TYPE
    SYNTAX       Gauge32
    MAX-ACCESS   read-only
    STATUS       current
    DESCRIPTION
        "Cisco Firepower sw:ExtUtilityFsmTask:seqId managed
        object property"
    ::= { cfprApSwExtUtilityFsmTaskEntry 7 }

cfprApSwFabricZoneNsTable OBJECT-TYPE
    SYNTAX           SEQUENCE OF CfprApSwFabricZoneNsEntry
    MAX-ACCESS       not-accessible
    STATUS           current
    DESCRIPTION
        "Cisco Firepower sw:FabricZoneNs managed object table"
    ::= { cfprApSwObjects 35 }

cfprApSwFabricZoneNsEntry OBJECT-TYPE
    SYNTAX           CfprApSwFabricZoneNsEntry
    MAX-ACCESS       not-accessible
    STATUS           current
    DESCRIPTION
        "Entry for the cfprApSwFabricZoneNsTable table."
    INDEX { cfprApSwFabricZoneNsInstanceId }
    ::= { cfprApSwFabricZoneNsTable 1 }

CfprApSwFabricZoneNsEntry ::= SEQUENCE {
    cfprApSwFabricZoneNsInstanceId                                   CfprApManagedObjectId,
    cfprApSwFabricZoneNsDn                                           CfprApManagedObjectDn,
    cfprApSwFabricZoneNsRn                                           SnmpAdminString,
    cfprApSwFabricZoneNsAllocStatus                                  CfprApSwFabricZoneNsAllocStatus,
    cfprApSwFabricZoneNsLimit                                        Gauge32,
    cfprApSwFabricZoneNsSwitchId                                     CfprApNetworkSwitchId,
    cfprApSwFabricZoneNsZoneCount                                    Gauge32
}

cfprApSwFabricZoneNsInstanceId OBJECT-TYPE
    SYNTAX       CfprApManagedObjectId
    MAX-ACCESS   not-accessible
    STATUS       current
    DESCRIPTION
        "Instance identifier of the managed object."
    ::= { cfprApSwFabricZoneNsEntry 1 }

cfprApSwFabricZoneNsDn OBJECT-TYPE
    SYNTAX       CfprApManagedObjectDn
    MAX-ACCESS   read-only
    STATUS       current
    DESCRIPTION
        "Cisco Firepower sw:FabricZoneNs:dn managed object property"
    ::= { cfprApSwFabricZoneNsEntry 2 }

cfprApSwFabricZoneNsRn OBJECT-TYPE
    SYNTAX       SnmpAdminString
    MAX-ACCESS   read-only
    STATUS       current
    DESCRIPTION
        "Cisco Firepower sw:FabricZoneNs:rn managed object property"
    ::= { cfprApSwFabricZoneNsEntry 3 }

cfprApSwFabricZoneNsAllocStatus OBJECT-TYPE
    SYNTAX       CfprApSwFabricZoneNsAllocStatus
    MAX-ACCESS   read-only
    STATUS       current
    DESCRIPTION
        "Cisco Firepower sw:FabricZoneNs:allocStatus managed
        object property"
    ::= { cfprApSwFabricZoneNsEntry 4 }

cfprApSwFabricZoneNsLimit OBJECT-TYPE
    SYNTAX       Gauge32
    MAX-ACCESS   read-only
    STATUS       current
    DESCRIPTION
        "Cisco Firepower sw:FabricZoneNs:limit managed object property"
    ::= { cfprApSwFabricZoneNsEntry 5 }

cfprApSwFabricZoneNsSwitchId OBJECT-TYPE
    SYNTAX       CfprApNetworkSwitchId
    MAX-ACCESS   read-only
    STATUS       current
    DESCRIPTION
        "Cisco Firepower sw:FabricZoneNs:switchId managed object property"
    ::= { cfprApSwFabricZoneNsEntry 6 }

cfprApSwFabricZoneNsZoneCount OBJECT-TYPE
    SYNTAX       Gauge32
    MAX-ACCESS   read-only
    STATUS       current
    DESCRIPTION
        "Cisco Firepower sw:FabricZoneNs:zoneCount managed
        object property"
    ::= { cfprApSwFabricZoneNsEntry 7 }

cfprApSwFabricZoneNsOverrideTable OBJECT-TYPE
    SYNTAX           SEQUENCE OF CfprApSwFabricZoneNsOverrideEntry
    MAX-ACCESS       not-accessible
    STATUS           current
    DESCRIPTION
        "Cisco Firepower sw:FabricZoneNsOverride managed object table"
    ::= { cfprApSwObjects 36 }

cfprApSwFabricZoneNsOverrideEntry OBJECT-TYPE
    SYNTAX           CfprApSwFabricZoneNsOverrideEntry
    MAX-ACCESS       not-accessible
    STATUS           current
    DESCRIPTION
        "Entry for the cfprApSwFabricZoneNsOverrideTable table."
    INDEX { cfprApSwFabricZoneNsOverrideInstanceId }
    ::= { cfprApSwFabricZoneNsOverrideTable 1 }

CfprApSwFabricZoneNsOverrideEntry ::= SEQUENCE {
    cfprApSwFabricZoneNsOverrideInstanceId                           CfprApManagedObjectId,
    cfprApSwFabricZoneNsOverrideDn                                   CfprApManagedObjectDn,
    cfprApSwFabricZoneNsOverrideRn                                   SnmpAdminString,
    cfprApSwFabricZoneNsOverrideLimit                                Gauge32
}

cfprApSwFabricZoneNsOverrideInstanceId OBJECT-TYPE
    SYNTAX       CfprApManagedObjectId
    MAX-ACCESS   not-accessible
    STATUS       current
    DESCRIPTION
        "Instance identifier of the managed object."
    ::= { cfprApSwFabricZoneNsOverrideEntry 1 }

cfprApSwFabricZoneNsOverrideDn OBJECT-TYPE
    SYNTAX       CfprApManagedObjectDn
    MAX-ACCESS   read-only
    STATUS       current
    DESCRIPTION
        "Cisco Firepower sw:FabricZoneNsOverride:dn managed
        object property"
    ::= { cfprApSwFabricZoneNsOverrideEntry 2 }

cfprApSwFabricZoneNsOverrideRn OBJECT-TYPE
    SYNTAX       SnmpAdminString
    MAX-ACCESS   read-only
    STATUS       current
    DESCRIPTION
        "Cisco Firepower sw:FabricZoneNsOverride:rn managed
        object property"
    ::= { cfprApSwFabricZoneNsOverrideEntry 3 }

cfprApSwFabricZoneNsOverrideLimit OBJECT-TYPE
    SYNTAX       Gauge32
    MAX-ACCESS   read-only
    STATUS       current
    DESCRIPTION
        "Cisco Firepower sw:FabricZoneNsOverride:limit
        managed object property"
    ::= { cfprApSwFabricZoneNsOverrideEntry 4 }

cfprApSwFcSanBorderTable OBJECT-TYPE
    SYNTAX           SEQUENCE OF CfprApSwFcSanBorderEntry
    MAX-ACCESS       not-accessible
    STATUS           current
    DESCRIPTION
        "Cisco Firepower sw:FcSanBorder managed object table"
    ::= { cfprApSwObjects 44 }

cfprApSwFcSanBorderEntry OBJECT-TYPE
    SYNTAX           CfprApSwFcSanBorderEntry
    MAX-ACCESS       not-accessible
    STATUS           current
    DESCRIPTION
        "Entry for the cfprApSwFcSanBorderTable table."
    INDEX { cfprApSwFcSanBorderInstanceId }
    ::= { cfprApSwFcSanBorderTable 1 }

CfprApSwFcSanBorderEntry ::= SEQUENCE {
    cfprApSwFcSanBorderInstanceId                                    CfprApManagedObjectId,
    cfprApSwFcSanBorderDn                                            CfprApManagedObjectDn,
    cfprApSwFcSanBorderRn                                            SnmpAdminString,
    cfprApSwFcSanBorderFsmDescr                                      SnmpAdminString,
    cfprApSwFcSanBorderFsmPrev                                       SnmpAdminString,
    cfprApSwFcSanBorderFsmProgr                                      Gauge32,
    cfprApSwFcSanBorderFsmRmtInvErrCode                              Gauge32,
    cfprApSwFcSanBorderFsmRmtInvErrDescr                             SnmpAdminString,
    cfprApSwFcSanBorderFsmRmtInvRslt                                 CfprApConditionRemoteInvRslt,
    cfprApSwFcSanBorderFsmStageDescr                                 SnmpAdminString,
    cfprApSwFcSanBorderFsmStamp                                      DateAndTime,
    cfprApSwFcSanBorderFsmStatus                                     SnmpAdminString,
    cfprApSwFcSanBorderFsmTry                                        Gauge32,
    cfprApSwFcSanBorderLocale                                        CfprApSwBorderDomainLocale,
    cfprApSwFcSanBorderName                                          SnmpAdminString,
    cfprApSwFcSanBorderSwitchId                                      CfprApNetworkSwitchId,
    cfprApSwFcSanBorderTransport                                     CfprApSwFcSanBorderTransport,
    cfprApSwFcSanBorderType                                          CfprApSwSanBorderType,
    cfprApSwFcSanBorderUplinkTrunking                                CfprApSwFcSanBorderUplinkTrunking
}

cfprApSwFcSanBorderInstanceId OBJECT-TYPE
    SYNTAX       CfprApManagedObjectId
    MAX-ACCESS   not-accessible
    STATUS       current
    DESCRIPTION
        "Instance identifier of the managed object."
    ::= { cfprApSwFcSanBorderEntry 1 }

cfprApSwFcSanBorderDn OBJECT-TYPE
    SYNTAX       CfprApManagedObjectDn
    MAX-ACCESS   read-only
    STATUS       current
    DESCRIPTION
        "Cisco Firepower sw:FcSanBorder:dn managed object property"
    ::= { cfprApSwFcSanBorderEntry 2 }

cfprApSwFcSanBorderRn OBJECT-TYPE
    SYNTAX       SnmpAdminString
    MAX-ACCESS   read-only
    STATUS       current
    DESCRIPTION
        "Cisco Firepower sw:FcSanBorder:rn managed object property"
    ::= { cfprApSwFcSanBorderEntry 3 }

cfprApSwFcSanBorderFsmDescr OBJECT-TYPE
    SYNTAX       SnmpAdminString
    MAX-ACCESS   read-only
    STATUS       current
    DESCRIPTION
        "Cisco Firepower sw:FcSanBorder:fsmDescr managed object property"
    ::= { cfprApSwFcSanBorderEntry 4 }

cfprApSwFcSanBorderFsmPrev OBJECT-TYPE
    SYNTAX       SnmpAdminString
    MAX-ACCESS   read-only
    STATUS       current
    DESCRIPTION
        "Cisco Firepower sw:FcSanBorder:fsmPrev managed object property"
    ::= { cfprApSwFcSanBorderEntry 5 }

cfprApSwFcSanBorderFsmProgr OBJECT-TYPE
    SYNTAX       Gauge32
    MAX-ACCESS   read-only
    STATUS       current
    DESCRIPTION
        "Cisco Firepower sw:FcSanBorder:fsmProgr managed object property"
    ::= { cfprApSwFcSanBorderEntry 6 }

cfprApSwFcSanBorderFsmRmtInvErrCode OBJECT-TYPE
    SYNTAX       Gauge32
    MAX-ACCESS   read-only
    STATUS       current
    DESCRIPTION
        "Cisco Firepower sw:FcSanBorder:fsmRmtInvErrCode
        managed object property"
    ::= { cfprApSwFcSanBorderEntry 7 }

cfprApSwFcSanBorderFsmRmtInvErrDescr OBJECT-TYPE
    SYNTAX       SnmpAdminString
    MAX-ACCESS   read-only
    STATUS       current
    DESCRIPTION
        "Cisco Firepower sw:FcSanBorder:fsmRmtInvErrDescr
        managed object property"
    ::= { cfprApSwFcSanBorderEntry 8 }

cfprApSwFcSanBorderFsmRmtInvRslt OBJECT-TYPE
    SYNTAX       CfprApConditionRemoteInvRslt
    MAX-ACCESS   read-only
    STATUS       current
    DESCRIPTION
        "Cisco Firepower sw:FcSanBorder:fsmRmtInvRslt managed
        object property"
    ::= { cfprApSwFcSanBorderEntry 9 }

cfprApSwFcSanBorderFsmStageDescr OBJECT-TYPE
    SYNTAX       SnmpAdminString
    MAX-ACCESS   read-only
    STATUS       current
    DESCRIPTION
        "Cisco Firepower sw:FcSanBorder:fsmStageDescr managed
        object property"
    ::= { cfprApSwFcSanBorderEntry 10 }

cfprApSwFcSanBorderFsmStamp OBJECT-TYPE
    SYNTAX       DateAndTime
    MAX-ACCESS   read-only
    STATUS       current
    DESCRIPTION
        "Cisco Firepower sw:FcSanBorder:fsmStamp managed object property"
    ::= { cfprApSwFcSanBorderEntry 11 }

cfprApSwFcSanBorderFsmStatus OBJECT-TYPE
    SYNTAX       SnmpAdminString
    MAX-ACCESS   read-only
    STATUS       current
    DESCRIPTION
        "Cisco Firepower sw:FcSanBorder:fsmStatus managed object property"
    ::= { cfprApSwFcSanBorderEntry 12 }

cfprApSwFcSanBorderFsmTry OBJECT-TYPE
    SYNTAX       Gauge32
    MAX-ACCESS   read-only
    STATUS       current
    DESCRIPTION
        "Cisco Firepower sw:FcSanBorder:fsmTry managed object property"
    ::= { cfprApSwFcSanBorderEntry 13 }

cfprApSwFcSanBorderLocale OBJECT-TYPE
    SYNTAX       CfprApSwBorderDomainLocale
    MAX-ACCESS   read-only
    STATUS       current
    DESCRIPTION
        "Cisco Firepower sw:FcSanBorder:locale managed object property"
    ::= { cfprApSwFcSanBorderEntry 14 }

cfprApSwFcSanBorderName OBJECT-TYPE
    SYNTAX       SnmpAdminString
    MAX-ACCESS   read-only
    STATUS       current
    DESCRIPTION
        "Cisco Firepower sw:FcSanBorder:name managed object property"
    ::= { cfprApSwFcSanBorderEntry 15 }

cfprApSwFcSanBorderSwitchId OBJECT-TYPE
    SYNTAX       CfprApNetworkSwitchId
    MAX-ACCESS   read-only
    STATUS       current
    DESCRIPTION
        "Cisco Firepower sw:FcSanBorder:switchId managed object property"
    ::= { cfprApSwFcSanBorderEntry 16 }

cfprApSwFcSanBorderTransport OBJECT-TYPE
    SYNTAX       CfprApSwFcSanBorderTransport
    MAX-ACCESS   read-only
    STATUS       current
    DESCRIPTION
        "Cisco Firepower sw:FcSanBorder:transport managed object property"
    ::= { cfprApSwFcSanBorderEntry 17 }

cfprApSwFcSanBorderType OBJECT-TYPE
    SYNTAX       CfprApSwSanBorderType
    MAX-ACCESS   read-only
    STATUS       current
    DESCRIPTION
        "Cisco Firepower sw:FcSanBorder:type managed object property"
    ::= { cfprApSwFcSanBorderEntry 18 }

cfprApSwFcSanBorderUplinkTrunking OBJECT-TYPE
    SYNTAX       CfprApSwFcSanBorderUplinkTrunking
    MAX-ACCESS   read-only
    STATUS       current
    DESCRIPTION
        "Cisco Firepower sw:FcSanBorder:uplinkTrunking
        managed object property"
    ::= { cfprApSwFcSanBorderEntry 19 }

cfprApSwFcSanBorderFsmTable OBJECT-TYPE
    SYNTAX           SEQUENCE OF CfprApSwFcSanBorderFsmEntry
    MAX-ACCESS       not-accessible
    STATUS           current
    DESCRIPTION
        "Cisco Firepower sw:FcSanBorderFsm managed object table"
    ::= { cfprApSwObjects 45 }

cfprApSwFcSanBorderFsmEntry OBJECT-TYPE
    SYNTAX           CfprApSwFcSanBorderFsmEntry
    MAX-ACCESS       not-accessible
    STATUS           current
    DESCRIPTION
        "Entry for the cfprApSwFcSanBorderFsmTable table."
    INDEX { cfprApSwFcSanBorderFsmInstanceId }
    ::= { cfprApSwFcSanBorderFsmTable 1 }

CfprApSwFcSanBorderFsmEntry ::= SEQUENCE {
    cfprApSwFcSanBorderFsmInstanceId                                 CfprApManagedObjectId,
    cfprApSwFcSanBorderFsmDn                                         CfprApManagedObjectDn,
    cfprApSwFcSanBorderFsmRn                                         SnmpAdminString,
    cfprApSwFcSanBorderFsmCompletionTime                             DateAndTime,
    cfprApSwFcSanBorderFsmCurrentFsm                                 CfprApSwFcSanBorderFsmCurrentFsm,
    cfprApSwFcSanBorderFsmDescrData                                  SnmpAdminString,
    cfprApSwFcSanBorderFsmFsmStatus                                  CfprApFsmFsmStageStatus,
    cfprApSwFcSanBorderFsmProgress                                   Gauge32,
    cfprApSwFcSanBorderFsmRmtErrCode                                 Gauge32,
    cfprApSwFcSanBorderFsmRmtErrDescr                                SnmpAdminString,
    cfprApSwFcSanBorderFsmRmtRslt                                    CfprApConditionRemoteInvRslt
}

cfprApSwFcSanBorderFsmInstanceId OBJECT-TYPE
    SYNTAX       CfprApManagedObjectId
    MAX-ACCESS   not-accessible
    STATUS       current
    DESCRIPTION
        "Instance identifier of the managed object."
    ::= { cfprApSwFcSanBorderFsmEntry 1 }

cfprApSwFcSanBorderFsmDn OBJECT-TYPE
    SYNTAX       CfprApManagedObjectDn
    MAX-ACCESS   read-only
    STATUS       current
    DESCRIPTION
        "Cisco Firepower sw:FcSanBorderFsm:dn managed object property"
    ::= { cfprApSwFcSanBorderFsmEntry 2 }

cfprApSwFcSanBorderFsmRn OBJECT-TYPE
    SYNTAX       SnmpAdminString
    MAX-ACCESS   read-only
    STATUS       current
    DESCRIPTION
        "Cisco Firepower sw:FcSanBorderFsm:rn managed object property"
    ::= { cfprApSwFcSanBorderFsmEntry 3 }

cfprApSwFcSanBorderFsmCompletionTime OBJECT-TYPE
    SYNTAX       DateAndTime
    MAX-ACCESS   read-only
    STATUS       current
    DESCRIPTION
        "Cisco Firepower sw:FcSanBorderFsm:completionTime
        managed object property"
    ::= { cfprApSwFcSanBorderFsmEntry 4 }

cfprApSwFcSanBorderFsmCurrentFsm OBJECT-TYPE
    SYNTAX       CfprApSwFcSanBorderFsmCurrentFsm
    MAX-ACCESS   read-only
    STATUS       current
    DESCRIPTION
        "Cisco Firepower sw:FcSanBorderFsm:currentFsm managed
        object property"
    ::= { cfprApSwFcSanBorderFsmEntry 5 }

cfprApSwFcSanBorderFsmDescrData OBJECT-TYPE
    SYNTAX       SnmpAdminString
    MAX-ACCESS   read-only
    STATUS       current
    DESCRIPTION
        "Cisco Firepower sw:FcSanBorderFsm:descr managed object property"
    ::= { cfprApSwFcSanBorderFsmEntry 6 }

cfprApSwFcSanBorderFsmFsmStatus OBJECT-TYPE
    SYNTAX       CfprApFsmFsmStageStatus
    MAX-ACCESS   read-only
    STATUS       current
    DESCRIPTION
        "Cisco Firepower sw:FcSanBorderFsm:fsmStatus managed
        object property"
    ::= { cfprApSwFcSanBorderFsmEntry 7 }

cfprApSwFcSanBorderFsmProgress OBJECT-TYPE
    SYNTAX       Gauge32
    MAX-ACCESS   read-only
    STATUS       current
    DESCRIPTION
        "Cisco Firepower sw:FcSanBorderFsm:progress managed
        object property"
    ::= { cfprApSwFcSanBorderFsmEntry 8 }

cfprApSwFcSanBorderFsmRmtErrCode OBJECT-TYPE
    SYNTAX       Gauge32
    MAX-ACCESS   read-only
    STATUS       current
    DESCRIPTION
        "Cisco Firepower sw:FcSanBorderFsm:rmtErrCode managed
        object property"
    ::= { cfprApSwFcSanBorderFsmEntry 9 }

cfprApSwFcSanBorderFsmRmtErrDescr OBJECT-TYPE
    SYNTAX       SnmpAdminString
    MAX-ACCESS   read-only
    STATUS       current
    DESCRIPTION
        "Cisco Firepower sw:FcSanBorderFsm:rmtErrDescr
        managed object property"
    ::= { cfprApSwFcSanBorderFsmEntry 10 }

cfprApSwFcSanBorderFsmRmtRslt OBJECT-TYPE
    SYNTAX       CfprApConditionRemoteInvRslt
    MAX-ACCESS   read-only
    STATUS       current
    DESCRIPTION
        "Cisco Firepower sw:FcSanBorderFsm:rmtRslt managed
        object property"
    ::= { cfprApSwFcSanBorderFsmEntry 11 }

cfprApSwFcSanBorderFsmStageTable OBJECT-TYPE
    SYNTAX           SEQUENCE OF CfprApSwFcSanBorderFsmStageEntry
    MAX-ACCESS       not-accessible
    STATUS           current
    DESCRIPTION
        "Cisco Firepower sw:FcSanBorderFsmStage managed object table"
    ::= { cfprApSwObjects 46 }

cfprApSwFcSanBorderFsmStageEntry OBJECT-TYPE
    SYNTAX           CfprApSwFcSanBorderFsmStageEntry
    MAX-ACCESS       not-accessible
    STATUS           current
    DESCRIPTION
        "Entry for the cfprApSwFcSanBorderFsmStageTable table."
    INDEX { cfprApSwFcSanBorderFsmStageInstanceId }
    ::= { cfprApSwFcSanBorderFsmStageTable 1 }

CfprApSwFcSanBorderFsmStageEntry ::= SEQUENCE {
    cfprApSwFcSanBorderFsmStageInstanceId                            CfprApManagedObjectId,
    cfprApSwFcSanBorderFsmStageDn                                    CfprApManagedObjectDn,
    cfprApSwFcSanBorderFsmStageRn                                    SnmpAdminString,
    cfprApSwFcSanBorderFsmStageDescrData                             SnmpAdminString,
    cfprApSwFcSanBorderFsmStageLastUpdateTime                        DateAndTime,
    cfprApSwFcSanBorderFsmStageName                                  CfprApSwFcSanBorderFsmStageName,
    cfprApSwFcSanBorderFsmStageOrder                                 Gauge32,
    cfprApSwFcSanBorderFsmStageRetry                                 Gauge32,
    cfprApSwFcSanBorderFsmStageStageStatus                           CfprApFsmFsmStageStatus
}

cfprApSwFcSanBorderFsmStageInstanceId OBJECT-TYPE
    SYNTAX       CfprApManagedObjectId
    MAX-ACCESS   not-accessible
    STATUS       current
    DESCRIPTION
        "Instance identifier of the managed object."
    ::= { cfprApSwFcSanBorderFsmStageEntry 1 }

cfprApSwFcSanBorderFsmStageDn OBJECT-TYPE
    SYNTAX       CfprApManagedObjectDn
    MAX-ACCESS   read-only
    STATUS       current
    DESCRIPTION
        "Cisco Firepower sw:FcSanBorderFsmStage:dn managed
        object property"
    ::= { cfprApSwFcSanBorderFsmStageEntry 2 }

cfprApSwFcSanBorderFsmStageRn OBJECT-TYPE
    SYNTAX       SnmpAdminString
    MAX-ACCESS   read-only
    STATUS       current
    DESCRIPTION
        "Cisco Firepower sw:FcSanBorderFsmStage:rn managed
        object property"
    ::= { cfprApSwFcSanBorderFsmStageEntry 3 }

cfprApSwFcSanBorderFsmStageDescrData OBJECT-TYPE
    SYNTAX       SnmpAdminString
    MAX-ACCESS   read-only
    STATUS       current
    DESCRIPTION
        "Cisco Firepower sw:FcSanBorderFsmStage:descr managed
        object property"
    ::= { cfprApSwFcSanBorderFsmStageEntry 4 }

cfprApSwFcSanBorderFsmStageLastUpdateTime OBJECT-TYPE
    SYNTAX       DateAndTime
    MAX-ACCESS   read-only
    STATUS       current
    DESCRIPTION
        "Cisco Firepower sw:FcSanBorderFsmStage:lastUpdateTime
        managed object property"
    ::= { cfprApSwFcSanBorderFsmStageEntry 5 }

cfprApSwFcSanBorderFsmStageName OBJECT-TYPE
    SYNTAX       CfprApSwFcSanBorderFsmStageName
    MAX-ACCESS   read-only
    STATUS       current
    DESCRIPTION
        "Cisco Firepower sw:FcSanBorderFsmStage:name managed
        object property"
    ::= { cfprApSwFcSanBorderFsmStageEntry 6 }

cfprApSwFcSanBorderFsmStageOrder OBJECT-TYPE
    SYNTAX       Gauge32
    MAX-ACCESS   read-only
    STATUS       current
    DESCRIPTION
        "Cisco Firepower sw:FcSanBorderFsmStage:order managed
        object property"
    ::= { cfprApSwFcSanBorderFsmStageEntry 7 }

cfprApSwFcSanBorderFsmStageRetry OBJECT-TYPE
    SYNTAX       Gauge32
    MAX-ACCESS   read-only
    STATUS       current
    DESCRIPTION
        "Cisco Firepower sw:FcSanBorderFsmStage:retry managed
        object property"
    ::= { cfprApSwFcSanBorderFsmStageEntry 8 }

cfprApSwFcSanBorderFsmStageStageStatus OBJECT-TYPE
    SYNTAX       CfprApFsmFsmStageStatus
    MAX-ACCESS   read-only
    STATUS       current
    DESCRIPTION
        "Cisco Firepower sw:FcSanBorderFsmStage:stageStatus
        managed object property"
    ::= { cfprApSwFcSanBorderFsmStageEntry 9 }

cfprApSwFcSanBorderFsmTaskTable OBJECT-TYPE
    SYNTAX           SEQUENCE OF CfprApSwFcSanBorderFsmTaskEntry
    MAX-ACCESS       not-accessible
    STATUS           current
    DESCRIPTION
        "Cisco Firepower sw:FcSanBorderFsmTask managed object table"
    ::= { cfprApSwObjects 47 }

cfprApSwFcSanBorderFsmTaskEntry OBJECT-TYPE
    SYNTAX           CfprApSwFcSanBorderFsmTaskEntry
    MAX-ACCESS       not-accessible
    STATUS           current
    DESCRIPTION
        "Entry for the cfprApSwFcSanBorderFsmTaskTable table."
    INDEX { cfprApSwFcSanBorderFsmTaskInstanceId }
    ::= { cfprApSwFcSanBorderFsmTaskTable 1 }

CfprApSwFcSanBorderFsmTaskEntry ::= SEQUENCE {
    cfprApSwFcSanBorderFsmTaskInstanceId                             CfprApManagedObjectId,
    cfprApSwFcSanBorderFsmTaskDn                                     CfprApManagedObjectDn,
    cfprApSwFcSanBorderFsmTaskRn                                     SnmpAdminString,
    cfprApSwFcSanBorderFsmTaskCompletion                             CfprApFsmCompletion,
    cfprApSwFcSanBorderFsmTaskFlags                                  CfprApFsmFlags,
    cfprApSwFcSanBorderFsmTaskItem                                   CfprApSwFcSanBorderFsmTaskItem,
    cfprApSwFcSanBorderFsmTaskSeqId                                  Gauge32
}

cfprApSwFcSanBorderFsmTaskInstanceId OBJECT-TYPE
    SYNTAX       CfprApManagedObjectId
    MAX-ACCESS   not-accessible
    STATUS       current
    DESCRIPTION
        "Instance identifier of the managed object."
    ::= { cfprApSwFcSanBorderFsmTaskEntry 1 }

cfprApSwFcSanBorderFsmTaskDn OBJECT-TYPE
    SYNTAX       CfprApManagedObjectDn
    MAX-ACCESS   read-only
    STATUS       current
    DESCRIPTION
        "Cisco Firepower sw:FcSanBorderFsmTask:dn managed object property"
    ::= { cfprApSwFcSanBorderFsmTaskEntry 2 }

cfprApSwFcSanBorderFsmTaskRn OBJECT-TYPE
    SYNTAX       SnmpAdminString
    MAX-ACCESS   read-only
    STATUS       current
    DESCRIPTION
        "Cisco Firepower sw:FcSanBorderFsmTask:rn managed object property"
    ::= { cfprApSwFcSanBorderFsmTaskEntry 3 }

cfprApSwFcSanBorderFsmTaskCompletion OBJECT-TYPE
    SYNTAX       CfprApFsmCompletion
    MAX-ACCESS   read-only
    STATUS       current
    DESCRIPTION
        "Cisco Firepower sw:FcSanBorderFsmTask:completion
        managed object property"
    ::= { cfprApSwFcSanBorderFsmTaskEntry 4 }

cfprApSwFcSanBorderFsmTaskFlags OBJECT-TYPE
    SYNTAX       CfprApFsmFlags
    MAX-ACCESS   read-only
    STATUS       current
    DESCRIPTION
        "Cisco Firepower sw:FcSanBorderFsmTask:flags managed
        object property"
    ::= { cfprApSwFcSanBorderFsmTaskEntry 5 }

cfprApSwFcSanBorderFsmTaskItem OBJECT-TYPE
    SYNTAX       CfprApSwFcSanBorderFsmTaskItem
    MAX-ACCESS   read-only
    STATUS       current
    DESCRIPTION
        "Cisco Firepower sw:FcSanBorderFsmTask:item managed
        object property"
    ::= { cfprApSwFcSanBorderFsmTaskEntry 6 }

cfprApSwFcSanBorderFsmTaskSeqId OBJECT-TYPE
    SYNTAX       Gauge32
    MAX-ACCESS   read-only
    STATUS       current
    DESCRIPTION
        "Cisco Firepower sw:FcSanBorderFsmTask:seqId managed
        object property"
    ::= { cfprApSwFcSanBorderFsmTaskEntry 7 }

cfprApSwFcSanEpTable OBJECT-TYPE
    SYNTAX           SEQUENCE OF CfprApSwFcSanEpEntry
    MAX-ACCESS       not-accessible
    STATUS           current
    DESCRIPTION
        "Cisco Firepower sw:FcSanEp managed object table"
    ::= { cfprApSwObjects 48 }

cfprApSwFcSanEpEntry OBJECT-TYPE
    SYNTAX           CfprApSwFcSanEpEntry
    MAX-ACCESS       not-accessible
    STATUS           current
    DESCRIPTION
        "Entry for the cfprApSwFcSanEpTable table."
    INDEX { cfprApSwFcSanEpInstanceId }
    ::= { cfprApSwFcSanEpTable 1 }

CfprApSwFcSanEpEntry ::= SEQUENCE {
    cfprApSwFcSanEpInstanceId                                        CfprApManagedObjectId,
    cfprApSwFcSanEpDn                                                CfprApManagedObjectDn,
    cfprApSwFcSanEpRn                                                SnmpAdminString,
    cfprApSwFcSanEpAdminSpeed                                        CfprApPortSpeed,
    cfprApSwFcSanEpAdminState                                        CfprApFabricAdminState,
    cfprApSwFcSanEpAggrPortId                                        Gauge32,
    cfprApSwFcSanEpChassisId                                         Gauge32,
    cfprApSwFcSanEpEpDn                                              SnmpAdminString,
    cfprApSwFcSanEpFillPattern                                       CfprApFabricFillPattern,
    cfprApSwFcSanEpIfRole                                            CfprApSwSanEpIfRole,
    cfprApSwFcSanEpIfType                                            CfprApSwPIoEpIfType,
    cfprApSwFcSanEpLc                                                CfprApSwPIoEpLc,
    cfprApSwFcSanEpLocale                                            CfprApSwBorderEpLocale,
    cfprApSwFcSanEpName                                              SnmpAdminString,
    cfprApSwFcSanEpPcId                                              Gauge32,
    cfprApSwFcSanEpPeerAggrPortId                                    Gauge32,
    cfprApSwFcSanEpPeerChassisId                                     Gauge32,
    cfprApSwFcSanEpPeerDn                                            SnmpAdminString,
    cfprApSwFcSanEpPeerPortId                                        Gauge32,
    cfprApSwFcSanEpPeerSlotId                                        Gauge32,
    cfprApSwFcSanEpPortId                                            Gauge32,
    cfprApSwFcSanEpPortVsanId                                        Gauge32,
    cfprApSwFcSanEpSlotId                                            Gauge32,
    cfprApSwFcSanEpSwitchId                                          CfprApNetworkSwitchId,
    cfprApSwFcSanEpTransport                                         CfprApSwFcSanEpTransport,
    cfprApSwFcSanEpType                                              CfprApSwSanEpType
}

cfprApSwFcSanEpInstanceId OBJECT-TYPE
    SYNTAX       CfprApManagedObjectId
    MAX-ACCESS   not-accessible
    STATUS       current
    DESCRIPTION
        "Instance identifier of the managed object."
    ::= { cfprApSwFcSanEpEntry 1 }

cfprApSwFcSanEpDn OBJECT-TYPE
    SYNTAX       CfprApManagedObjectDn
    MAX-ACCESS   read-only
    STATUS       current
    DESCRIPTION
        "Cisco Firepower sw:FcSanEp:dn managed object property"
    ::= { cfprApSwFcSanEpEntry 2 }

cfprApSwFcSanEpRn OBJECT-TYPE
    SYNTAX       SnmpAdminString
    MAX-ACCESS   read-only
    STATUS       current
    DESCRIPTION
        "Cisco Firepower sw:FcSanEp:rn managed object property"
    ::= { cfprApSwFcSanEpEntry 3 }

cfprApSwFcSanEpAdminSpeed OBJECT-TYPE
    SYNTAX       CfprApPortSpeed
    MAX-ACCESS   read-only
    STATUS       current
    DESCRIPTION
        "Cisco Firepower sw:FcSanEp:adminSpeed managed object property"
    ::= { cfprApSwFcSanEpEntry 4 }

cfprApSwFcSanEpAdminState OBJECT-TYPE
    SYNTAX       CfprApFabricAdminState
    MAX-ACCESS   read-only
    STATUS       current
    DESCRIPTION
        "Cisco Firepower sw:FcSanEp:adminState managed object property"
    ::= { cfprApSwFcSanEpEntry 5 }

cfprApSwFcSanEpAggrPortId OBJECT-TYPE
    SYNTAX       Gauge32
    MAX-ACCESS   read-only
    STATUS       current
    DESCRIPTION
        "Cisco Firepower sw:FcSanEp:aggrPortId managed object property"
    ::= { cfprApSwFcSanEpEntry 6 }

cfprApSwFcSanEpChassisId OBJECT-TYPE
    SYNTAX       Gauge32
    MAX-ACCESS   read-only
    STATUS       current
    DESCRIPTION
        "Cisco Firepower sw:FcSanEp:chassisId managed object property"
    ::= { cfprApSwFcSanEpEntry 7 }

cfprApSwFcSanEpEpDn OBJECT-TYPE
    SYNTAX       SnmpAdminString
    MAX-ACCESS   read-only
    STATUS       current
    DESCRIPTION
        "Cisco Firepower sw:FcSanEp:epDn managed object property"
    ::= { cfprApSwFcSanEpEntry 8 }

cfprApSwFcSanEpFillPattern OBJECT-TYPE
    SYNTAX       CfprApFabricFillPattern
    MAX-ACCESS   read-only
    STATUS       current
    DESCRIPTION
        "Cisco Firepower sw:FcSanEp:fillPattern managed object property"
    ::= { cfprApSwFcSanEpEntry 9 }

cfprApSwFcSanEpIfRole OBJECT-TYPE
    SYNTAX       CfprApSwSanEpIfRole
    MAX-ACCESS   read-only
    STATUS       current
    DESCRIPTION
        "Cisco Firepower sw:FcSanEp:ifRole managed object property"
    ::= { cfprApSwFcSanEpEntry 10 }

cfprApSwFcSanEpIfType OBJECT-TYPE
    SYNTAX       CfprApSwPIoEpIfType
    MAX-ACCESS   read-only
    STATUS       current
    DESCRIPTION
        "Cisco Firepower sw:FcSanEp:ifType managed object property"
    ::= { cfprApSwFcSanEpEntry 11 }

cfprApSwFcSanEpLc OBJECT-TYPE
    SYNTAX       CfprApSwPIoEpLc
    MAX-ACCESS   read-only
    STATUS       current
    DESCRIPTION
        "Cisco Firepower sw:FcSanEp:lc managed object property"
    ::= { cfprApSwFcSanEpEntry 12 }

cfprApSwFcSanEpLocale OBJECT-TYPE
    SYNTAX       CfprApSwBorderEpLocale
    MAX-ACCESS   read-only
    STATUS       current
    DESCRIPTION
        "Cisco Firepower sw:FcSanEp:locale managed object property"
    ::= { cfprApSwFcSanEpEntry 13 }

cfprApSwFcSanEpName OBJECT-TYPE
    SYNTAX       SnmpAdminString
    MAX-ACCESS   read-only
    STATUS       current
    DESCRIPTION
        "Cisco Firepower sw:FcSanEp:name managed object property"
    ::= { cfprApSwFcSanEpEntry 14 }

cfprApSwFcSanEpPcId OBJECT-TYPE
    SYNTAX       Gauge32
    MAX-ACCESS   read-only
    STATUS       current
    DESCRIPTION
        "Cisco Firepower sw:FcSanEp:pcId managed object property"
    ::= { cfprApSwFcSanEpEntry 15 }

cfprApSwFcSanEpPeerAggrPortId OBJECT-TYPE
    SYNTAX       Gauge32
    MAX-ACCESS   read-only
    STATUS       current
    DESCRIPTION
        "Cisco Firepower sw:FcSanEp:peerAggrPortId managed
        object property"
    ::= { cfprApSwFcSanEpEntry 16 }

cfprApSwFcSanEpPeerChassisId OBJECT-TYPE
    SYNTAX       Gauge32
    MAX-ACCESS   read-only
    STATUS       current
    DESCRIPTION
        "Cisco Firepower sw:FcSanEp:peerChassisId managed object property"
    ::= { cfprApSwFcSanEpEntry 17 }

cfprApSwFcSanEpPeerDn OBJECT-TYPE
    SYNTAX       SnmpAdminString
    MAX-ACCESS   read-only
    STATUS       current
    DESCRIPTION
        "Cisco Firepower sw:FcSanEp:peerDn managed object property"
    ::= { cfprApSwFcSanEpEntry 18 }

cfprApSwFcSanEpPeerPortId OBJECT-TYPE
    SYNTAX       Gauge32
    MAX-ACCESS   read-only
    STATUS       current
    DESCRIPTION
        "Cisco Firepower sw:FcSanEp:peerPortId managed object property"
    ::= { cfprApSwFcSanEpEntry 19 }

cfprApSwFcSanEpPeerSlotId OBJECT-TYPE
    SYNTAX       Gauge32
    MAX-ACCESS   read-only
    STATUS       current
    DESCRIPTION
        "Cisco Firepower sw:FcSanEp:peerSlotId managed object property"
    ::= { cfprApSwFcSanEpEntry 20 }

cfprApSwFcSanEpPortId OBJECT-TYPE
    SYNTAX       Gauge32
    MAX-ACCESS   read-only
    STATUS       current
    DESCRIPTION
        "Cisco Firepower sw:FcSanEp:portId managed object property"
    ::= { cfprApSwFcSanEpEntry 21 }

cfprApSwFcSanEpPortVsanId OBJECT-TYPE
    SYNTAX       Gauge32
    MAX-ACCESS   read-only
    STATUS       current
    DESCRIPTION
        "Cisco Firepower sw:FcSanEp:portVsanId managed object property"
    ::= { cfprApSwFcSanEpEntry 22 }

cfprApSwFcSanEpSlotId OBJECT-TYPE
    SYNTAX       Gauge32
    MAX-ACCESS   read-only
    STATUS       current
    DESCRIPTION
        "Cisco Firepower sw:FcSanEp:slotId managed object property"
    ::= { cfprApSwFcSanEpEntry 23 }

cfprApSwFcSanEpSwitchId OBJECT-TYPE
    SYNTAX       CfprApNetworkSwitchId
    MAX-ACCESS   read-only
    STATUS       current
    DESCRIPTION
        "Cisco Firepower sw:FcSanEp:switchId managed object property"
    ::= { cfprApSwFcSanEpEntry 24 }

cfprApSwFcSanEpTransport OBJECT-TYPE
    SYNTAX       CfprApSwFcSanEpTransport
    MAX-ACCESS   read-only
    STATUS       current
    DESCRIPTION
        "Cisco Firepower sw:FcSanEp:transport managed object property"
    ::= { cfprApSwFcSanEpEntry 25 }

cfprApSwFcSanEpType OBJECT-TYPE
    SYNTAX       CfprApSwSanEpType
    MAX-ACCESS   read-only
    STATUS       current
    DESCRIPTION
        "Cisco Firepower sw:FcSanEp:type managed object property"
    ::= { cfprApSwFcSanEpEntry 26 }

cfprApSwFcSanPcTable OBJECT-TYPE
    SYNTAX           SEQUENCE OF CfprApSwFcSanPcEntry
    MAX-ACCESS       not-accessible
    STATUS           current
    DESCRIPTION
        "Cisco Firepower sw:FcSanPc managed object table"
    ::= { cfprApSwObjects 50 }

cfprApSwFcSanPcEntry OBJECT-TYPE
    SYNTAX           CfprApSwFcSanPcEntry
    MAX-ACCESS       not-accessible
    STATUS           current
    DESCRIPTION
        "Entry for the cfprApSwFcSanPcTable table."
    INDEX { cfprApSwFcSanPcInstanceId }
    ::= { cfprApSwFcSanPcTable 1 }

CfprApSwFcSanPcEntry ::= SEQUENCE {
    cfprApSwFcSanPcInstanceId                                        CfprApManagedObjectId,
    cfprApSwFcSanPcDn                                                CfprApManagedObjectDn,
    cfprApSwFcSanPcRn                                                SnmpAdminString,
    cfprApSwFcSanPcAdminSpeed                                        CfprApPortSpeed,
    cfprApSwFcSanPcAdminState                                        CfprApFabricAdminState,
    cfprApSwFcSanPcEpDn                                              SnmpAdminString,
    cfprApSwFcSanPcIfRole                                            CfprApSwSanPcIfRole,
    cfprApSwFcSanPcIfType                                            CfprApSwCIoEpIfType,
    cfprApSwFcSanPcLocale                                            CfprApSwBorderPcLocale,
    cfprApSwFcSanPcMonTrafDir                                        CfprApFabricTrafficDirection,
    cfprApSwFcSanPcName                                              SnmpAdminString,
    cfprApSwFcSanPcPcId                                              Gauge32,
    cfprApSwFcSanPcPeerDn                                            SnmpAdminString,
    cfprApSwFcSanPcPortId                                            Gauge32,
    cfprApSwFcSanPcPortVsanId                                        Gauge32,
    cfprApSwFcSanPcSwitchId                                          CfprApNetworkSwitchId,
    cfprApSwFcSanPcTransport                                         CfprApSwFcSanPcTransport,
    cfprApSwFcSanPcType                                              CfprApSwSanPcType
}

cfprApSwFcSanPcInstanceId OBJECT-TYPE
    SYNTAX       CfprApManagedObjectId
    MAX-ACCESS   not-accessible
    STATUS       current
    DESCRIPTION
        "Instance identifier of the managed object."
    ::= { cfprApSwFcSanPcEntry 1 }

cfprApSwFcSanPcDn OBJECT-TYPE
    SYNTAX       CfprApManagedObjectDn
    MAX-ACCESS   read-only
    STATUS       current
    DESCRIPTION
        "Cisco Firepower sw:FcSanPc:dn managed object property"
    ::= { cfprApSwFcSanPcEntry 2 }

cfprApSwFcSanPcRn OBJECT-TYPE
    SYNTAX       SnmpAdminString
    MAX-ACCESS   read-only
    STATUS       current
    DESCRIPTION
        "Cisco Firepower sw:FcSanPc:rn managed object property"
    ::= { cfprApSwFcSanPcEntry 3 }

cfprApSwFcSanPcAdminSpeed OBJECT-TYPE
    SYNTAX       CfprApPortSpeed
    MAX-ACCESS   read-only
    STATUS       current
    DESCRIPTION
        "Cisco Firepower sw:FcSanPc:adminSpeed managed object property"
    ::= { cfprApSwFcSanPcEntry 4 }

cfprApSwFcSanPcAdminState OBJECT-TYPE
    SYNTAX       CfprApFabricAdminState
    MAX-ACCESS   read-only
    STATUS       current
    DESCRIPTION
        "Cisco Firepower sw:FcSanPc:adminState managed object property"
    ::= { cfprApSwFcSanPcEntry 5 }

cfprApSwFcSanPcEpDn OBJECT-TYPE
    SYNTAX       SnmpAdminString
    MAX-ACCESS   read-only
    STATUS       current
    DESCRIPTION
        "Cisco Firepower sw:FcSanPc:epDn managed object property"
    ::= { cfprApSwFcSanPcEntry 6 }

cfprApSwFcSanPcIfRole OBJECT-TYPE
    SYNTAX       CfprApSwSanPcIfRole
    MAX-ACCESS   read-only
    STATUS       current
    DESCRIPTION
        "Cisco Firepower sw:FcSanPc:ifRole managed object property"
    ::= { cfprApSwFcSanPcEntry 7 }

cfprApSwFcSanPcIfType OBJECT-TYPE
    SYNTAX       CfprApSwCIoEpIfType
    MAX-ACCESS   read-only
    STATUS       current
    DESCRIPTION
        "Cisco Firepower sw:FcSanPc:ifType managed object property"
    ::= { cfprApSwFcSanPcEntry 8 }

cfprApSwFcSanPcLocale OBJECT-TYPE
    SYNTAX       CfprApSwBorderPcLocale
    MAX-ACCESS   read-only
    STATUS       current
    DESCRIPTION
        "Cisco Firepower sw:FcSanPc:locale managed object property"
    ::= { cfprApSwFcSanPcEntry 9 }

cfprApSwFcSanPcMonTrafDir OBJECT-TYPE
    SYNTAX       CfprApFabricTrafficDirection
    MAX-ACCESS   read-only
    STATUS       current
    DESCRIPTION
        "Cisco Firepower sw:FcSanPc:monTrafDir managed object property"
    ::= { cfprApSwFcSanPcEntry 10 }

cfprApSwFcSanPcName OBJECT-TYPE
    SYNTAX       SnmpAdminString
    MAX-ACCESS   read-only
    STATUS       current
    DESCRIPTION
        "Cisco Firepower sw:FcSanPc:name managed object property"
    ::= { cfprApSwFcSanPcEntry 11 }

cfprApSwFcSanPcPcId OBJECT-TYPE
    SYNTAX       Gauge32
    MAX-ACCESS   read-only
    STATUS       current
    DESCRIPTION
        "Cisco Firepower sw:FcSanPc:pcId managed object property"
    ::= { cfprApSwFcSanPcEntry 12 }

cfprApSwFcSanPcPeerDn OBJECT-TYPE
    SYNTAX       SnmpAdminString
    MAX-ACCESS   read-only
    STATUS       current
    DESCRIPTION
        "Cisco Firepower sw:FcSanPc:peerDn managed object property"
    ::= { cfprApSwFcSanPcEntry 13 }

cfprApSwFcSanPcPortId OBJECT-TYPE
    SYNTAX       Gauge32
    MAX-ACCESS   read-only
    STATUS       current
    DESCRIPTION
        "Cisco Firepower sw:FcSanPc:portId managed object property"
    ::= { cfprApSwFcSanPcEntry 14 }

cfprApSwFcSanPcPortVsanId OBJECT-TYPE
    SYNTAX       Gauge32
    MAX-ACCESS   read-only
    STATUS       current
    DESCRIPTION
        "Cisco Firepower sw:FcSanPc:portVsanId managed object property"
    ::= { cfprApSwFcSanPcEntry 15 }

cfprApSwFcSanPcSwitchId OBJECT-TYPE
    SYNTAX       CfprApNetworkSwitchId
    MAX-ACCESS   read-only
    STATUS       current
    DESCRIPTION
        "Cisco Firepower sw:FcSanPc:switchId managed object property"
    ::= { cfprApSwFcSanPcEntry 16 }

cfprApSwFcSanPcTransport OBJECT-TYPE
    SYNTAX       CfprApSwFcSanPcTransport
    MAX-ACCESS   read-only
    STATUS       current
    DESCRIPTION
        "Cisco Firepower sw:FcSanPc:transport managed object property"
    ::= { cfprApSwFcSanPcEntry 17 }

cfprApSwFcSanPcType OBJECT-TYPE
    SYNTAX       CfprApSwSanPcType
    MAX-ACCESS   read-only
    STATUS       current
    DESCRIPTION
        "Cisco Firepower sw:FcSanPc:type managed object property"
    ::= { cfprApSwFcSanPcEntry 18 }

cfprApSwFcServerZoneGroupTable OBJECT-TYPE
    SYNTAX           SEQUENCE OF CfprApSwFcServerZoneGroupEntry
    MAX-ACCESS       not-accessible
    STATUS           current
    DESCRIPTION
        "Cisco Firepower sw:FcServerZoneGroup managed object table"
    ::= { cfprApSwObjects 51 }

cfprApSwFcServerZoneGroupEntry OBJECT-TYPE
    SYNTAX           CfprApSwFcServerZoneGroupEntry
    MAX-ACCESS       not-accessible
    STATUS           current
    DESCRIPTION
        "Entry for the cfprApSwFcServerZoneGroupTable table."
    INDEX { cfprApSwFcServerZoneGroupInstanceId }
    ::= { cfprApSwFcServerZoneGroupTable 1 }

CfprApSwFcServerZoneGroupEntry ::= SEQUENCE {
    cfprApSwFcServerZoneGroupInstanceId                              CfprApManagedObjectId,
    cfprApSwFcServerZoneGroupDn                                      CfprApManagedObjectDn,
    cfprApSwFcServerZoneGroupRn                                      SnmpAdminString,
    cfprApSwFcServerZoneGroupEpDn                                    SnmpAdminString,
    cfprApSwFcServerZoneGroupId                                      Gauge32,
    cfprApSwFcServerZoneGroupLc                                      CfprApSwFcServerZoneGroupLc,
    cfprApSwFcServerZoneGroupName                                    SnmpAdminString,
    cfprApSwFcServerZoneGroupPeerDn                                  SnmpAdminString,
    cfprApSwFcServerZoneGroupServerDn                                SnmpAdminString
}

cfprApSwFcServerZoneGroupInstanceId OBJECT-TYPE
    SYNTAX       CfprApManagedObjectId
    MAX-ACCESS   not-accessible
    STATUS       current
    DESCRIPTION
        "Instance identifier of the managed object."
    ::= { cfprApSwFcServerZoneGroupEntry 1 }

cfprApSwFcServerZoneGroupDn OBJECT-TYPE
    SYNTAX       CfprApManagedObjectDn
    MAX-ACCESS   read-only
    STATUS       current
    DESCRIPTION
        "Cisco Firepower sw:FcServerZoneGroup:dn managed object property"
    ::= { cfprApSwFcServerZoneGroupEntry 2 }

cfprApSwFcServerZoneGroupRn OBJECT-TYPE
    SYNTAX       SnmpAdminString
    MAX-ACCESS   read-only
    STATUS       current
    DESCRIPTION
        "Cisco Firepower sw:FcServerZoneGroup:rn managed object property"
    ::= { cfprApSwFcServerZoneGroupEntry 3 }

cfprApSwFcServerZoneGroupEpDn OBJECT-TYPE
    SYNTAX       SnmpAdminString
    MAX-ACCESS   read-only
    STATUS       current
    DESCRIPTION
        "Cisco Firepower sw:FcServerZoneGroup:epDn managed
        object property"
    ::= { cfprApSwFcServerZoneGroupEntry 4 }

cfprApSwFcServerZoneGroupId OBJECT-TYPE
    SYNTAX       Gauge32
    MAX-ACCESS   read-only
    STATUS       current
    DESCRIPTION
        "Cisco Firepower sw:FcServerZoneGroup:id managed object property"
    ::= { cfprApSwFcServerZoneGroupEntry 5 }

cfprApSwFcServerZoneGroupLc OBJECT-TYPE
    SYNTAX       CfprApSwFcServerZoneGroupLc
    MAX-ACCESS   read-only
    STATUS       current
    DESCRIPTION
        "Cisco Firepower sw:FcServerZoneGroup:lc managed object property"
    ::= { cfprApSwFcServerZoneGroupEntry 6 }

cfprApSwFcServerZoneGroupName OBJECT-TYPE
    SYNTAX       SnmpAdminString
    MAX-ACCESS   read-only
    STATUS       current
    DESCRIPTION
        "Cisco Firepower sw:FcServerZoneGroup:name managed
        object property"
    ::= { cfprApSwFcServerZoneGroupEntry 7 }

cfprApSwFcServerZoneGroupPeerDn OBJECT-TYPE
    SYNTAX       SnmpAdminString
    MAX-ACCESS   read-only
    STATUS       current
    DESCRIPTION
        "Cisco Firepower sw:FcServerZoneGroup:peerDn managed
        object property"
    ::= { cfprApSwFcServerZoneGroupEntry 8 }

cfprApSwFcServerZoneGroupServerDn OBJECT-TYPE
    SYNTAX       SnmpAdminString
    MAX-ACCESS   read-only
    STATUS       current
    DESCRIPTION
        "Cisco Firepower sw:FcServerZoneGroup:serverDn
        managed object property"
    ::= { cfprApSwFcServerZoneGroupEntry 9 }

cfprApSwFcZoneTable OBJECT-TYPE
    SYNTAX           SEQUENCE OF CfprApSwFcZoneEntry
    MAX-ACCESS       not-accessible
    STATUS           current
    DESCRIPTION
        "Cisco Firepower sw:FcZone managed object table"
    ::= { cfprApSwObjects 52 }

cfprApSwFcZoneEntry OBJECT-TYPE
    SYNTAX           CfprApSwFcZoneEntry
    MAX-ACCESS       not-accessible
    STATUS           current
    DESCRIPTION
        "Entry for the cfprApSwFcZoneTable table."
    INDEX { cfprApSwFcZoneInstanceId }
    ::= { cfprApSwFcZoneTable 1 }

CfprApSwFcZoneEntry ::= SEQUENCE {
    cfprApSwFcZoneInstanceId                                         CfprApManagedObjectId,
    cfprApSwFcZoneDn                                                 CfprApManagedObjectDn,
    cfprApSwFcZoneRn                                                 SnmpAdminString,
    cfprApSwFcZoneId                                                 Gauge32,
    cfprApSwFcZoneIdentity                                           SnmpAdminString,
    cfprApSwFcZoneLc                                                 CfprApSwFcZoneLc,
    cfprApSwFcZoneName                                               SnmpAdminString,
    cfprApSwFcZoneOperState                                          CfprApLsFcZoneState,
    cfprApSwFcZonePeerDn                                             SnmpAdminString
}

cfprApSwFcZoneInstanceId OBJECT-TYPE
    SYNTAX       CfprApManagedObjectId
    MAX-ACCESS   not-accessible
    STATUS       current
    DESCRIPTION
        "Instance identifier of the managed object."
    ::= { cfprApSwFcZoneEntry 1 }

cfprApSwFcZoneDn OBJECT-TYPE
    SYNTAX       CfprApManagedObjectDn
    MAX-ACCESS   read-only
    STATUS       current
    DESCRIPTION
        "Cisco Firepower sw:FcZone:dn managed object property"
    ::= { cfprApSwFcZoneEntry 2 }

cfprApSwFcZoneRn OBJECT-TYPE
    SYNTAX       SnmpAdminString
    MAX-ACCESS   read-only
    STATUS       current
    DESCRIPTION
        "Cisco Firepower sw:FcZone:rn managed object property"
    ::= { cfprApSwFcZoneEntry 3 }

cfprApSwFcZoneId OBJECT-TYPE
    SYNTAX       Gauge32
    MAX-ACCESS   read-only
    STATUS       current
    DESCRIPTION
        "Cisco Firepower sw:FcZone:id managed object property"
    ::= { cfprApSwFcZoneEntry 4 }

cfprApSwFcZoneIdentity OBJECT-TYPE
    SYNTAX       SnmpAdminString
    MAX-ACCESS   read-only
    STATUS       current
    DESCRIPTION
        "Cisco Firepower sw:FcZone:identity managed object property"
    ::= { cfprApSwFcZoneEntry 5 }

cfprApSwFcZoneLc OBJECT-TYPE
    SYNTAX       CfprApSwFcZoneLc
    MAX-ACCESS   read-only
    STATUS       current
    DESCRIPTION
        "Cisco Firepower sw:FcZone:lc managed object property"
    ::= { cfprApSwFcZoneEntry 6 }

cfprApSwFcZoneName OBJECT-TYPE
    SYNTAX       SnmpAdminString
    MAX-ACCESS   read-only
    STATUS       current
    DESCRIPTION
        "Cisco Firepower sw:FcZone:name managed object property"
    ::= { cfprApSwFcZoneEntry 7 }

cfprApSwFcZoneOperState OBJECT-TYPE
    SYNTAX       CfprApLsFcZoneState
    MAX-ACCESS   read-only
    STATUS       current
    DESCRIPTION
        "Cisco Firepower sw:FcZone:operState managed object property"
    ::= { cfprApSwFcZoneEntry 8 }

cfprApSwFcZonePeerDn OBJECT-TYPE
    SYNTAX       SnmpAdminString
    MAX-ACCESS   read-only
    STATUS       current
    DESCRIPTION
        "Cisco Firepower sw:FcZone:peerDn managed object property"
    ::= { cfprApSwFcZoneEntry 9 }

cfprApSwFcZoneSetTable OBJECT-TYPE
    SYNTAX           SEQUENCE OF CfprApSwFcZoneSetEntry
    MAX-ACCESS       not-accessible
    STATUS           current
    DESCRIPTION
        "Cisco Firepower sw:FcZoneSet managed object table"
    ::= { cfprApSwObjects 53 }

cfprApSwFcZoneSetEntry OBJECT-TYPE
    SYNTAX           CfprApSwFcZoneSetEntry
    MAX-ACCESS       not-accessible
    STATUS           current
    DESCRIPTION
        "Entry for the cfprApSwFcZoneSetTable table."
    INDEX { cfprApSwFcZoneSetInstanceId }
    ::= { cfprApSwFcZoneSetTable 1 }

CfprApSwFcZoneSetEntry ::= SEQUENCE {
    cfprApSwFcZoneSetInstanceId                                      CfprApManagedObjectId,
    cfprApSwFcZoneSetDn                                              CfprApManagedObjectDn,
    cfprApSwFcZoneSetRn                                              SnmpAdminString,
    cfprApSwFcZoneSetCurrentZonePrefix                               SnmpAdminString,
    cfprApSwFcZoneSetLc                                              CfprApSwFcZoneSetLc,
    cfprApSwFcZoneSetName                                            SnmpAdminString,
    cfprApSwFcZoneSetOldZonePrefix                                   SnmpAdminString
}

cfprApSwFcZoneSetInstanceId OBJECT-TYPE
    SYNTAX       CfprApManagedObjectId
    MAX-ACCESS   not-accessible
    STATUS       current
    DESCRIPTION
        "Instance identifier of the managed object."
    ::= { cfprApSwFcZoneSetEntry 1 }

cfprApSwFcZoneSetDn OBJECT-TYPE
    SYNTAX       CfprApManagedObjectDn
    MAX-ACCESS   read-only
    STATUS       current
    DESCRIPTION
        "Cisco Firepower sw:FcZoneSet:dn managed object property"
    ::= { cfprApSwFcZoneSetEntry 2 }

cfprApSwFcZoneSetRn OBJECT-TYPE
    SYNTAX       SnmpAdminString
    MAX-ACCESS   read-only
    STATUS       current
    DESCRIPTION
        "Cisco Firepower sw:FcZoneSet:rn managed object property"
    ::= { cfprApSwFcZoneSetEntry 3 }

cfprApSwFcZoneSetCurrentZonePrefix OBJECT-TYPE
    SYNTAX       SnmpAdminString
    MAX-ACCESS   read-only
    STATUS       current
    DESCRIPTION
        "Cisco Firepower sw:FcZoneSet:currentZonePrefix
        managed object property"
    ::= { cfprApSwFcZoneSetEntry 4 }

cfprApSwFcZoneSetLc OBJECT-TYPE
    SYNTAX       CfprApSwFcZoneSetLc
    MAX-ACCESS   read-only
    STATUS       current
    DESCRIPTION
        "Cisco Firepower sw:FcZoneSet:lc managed object property"
    ::= { cfprApSwFcZoneSetEntry 5 }

cfprApSwFcZoneSetName OBJECT-TYPE
    SYNTAX       SnmpAdminString
    MAX-ACCESS   read-only
    STATUS       current
    DESCRIPTION
        "Cisco Firepower sw:FcZoneSet:name managed object property"
    ::= { cfprApSwFcZoneSetEntry 6 }

cfprApSwFcZoneSetOldZonePrefix OBJECT-TYPE
    SYNTAX       SnmpAdminString
    MAX-ACCESS   read-only
    STATUS       current
    DESCRIPTION
        "Cisco Firepower sw:FcZoneSet:oldZonePrefix managed
        object property"
    ::= { cfprApSwFcZoneSetEntry 7 }

cfprApSwFcoeSanEpTable OBJECT-TYPE
    SYNTAX           SEQUENCE OF CfprApSwFcoeSanEpEntry
    MAX-ACCESS       not-accessible
    STATUS           current
    DESCRIPTION
        "Cisco Firepower sw:FcoeSanEp managed object table"
    ::= { cfprApSwObjects 55 }

cfprApSwFcoeSanEpEntry OBJECT-TYPE
    SYNTAX           CfprApSwFcoeSanEpEntry
    MAX-ACCESS       not-accessible
    STATUS           current
    DESCRIPTION
        "Entry for the cfprApSwFcoeSanEpTable table."
    INDEX { cfprApSwFcoeSanEpInstanceId }
    ::= { cfprApSwFcoeSanEpTable 1 }

CfprApSwFcoeSanEpEntry ::= SEQUENCE {
    cfprApSwFcoeSanEpInstanceId                                      CfprApManagedObjectId,
    cfprApSwFcoeSanEpDn                                              CfprApManagedObjectDn,
    cfprApSwFcoeSanEpRn                                              SnmpAdminString,
    cfprApSwFcoeSanEpAdminSpeed                                      CfprApPortSpeed,
    cfprApSwFcoeSanEpAdminState                                      CfprApFabricAdminState,
    cfprApSwFcoeSanEpAggrPortId                                      Gauge32,
    cfprApSwFcoeSanEpChassisId                                       Gauge32,
    cfprApSwFcoeSanEpEpDn                                            SnmpAdminString,
    cfprApSwFcoeSanEpIfRole                                          CfprApSwSanEpIfRole,
    cfprApSwFcoeSanEpIfType                                          CfprApSwPIoEpIfType,
    cfprApSwFcoeSanEpLc                                              CfprApSwPIoEpLc,
    cfprApSwFcoeSanEpLocale                                          CfprApSwBorderEpLocale,
    cfprApSwFcoeSanEpName                                            SnmpAdminString,
    cfprApSwFcoeSanEpPcId                                            Gauge32,
    cfprApSwFcoeSanEpPeerAggrPortId                                  Gauge32,
    cfprApSwFcoeSanEpPeerChassisId                                   Gauge32,
    cfprApSwFcoeSanEpPeerDn                                          SnmpAdminString,
    cfprApSwFcoeSanEpPeerPortId                                      Gauge32,
    cfprApSwFcoeSanEpPeerSlotId                                      Gauge32,
    cfprApSwFcoeSanEpPeerState                                       CfprApSwPeerStatus,
    cfprApSwFcoeSanEpPortId                                          Gauge32,
    cfprApSwFcoeSanEpPortVsanId                                      Gauge32,
    cfprApSwFcoeSanEpSlotId                                          Gauge32,
    cfprApSwFcoeSanEpSwitchId                                        CfprApNetworkSwitchId,
    cfprApSwFcoeSanEpTransport                                       CfprApSwFcoeSanEpTransport,
    cfprApSwFcoeSanEpType                                            CfprApSwSanEpType,
    cfprApSwFcoeSanEpUdldAdminState                                  CfprApSwFcoeSanEpUdldAdminState,
    cfprApSwFcoeSanEpUdldMode                                        CfprApSwFcoeSanEpUdldMode
}

cfprApSwFcoeSanEpInstanceId OBJECT-TYPE
    SYNTAX       CfprApManagedObjectId
    MAX-ACCESS   not-accessible
    STATUS       current
    DESCRIPTION
        "Instance identifier of the managed object."
    ::= { cfprApSwFcoeSanEpEntry 1 }

cfprApSwFcoeSanEpDn OBJECT-TYPE
    SYNTAX       CfprApManagedObjectDn
    MAX-ACCESS   read-only
    STATUS       current
    DESCRIPTION
        "Cisco Firepower sw:FcoeSanEp:dn managed object property"
    ::= { cfprApSwFcoeSanEpEntry 2 }

cfprApSwFcoeSanEpRn OBJECT-TYPE
    SYNTAX       SnmpAdminString
    MAX-ACCESS   read-only
    STATUS       current
    DESCRIPTION
        "Cisco Firepower sw:FcoeSanEp:rn managed object property"
    ::= { cfprApSwFcoeSanEpEntry 3 }

cfprApSwFcoeSanEpAdminSpeed OBJECT-TYPE
    SYNTAX       CfprApPortSpeed
    MAX-ACCESS   read-only
    STATUS       current
    DESCRIPTION
        "Cisco Firepower sw:FcoeSanEp:adminSpeed managed object property"
    ::= { cfprApSwFcoeSanEpEntry 4 }

cfprApSwFcoeSanEpAdminState OBJECT-TYPE
    SYNTAX       CfprApFabricAdminState
    MAX-ACCESS   read-only
    STATUS       current
    DESCRIPTION
        "Cisco Firepower sw:FcoeSanEp:adminState managed object property"
    ::= { cfprApSwFcoeSanEpEntry 5 }

cfprApSwFcoeSanEpAggrPortId OBJECT-TYPE
    SYNTAX       Gauge32
    MAX-ACCESS   read-only
    STATUS       current
    DESCRIPTION
        "Cisco Firepower sw:FcoeSanEp:aggrPortId managed object property"
    ::= { cfprApSwFcoeSanEpEntry 6 }

cfprApSwFcoeSanEpChassisId OBJECT-TYPE
    SYNTAX       Gauge32
    MAX-ACCESS   read-only
    STATUS       current
    DESCRIPTION
        "Cisco Firepower sw:FcoeSanEp:chassisId managed object property"
    ::= { cfprApSwFcoeSanEpEntry 7 }

cfprApSwFcoeSanEpEpDn OBJECT-TYPE
    SYNTAX       SnmpAdminString
    MAX-ACCESS   read-only
    STATUS       current
    DESCRIPTION
        "Cisco Firepower sw:FcoeSanEp:epDn managed object property"
    ::= { cfprApSwFcoeSanEpEntry 8 }

cfprApSwFcoeSanEpIfRole OBJECT-TYPE
    SYNTAX       CfprApSwSanEpIfRole
    MAX-ACCESS   read-only
    STATUS       current
    DESCRIPTION
        "Cisco Firepower sw:FcoeSanEp:ifRole managed object property"
    ::= { cfprApSwFcoeSanEpEntry 9 }

cfprApSwFcoeSanEpIfType OBJECT-TYPE
    SYNTAX       CfprApSwPIoEpIfType
    MAX-ACCESS   read-only
    STATUS       current
    DESCRIPTION
        "Cisco Firepower sw:FcoeSanEp:ifType managed object property"
    ::= { cfprApSwFcoeSanEpEntry 10 }

cfprApSwFcoeSanEpLc OBJECT-TYPE
    SYNTAX       CfprApSwPIoEpLc
    MAX-ACCESS   read-only
    STATUS       current
    DESCRIPTION
        "Cisco Firepower sw:FcoeSanEp:lc managed object property"
    ::= { cfprApSwFcoeSanEpEntry 11 }

cfprApSwFcoeSanEpLocale OBJECT-TYPE
    SYNTAX       CfprApSwBorderEpLocale
    MAX-ACCESS   read-only
    STATUS       current
    DESCRIPTION
        "Cisco Firepower sw:FcoeSanEp:locale managed object property"
    ::= { cfprApSwFcoeSanEpEntry 12 }

cfprApSwFcoeSanEpName OBJECT-TYPE
    SYNTAX       SnmpAdminString
    MAX-ACCESS   read-only
    STATUS       current
    DESCRIPTION
        "Cisco Firepower sw:FcoeSanEp:name managed object property"
    ::= { cfprApSwFcoeSanEpEntry 13 }

cfprApSwFcoeSanEpPcId OBJECT-TYPE
    SYNTAX       Gauge32
    MAX-ACCESS   read-only
    STATUS       current
    DESCRIPTION
        "Cisco Firepower sw:FcoeSanEp:pcId managed object property"
    ::= { cfprApSwFcoeSanEpEntry 14 }

cfprApSwFcoeSanEpPeerAggrPortId OBJECT-TYPE
    SYNTAX       Gauge32
    MAX-ACCESS   read-only
    STATUS       current
    DESCRIPTION
        "Cisco Firepower sw:FcoeSanEp:peerAggrPortId managed
        object property"
    ::= { cfprApSwFcoeSanEpEntry 15 }

cfprApSwFcoeSanEpPeerChassisId OBJECT-TYPE
    SYNTAX       Gauge32
    MAX-ACCESS   read-only
    STATUS       current
    DESCRIPTION
        "Cisco Firepower sw:FcoeSanEp:peerChassisId managed
        object property"
    ::= { cfprApSwFcoeSanEpEntry 16 }

cfprApSwFcoeSanEpPeerDn OBJECT-TYPE
    SYNTAX       SnmpAdminString
    MAX-ACCESS   read-only
    STATUS       current
    DESCRIPTION
        "Cisco Firepower sw:FcoeSanEp:peerDn managed object property"
    ::= { cfprApSwFcoeSanEpEntry 17 }

cfprApSwFcoeSanEpPeerPortId OBJECT-TYPE
    SYNTAX       Gauge32
    MAX-ACCESS   read-only
    STATUS       current
    DESCRIPTION
        "Cisco Firepower sw:FcoeSanEp:peerPortId managed object property"
    ::= { cfprApSwFcoeSanEpEntry 18 }

cfprApSwFcoeSanEpPeerSlotId OBJECT-TYPE
    SYNTAX       Gauge32
    MAX-ACCESS   read-only
    STATUS       current
    DESCRIPTION
        "Cisco Firepower sw:FcoeSanEp:peerSlotId managed object property"
    ::= { cfprApSwFcoeSanEpEntry 19 }

cfprApSwFcoeSanEpPeerState OBJECT-TYPE
    SYNTAX       CfprApSwPeerStatus
    MAX-ACCESS   read-only
    STATUS       current
    DESCRIPTION
        "Cisco Firepower sw:FcoeSanEp:peerState managed object property"
    ::= { cfprApSwFcoeSanEpEntry 20 }

cfprApSwFcoeSanEpPortId OBJECT-TYPE
    SYNTAX       Gauge32
    MAX-ACCESS   read-only
    STATUS       current
    DESCRIPTION
        "Cisco Firepower sw:FcoeSanEp:portId managed object property"
    ::= { cfprApSwFcoeSanEpEntry 21 }

cfprApSwFcoeSanEpPortVsanId OBJECT-TYPE
    SYNTAX       Gauge32
    MAX-ACCESS   read-only
    STATUS       current
    DESCRIPTION
        "Cisco Firepower sw:FcoeSanEp:portVsanId managed object property"
    ::= { cfprApSwFcoeSanEpEntry 22 }

cfprApSwFcoeSanEpSlotId OBJECT-TYPE
    SYNTAX       Gauge32
    MAX-ACCESS   read-only
    STATUS       current
    DESCRIPTION
        "Cisco Firepower sw:FcoeSanEp:slotId managed object property"
    ::= { cfprApSwFcoeSanEpEntry 23 }

cfprApSwFcoeSanEpSwitchId OBJECT-TYPE
    SYNTAX       CfprApNetworkSwitchId
    MAX-ACCESS   read-only
    STATUS       current
    DESCRIPTION
        "Cisco Firepower sw:FcoeSanEp:switchId managed object property"
    ::= { cfprApSwFcoeSanEpEntry 24 }

cfprApSwFcoeSanEpTransport OBJECT-TYPE
    SYNTAX       CfprApSwFcoeSanEpTransport
    MAX-ACCESS   read-only
    STATUS       current
    DESCRIPTION
        "Cisco Firepower sw:FcoeSanEp:transport managed object property"
    ::= { cfprApSwFcoeSanEpEntry 25 }

cfprApSwFcoeSanEpType OBJECT-TYPE
    SYNTAX       CfprApSwSanEpType
    MAX-ACCESS   read-only
    STATUS       current
    DESCRIPTION
        "Cisco Firepower sw:FcoeSanEp:type managed object property"
    ::= { cfprApSwFcoeSanEpEntry 26 }

cfprApSwFcoeSanEpUdldAdminState OBJECT-TYPE
    SYNTAX       CfprApSwFcoeSanEpUdldAdminState
    MAX-ACCESS   read-only
    STATUS       current
    DESCRIPTION
        "Cisco Firepower sw:FcoeSanEp:udldAdminState managed
        object property"
    ::= { cfprApSwFcoeSanEpEntry 27 }

cfprApSwFcoeSanEpUdldMode OBJECT-TYPE
    SYNTAX       CfprApSwFcoeSanEpUdldMode
    MAX-ACCESS   read-only
    STATUS       current
    DESCRIPTION
        "Cisco Firepower sw:FcoeSanEp:udldMode managed object property"
    ::= { cfprApSwFcoeSanEpEntry 28 }

cfprApSwFcoeSanPcTable OBJECT-TYPE
    SYNTAX           SEQUENCE OF CfprApSwFcoeSanPcEntry
    MAX-ACCESS       not-accessible
    STATUS           current
    DESCRIPTION
        "Cisco Firepower sw:FcoeSanPc managed object table"
    ::= { cfprApSwObjects 56 }

cfprApSwFcoeSanPcEntry OBJECT-TYPE
    SYNTAX           CfprApSwFcoeSanPcEntry
    MAX-ACCESS       not-accessible
    STATUS           current
    DESCRIPTION
        "Entry for the cfprApSwFcoeSanPcTable table."
    INDEX { cfprApSwFcoeSanPcInstanceId }
    ::= { cfprApSwFcoeSanPcTable 1 }

CfprApSwFcoeSanPcEntry ::= SEQUENCE {
    cfprApSwFcoeSanPcInstanceId                                      CfprApManagedObjectId,
    cfprApSwFcoeSanPcDn                                              CfprApManagedObjectDn,
    cfprApSwFcoeSanPcRn                                              SnmpAdminString,
    cfprApSwFcoeSanPcAdminState                                      CfprApFabricAdminState,
    cfprApSwFcoeSanPcEpDn                                            SnmpAdminString,
    cfprApSwFcoeSanPcIfRole                                          CfprApSwSanPcIfRole,
    cfprApSwFcoeSanPcIfType                                          CfprApSwCIoEpIfType,
    cfprApSwFcoeSanPcLacpFastTimer                                   TruthValue,
    cfprApSwFcoeSanPcLacpSuspendIndividual                           TruthValue,
    cfprApSwFcoeSanPcLocale                                          CfprApSwBorderPcLocale,
    cfprApSwFcoeSanPcMonTrafDir                                      CfprApFabricTrafficDirection,
    cfprApSwFcoeSanPcName                                            SnmpAdminString,
    cfprApSwFcoeSanPcPcId                                            Gauge32,
    cfprApSwFcoeSanPcPeerDn                                          SnmpAdminString,
    cfprApSwFcoeSanPcPeerState                                       CfprApSwPeerStatus,
    cfprApSwFcoeSanPcPortId                                          Gauge32,
    cfprApSwFcoeSanPcPortVsanId                                      Gauge32,
    cfprApSwFcoeSanPcSwitchId                                        CfprApNetworkSwitchId,
    cfprApSwFcoeSanPcTransport                                       CfprApSwFcoeSanPcTransport,
    cfprApSwFcoeSanPcType                                            CfprApSwSanPcType
}

cfprApSwFcoeSanPcInstanceId OBJECT-TYPE
    SYNTAX       CfprApManagedObjectId
    MAX-ACCESS   not-accessible
    STATUS       current
    DESCRIPTION
        "Instance identifier of the managed object."
    ::= { cfprApSwFcoeSanPcEntry 1 }

cfprApSwFcoeSanPcDn OBJECT-TYPE
    SYNTAX       CfprApManagedObjectDn
    MAX-ACCESS   read-only
    STATUS       current
    DESCRIPTION
        "Cisco Firepower sw:FcoeSanPc:dn managed object property"
    ::= { cfprApSwFcoeSanPcEntry 2 }

cfprApSwFcoeSanPcRn OBJECT-TYPE
    SYNTAX       SnmpAdminString
    MAX-ACCESS   read-only
    STATUS       current
    DESCRIPTION
        "Cisco Firepower sw:FcoeSanPc:rn managed object property"
    ::= { cfprApSwFcoeSanPcEntry 3 }

cfprApSwFcoeSanPcAdminState OBJECT-TYPE
    SYNTAX       CfprApFabricAdminState
    MAX-ACCESS   read-only
    STATUS       current
    DESCRIPTION
        "Cisco Firepower sw:FcoeSanPc:adminState managed object property"
    ::= { cfprApSwFcoeSanPcEntry 4 }

cfprApSwFcoeSanPcEpDn OBJECT-TYPE
    SYNTAX       SnmpAdminString
    MAX-ACCESS   read-only
    STATUS       current
    DESCRIPTION
        "Cisco Firepower sw:FcoeSanPc:epDn managed object property"
    ::= { cfprApSwFcoeSanPcEntry 5 }

cfprApSwFcoeSanPcIfRole OBJECT-TYPE
    SYNTAX       CfprApSwSanPcIfRole
    MAX-ACCESS   read-only
    STATUS       current
    DESCRIPTION
        "Cisco Firepower sw:FcoeSanPc:ifRole managed object property"
    ::= { cfprApSwFcoeSanPcEntry 6 }

cfprApSwFcoeSanPcIfType OBJECT-TYPE
    SYNTAX       CfprApSwCIoEpIfType
    MAX-ACCESS   read-only
    STATUS       current
    DESCRIPTION
        "Cisco Firepower sw:FcoeSanPc:ifType managed object property"
    ::= { cfprApSwFcoeSanPcEntry 7 }

cfprApSwFcoeSanPcLacpFastTimer OBJECT-TYPE
    SYNTAX       TruthValue
    MAX-ACCESS   read-only
    STATUS       current
    DESCRIPTION
        "Cisco Firepower sw:FcoeSanPc:lacpFastTimer managed
        object property"
    ::= { cfprApSwFcoeSanPcEntry 8 }

cfprApSwFcoeSanPcLacpSuspendIndividual OBJECT-TYPE
    SYNTAX       TruthValue
    MAX-ACCESS   read-only
    STATUS       current
    DESCRIPTION
        "Cisco Firepower sw:FcoeSanPc:lacpSuspendIndividual
        managed object property"
    ::= { cfprApSwFcoeSanPcEntry 9 }

cfprApSwFcoeSanPcLocale OBJECT-TYPE
    SYNTAX       CfprApSwBorderPcLocale
    MAX-ACCESS   read-only
    STATUS       current
    DESCRIPTION
        "Cisco Firepower sw:FcoeSanPc:locale managed object property"
    ::= { cfprApSwFcoeSanPcEntry 10 }

cfprApSwFcoeSanPcMonTrafDir OBJECT-TYPE
    SYNTAX       CfprApFabricTrafficDirection
    MAX-ACCESS   read-only
    STATUS       current
    DESCRIPTION
        "Cisco Firepower sw:FcoeSanPc:monTrafDir managed object property"
    ::= { cfprApSwFcoeSanPcEntry 11 }

cfprApSwFcoeSanPcName OBJECT-TYPE
    SYNTAX       SnmpAdminString
    MAX-ACCESS   read-only
    STATUS       current
    DESCRIPTION
        "Cisco Firepower sw:FcoeSanPc:name managed object property"
    ::= { cfprApSwFcoeSanPcEntry 12 }

cfprApSwFcoeSanPcPcId OBJECT-TYPE
    SYNTAX       Gauge32
    MAX-ACCESS   read-only
    STATUS       current
    DESCRIPTION
        "Cisco Firepower sw:FcoeSanPc:pcId managed object property"
    ::= { cfprApSwFcoeSanPcEntry 13 }

cfprApSwFcoeSanPcPeerDn OBJECT-TYPE
    SYNTAX       SnmpAdminString
    MAX-ACCESS   read-only
    STATUS       current
    DESCRIPTION
        "Cisco Firepower sw:FcoeSanPc:peerDn managed object property"
    ::= { cfprApSwFcoeSanPcEntry 14 }

cfprApSwFcoeSanPcPeerState OBJECT-TYPE
    SYNTAX       CfprApSwPeerStatus
    MAX-ACCESS   read-only
    STATUS       current
    DESCRIPTION
        "Cisco Firepower sw:FcoeSanPc:peerState managed object property"
    ::= { cfprApSwFcoeSanPcEntry 15 }

cfprApSwFcoeSanPcPortId OBJECT-TYPE
    SYNTAX       Gauge32
    MAX-ACCESS   read-only
    STATUS       current
    DESCRIPTION
        "Cisco Firepower sw:FcoeSanPc:portId managed object property"
    ::= { cfprApSwFcoeSanPcEntry 16 }

cfprApSwFcoeSanPcPortVsanId OBJECT-TYPE
    SYNTAX       Gauge32
    MAX-ACCESS   read-only
    STATUS       current
    DESCRIPTION
        "Cisco Firepower sw:FcoeSanPc:portVsanId managed object property"
    ::= { cfprApSwFcoeSanPcEntry 17 }

cfprApSwFcoeSanPcSwitchId OBJECT-TYPE
    SYNTAX       CfprApNetworkSwitchId
    MAX-ACCESS   read-only
    STATUS       current
    DESCRIPTION
        "Cisco Firepower sw:FcoeSanPc:switchId managed object property"
    ::= { cfprApSwFcoeSanPcEntry 18 }

cfprApSwFcoeSanPcTransport OBJECT-TYPE
    SYNTAX       CfprApSwFcoeSanPcTransport
    MAX-ACCESS   read-only
    STATUS       current
    DESCRIPTION
        "Cisco Firepower sw:FcoeSanPc:transport managed object property"
    ::= { cfprApSwFcoeSanPcEntry 19 }

cfprApSwFcoeSanPcType OBJECT-TYPE
    SYNTAX       CfprApSwSanPcType
    MAX-ACCESS   read-only
    STATUS       current
    DESCRIPTION
        "Cisco Firepower sw:FcoeSanPc:type managed object property"
    ::= { cfprApSwFcoeSanPcEntry 20 }

cfprApSwPhysTable OBJECT-TYPE
    SYNTAX           SEQUENCE OF CfprApSwPhysEntry
    MAX-ACCESS       not-accessible
    STATUS           current
    DESCRIPTION
        "Cisco Firepower sw:Phys managed object table"
    ::= { cfprApSwObjects 64 }

cfprApSwPhysEntry OBJECT-TYPE
    SYNTAX           CfprApSwPhysEntry
    MAX-ACCESS       not-accessible
    STATUS           current
    DESCRIPTION
        "Entry for the cfprApSwPhysTable table."
    INDEX { cfprApSwPhysInstanceId }
    ::= { cfprApSwPhysTable 1 }

CfprApSwPhysEntry ::= SEQUENCE {
    cfprApSwPhysInstanceId                                           CfprApManagedObjectId,
    cfprApSwPhysDn                                                   CfprApManagedObjectDn,
    cfprApSwPhysRn                                                   SnmpAdminString,
    cfprApSwPhysConfMode                                             CfprApSwConfMode,
    cfprApSwPhysFsmDescr                                             SnmpAdminString,
    cfprApSwPhysFsmPrev                                              SnmpAdminString,
    cfprApSwPhysFsmProgr                                             Gauge32,
    cfprApSwPhysFsmRmtInvErrCode                                     Gauge32,
    cfprApSwPhysFsmRmtInvErrDescr                                    SnmpAdminString,
    cfprApSwPhysFsmRmtInvRslt                                        CfprApConditionRemoteInvRslt,
    cfprApSwPhysFsmStageDescr                                        SnmpAdminString,
    cfprApSwPhysFsmStamp                                             DateAndTime,
    cfprApSwPhysFsmStatus                                            SnmpAdminString,
    cfprApSwPhysFsmTry                                               Gauge32
}

cfprApSwPhysInstanceId OBJECT-TYPE
    SYNTAX       CfprApManagedObjectId
    MAX-ACCESS   not-accessible
    STATUS       current
    DESCRIPTION
        "Instance identifier of the managed object."
    ::= { cfprApSwPhysEntry 1 }

cfprApSwPhysDn OBJECT-TYPE
    SYNTAX       CfprApManagedObjectDn
    MAX-ACCESS   read-only
    STATUS       current
    DESCRIPTION
        "Cisco Firepower sw:Phys:dn managed object property"
    ::= { cfprApSwPhysEntry 2 }

cfprApSwPhysRn OBJECT-TYPE
    SYNTAX       SnmpAdminString
    MAX-ACCESS   read-only
    STATUS       current
    DESCRIPTION
        "Cisco Firepower sw:Phys:rn managed object property"
    ::= { cfprApSwPhysEntry 3 }

cfprApSwPhysConfMode OBJECT-TYPE
    SYNTAX       CfprApSwConfMode
    MAX-ACCESS   read-only
    STATUS       current
    DESCRIPTION
        "Cisco Firepower sw:Phys:confMode managed object property"
    ::= { cfprApSwPhysEntry 4 }

cfprApSwPhysFsmDescr OBJECT-TYPE
    SYNTAX       SnmpAdminString
    MAX-ACCESS   read-only
    STATUS       current
    DESCRIPTION
        "Cisco Firepower sw:Phys:fsmDescr managed object property"
    ::= { cfprApSwPhysEntry 5 }

cfprApSwPhysFsmPrev OBJECT-TYPE
    SYNTAX       SnmpAdminString
    MAX-ACCESS   read-only
    STATUS       current
    DESCRIPTION
        "Cisco Firepower sw:Phys:fsmPrev managed object property"
    ::= { cfprApSwPhysEntry 6 }

cfprApSwPhysFsmProgr OBJECT-TYPE
    SYNTAX       Gauge32
    MAX-ACCESS   read-only
    STATUS       current
    DESCRIPTION
        "Cisco Firepower sw:Phys:fsmProgr managed object property"
    ::= { cfprApSwPhysEntry 7 }

cfprApSwPhysFsmRmtInvErrCode OBJECT-TYPE
    SYNTAX       Gauge32
    MAX-ACCESS   read-only
    STATUS       current
    DESCRIPTION
        "Cisco Firepower sw:Phys:fsmRmtInvErrCode managed object property"
    ::= { cfprApSwPhysEntry 8 }

cfprApSwPhysFsmRmtInvErrDescr OBJECT-TYPE
    SYNTAX       SnmpAdminString
    MAX-ACCESS   read-only
    STATUS       current
    DESCRIPTION
        "Cisco Firepower sw:Phys:fsmRmtInvErrDescr managed
        object property"
    ::= { cfprApSwPhysEntry 9 }

cfprApSwPhysFsmRmtInvRslt OBJECT-TYPE
    SYNTAX       CfprApConditionRemoteInvRslt
    MAX-ACCESS   read-only
    STATUS       current
    DESCRIPTION
        "Cisco Firepower sw:Phys:fsmRmtInvRslt managed object property"
    ::= { cfprApSwPhysEntry 10 }

cfprApSwPhysFsmStageDescr OBJECT-TYPE
    SYNTAX       SnmpAdminString
    MAX-ACCESS   read-only
    STATUS       current
    DESCRIPTION
        "Cisco Firepower sw:Phys:fsmStageDescr managed object property"
    ::= { cfprApSwPhysEntry 11 }

cfprApSwPhysFsmStamp OBJECT-TYPE
    SYNTAX       DateAndTime
    MAX-ACCESS   read-only
    STATUS       current
    DESCRIPTION
        "Cisco Firepower sw:Phys:fsmStamp managed object property"
    ::= { cfprApSwPhysEntry 12 }

cfprApSwPhysFsmStatus OBJECT-TYPE
    SYNTAX       SnmpAdminString
    MAX-ACCESS   read-only
    STATUS       current
    DESCRIPTION
        "Cisco Firepower sw:Phys:fsmStatus managed object property"
    ::= { cfprApSwPhysEntry 13 }

cfprApSwPhysFsmTry OBJECT-TYPE
    SYNTAX       Gauge32
    MAX-ACCESS   read-only
    STATUS       current
    DESCRIPTION
        "Cisco Firepower sw:Phys:fsmTry managed object property"
    ::= { cfprApSwPhysEntry 14 }

cfprApSwPhysEtherEpTable OBJECT-TYPE
    SYNTAX           SEQUENCE OF CfprApSwPhysEtherEpEntry
    MAX-ACCESS       not-accessible
    STATUS           current
    DESCRIPTION
        "Cisco Firepower sw:PhysEtherEp managed object table"
    ::= { cfprApSwObjects 65 }

cfprApSwPhysEtherEpEntry OBJECT-TYPE
    SYNTAX           CfprApSwPhysEtherEpEntry
    MAX-ACCESS       not-accessible
    STATUS           current
    DESCRIPTION
        "Entry for the cfprApSwPhysEtherEpTable table."
    INDEX { cfprApSwPhysEtherEpInstanceId }
    ::= { cfprApSwPhysEtherEpTable 1 }

CfprApSwPhysEtherEpEntry ::= SEQUENCE {
    cfprApSwPhysEtherEpInstanceId                                    CfprApManagedObjectId,
    cfprApSwPhysEtherEpDn                                            CfprApManagedObjectDn,
    cfprApSwPhysEtherEpRn                                            SnmpAdminString,
    cfprApSwPhysEtherEpAdminState                                    CfprApFabricAdminState,
    cfprApSwPhysEtherEpAggrPortId                                    Gauge32,
    cfprApSwPhysEtherEpChassisId                                     Gauge32,
    cfprApSwPhysEtherEpEpDn                                          SnmpAdminString,
    cfprApSwPhysEtherEpIfRole                                        CfprApNetworkPortRole,
    cfprApSwPhysEtherEpIfType                                        CfprApSwPIoEpIfType,
    cfprApSwPhysEtherEpLc                                            CfprApSwPIoEpLc,
    cfprApSwPhysEtherEpLocale                                        CfprApNetworkLocale,
    cfprApSwPhysEtherEpName                                          SnmpAdminString,
    cfprApSwPhysEtherEpPeerAggrPortId                                Gauge32,
    cfprApSwPhysEtherEpPeerChassisId                                 Gauge32,
    cfprApSwPhysEtherEpPeerDn                                        SnmpAdminString,
    cfprApSwPhysEtherEpPeerPortId                                    Gauge32,
    cfprApSwPhysEtherEpPeerSlotId                                    Gauge32,
    cfprApSwPhysEtherEpPortId                                        Gauge32,
    cfprApSwPhysEtherEpSlotId                                        Gauge32,
    cfprApSwPhysEtherEpSwitchId                                      CfprApNetworkSwitchId,
    cfprApSwPhysEtherEpTransport                                     CfprApNetworkTransport,
    cfprApSwPhysEtherEpType                                          CfprApNetworkConnectionType
}

cfprApSwPhysEtherEpInstanceId OBJECT-TYPE
    SYNTAX       CfprApManagedObjectId
    MAX-ACCESS   not-accessible
    STATUS       current
    DESCRIPTION
        "Instance identifier of the managed object."
    ::= { cfprApSwPhysEtherEpEntry 1 }

cfprApSwPhysEtherEpDn OBJECT-TYPE
    SYNTAX       CfprApManagedObjectDn
    MAX-ACCESS   read-only
    STATUS       current
    DESCRIPTION
        "Cisco Firepower sw:PhysEtherEp:dn managed object property"
    ::= { cfprApSwPhysEtherEpEntry 2 }

cfprApSwPhysEtherEpRn OBJECT-TYPE
    SYNTAX       SnmpAdminString
    MAX-ACCESS   read-only
    STATUS       current
    DESCRIPTION
        "Cisco Firepower sw:PhysEtherEp:rn managed object property"
    ::= { cfprApSwPhysEtherEpEntry 3 }

cfprApSwPhysEtherEpAdminState OBJECT-TYPE
    SYNTAX       CfprApFabricAdminState
    MAX-ACCESS   read-only
    STATUS       current
    DESCRIPTION
        "Cisco Firepower sw:PhysEtherEp:adminState managed
        object property"
    ::= { cfprApSwPhysEtherEpEntry 4 }

cfprApSwPhysEtherEpAggrPortId OBJECT-TYPE
    SYNTAX       Gauge32
    MAX-ACCESS   read-only
    STATUS       current
    DESCRIPTION
        "Cisco Firepower sw:PhysEtherEp:aggrPortId managed
        object property"
    ::= { cfprApSwPhysEtherEpEntry 5 }

cfprApSwPhysEtherEpChassisId OBJECT-TYPE
    SYNTAX       Gauge32
    MAX-ACCESS   read-only
    STATUS       current
    DESCRIPTION
        "Cisco Firepower sw:PhysEtherEp:chassisId managed object property"
    ::= { cfprApSwPhysEtherEpEntry 6 }

cfprApSwPhysEtherEpEpDn OBJECT-TYPE
    SYNTAX       SnmpAdminString
    MAX-ACCESS   read-only
    STATUS       current
    DESCRIPTION
        "Cisco Firepower sw:PhysEtherEp:epDn managed object property"
    ::= { cfprApSwPhysEtherEpEntry 7 }

cfprApSwPhysEtherEpIfRole OBJECT-TYPE
    SYNTAX       CfprApNetworkPortRole
    MAX-ACCESS   read-only
    STATUS       current
    DESCRIPTION
        "Cisco Firepower sw:PhysEtherEp:ifRole managed object property"
    ::= { cfprApSwPhysEtherEpEntry 8 }

cfprApSwPhysEtherEpIfType OBJECT-TYPE
    SYNTAX       CfprApSwPIoEpIfType
    MAX-ACCESS   read-only
    STATUS       current
    DESCRIPTION
        "Cisco Firepower sw:PhysEtherEp:ifType managed object property"
    ::= { cfprApSwPhysEtherEpEntry 9 }

cfprApSwPhysEtherEpLc OBJECT-TYPE
    SYNTAX       CfprApSwPIoEpLc
    MAX-ACCESS   read-only
    STATUS       current
    DESCRIPTION
        "Cisco Firepower sw:PhysEtherEp:lc managed object property"
    ::= { cfprApSwPhysEtherEpEntry 10 }

cfprApSwPhysEtherEpLocale OBJECT-TYPE
    SYNTAX       CfprApNetworkLocale
    MAX-ACCESS   read-only
    STATUS       current
    DESCRIPTION
        "Cisco Firepower sw:PhysEtherEp:locale managed object property"
    ::= { cfprApSwPhysEtherEpEntry 11 }

cfprApSwPhysEtherEpName OBJECT-TYPE
    SYNTAX       SnmpAdminString
    MAX-ACCESS   read-only
    STATUS       current
    DESCRIPTION
        "Cisco Firepower sw:PhysEtherEp:name managed object property"
    ::= { cfprApSwPhysEtherEpEntry 12 }

cfprApSwPhysEtherEpPeerAggrPortId OBJECT-TYPE
    SYNTAX       Gauge32
    MAX-ACCESS   read-only
    STATUS       current
    DESCRIPTION
        "Cisco Firepower sw:PhysEtherEp:peerAggrPortId
        managed object property"
    ::= { cfprApSwPhysEtherEpEntry 13 }

cfprApSwPhysEtherEpPeerChassisId OBJECT-TYPE
    SYNTAX       Gauge32
    MAX-ACCESS   read-only
    STATUS       current
    DESCRIPTION
        "Cisco Firepower sw:PhysEtherEp:peerChassisId managed
        object property"
    ::= { cfprApSwPhysEtherEpEntry 14 }

cfprApSwPhysEtherEpPeerDn OBJECT-TYPE
    SYNTAX       SnmpAdminString
    MAX-ACCESS   read-only
    STATUS       current
    DESCRIPTION
        "Cisco Firepower sw:PhysEtherEp:peerDn managed object property"
    ::= { cfprApSwPhysEtherEpEntry 15 }

cfprApSwPhysEtherEpPeerPortId OBJECT-TYPE
    SYNTAX       Gauge32
    MAX-ACCESS   read-only
    STATUS       current
    DESCRIPTION
        "Cisco Firepower sw:PhysEtherEp:peerPortId managed
        object property"
    ::= { cfprApSwPhysEtherEpEntry 16 }

cfprApSwPhysEtherEpPeerSlotId OBJECT-TYPE
    SYNTAX       Gauge32
    MAX-ACCESS   read-only
    STATUS       current
    DESCRIPTION
        "Cisco Firepower sw:PhysEtherEp:peerSlotId managed
        object property"
    ::= { cfprApSwPhysEtherEpEntry 17 }

cfprApSwPhysEtherEpPortId OBJECT-TYPE
    SYNTAX       Gauge32
    MAX-ACCESS   read-only
    STATUS       current
    DESCRIPTION
        "Cisco Firepower sw:PhysEtherEp:portId managed object property"
    ::= { cfprApSwPhysEtherEpEntry 18 }

cfprApSwPhysEtherEpSlotId OBJECT-TYPE
    SYNTAX       Gauge32
    MAX-ACCESS   read-only
    STATUS       current
    DESCRIPTION
        "Cisco Firepower sw:PhysEtherEp:slotId managed object property"
    ::= { cfprApSwPhysEtherEpEntry 19 }

cfprApSwPhysEtherEpSwitchId OBJECT-TYPE
    SYNTAX       CfprApNetworkSwitchId
    MAX-ACCESS   read-only
    STATUS       current
    DESCRIPTION
        "Cisco Firepower sw:PhysEtherEp:switchId managed object property"
    ::= { cfprApSwPhysEtherEpEntry 20 }

cfprApSwPhysEtherEpTransport OBJECT-TYPE
    SYNTAX       CfprApNetworkTransport
    MAX-ACCESS   read-only
    STATUS       current
    DESCRIPTION
        "Cisco Firepower sw:PhysEtherEp:transport managed object property"
    ::= { cfprApSwPhysEtherEpEntry 21 }

cfprApSwPhysEtherEpType OBJECT-TYPE
    SYNTAX       CfprApNetworkConnectionType
    MAX-ACCESS   read-only
    STATUS       current
    DESCRIPTION
        "Cisco Firepower sw:PhysEtherEp:type managed object property"
    ::= { cfprApSwPhysEtherEpEntry 22 }

cfprApSwPhysFcEpTable OBJECT-TYPE
    SYNTAX           SEQUENCE OF CfprApSwPhysFcEpEntry
    MAX-ACCESS       not-accessible
    STATUS           current
    DESCRIPTION
        "Cisco Firepower sw:PhysFcEp managed object table"
    ::= { cfprApSwObjects 66 }

cfprApSwPhysFcEpEntry OBJECT-TYPE
    SYNTAX           CfprApSwPhysFcEpEntry
    MAX-ACCESS       not-accessible
    STATUS           current
    DESCRIPTION
        "Entry for the cfprApSwPhysFcEpTable table."
    INDEX { cfprApSwPhysFcEpInstanceId }
    ::= { cfprApSwPhysFcEpTable 1 }

CfprApSwPhysFcEpEntry ::= SEQUENCE {
    cfprApSwPhysFcEpInstanceId                                       CfprApManagedObjectId,
    cfprApSwPhysFcEpDn                                               CfprApManagedObjectDn,
    cfprApSwPhysFcEpRn                                               SnmpAdminString,
    cfprApSwPhysFcEpAdminState                                       CfprApFabricAdminState,
    cfprApSwPhysFcEpAggrPortId                                       Gauge32,
    cfprApSwPhysFcEpChassisId                                        Gauge32,
    cfprApSwPhysFcEpEpDn                                             SnmpAdminString,
    cfprApSwPhysFcEpIfRole                                           CfprApNetworkPortRole,
    cfprApSwPhysFcEpIfType                                           CfprApSwPIoEpIfType,
    cfprApSwPhysFcEpLc                                               CfprApSwPIoEpLc,
    cfprApSwPhysFcEpLocale                                           CfprApNetworkLocale,
    cfprApSwPhysFcEpName                                             SnmpAdminString,
    cfprApSwPhysFcEpPeerAggrPortId                                   Gauge32,
    cfprApSwPhysFcEpPeerChassisId                                    Gauge32,
    cfprApSwPhysFcEpPeerDn                                           SnmpAdminString,
    cfprApSwPhysFcEpPeerPortId                                       Gauge32,
    cfprApSwPhysFcEpPeerSlotId                                       Gauge32,
    cfprApSwPhysFcEpPortId                                           Gauge32,
    cfprApSwPhysFcEpSlotId                                           Gauge32,
    cfprApSwPhysFcEpSwitchId                                         CfprApNetworkSwitchId,
    cfprApSwPhysFcEpTransport                                        CfprApNetworkTransport,
    cfprApSwPhysFcEpType                                             CfprApNetworkConnectionType
}

cfprApSwPhysFcEpInstanceId OBJECT-TYPE
    SYNTAX       CfprApManagedObjectId
    MAX-ACCESS   not-accessible
    STATUS       current
    DESCRIPTION
        "Instance identifier of the managed object."
    ::= { cfprApSwPhysFcEpEntry 1 }

cfprApSwPhysFcEpDn OBJECT-TYPE
    SYNTAX       CfprApManagedObjectDn
    MAX-ACCESS   read-only
    STATUS       current
    DESCRIPTION
        "Cisco Firepower sw:PhysFcEp:dn managed object property"
    ::= { cfprApSwPhysFcEpEntry 2 }

cfprApSwPhysFcEpRn OBJECT-TYPE
    SYNTAX       SnmpAdminString
    MAX-ACCESS   read-only
    STATUS       current
    DESCRIPTION
        "Cisco Firepower sw:PhysFcEp:rn managed object property"
    ::= { cfprApSwPhysFcEpEntry 3 }

cfprApSwPhysFcEpAdminState OBJECT-TYPE
    SYNTAX       CfprApFabricAdminState
    MAX-ACCESS   read-only
    STATUS       current
    DESCRIPTION
        "Cisco Firepower sw:PhysFcEp:adminState managed object property"
    ::= { cfprApSwPhysFcEpEntry 4 }

cfprApSwPhysFcEpAggrPortId OBJECT-TYPE
    SYNTAX       Gauge32
    MAX-ACCESS   read-only
    STATUS       current
    DESCRIPTION
        "Cisco Firepower sw:PhysFcEp:aggrPortId managed object property"
    ::= { cfprApSwPhysFcEpEntry 5 }

cfprApSwPhysFcEpChassisId OBJECT-TYPE
    SYNTAX       Gauge32
    MAX-ACCESS   read-only
    STATUS       current
    DESCRIPTION
        "Cisco Firepower sw:PhysFcEp:chassisId managed object property"
    ::= { cfprApSwPhysFcEpEntry 6 }

cfprApSwPhysFcEpEpDn OBJECT-TYPE
    SYNTAX       SnmpAdminString
    MAX-ACCESS   read-only
    STATUS       current
    DESCRIPTION
        "Cisco Firepower sw:PhysFcEp:epDn managed object property"
    ::= { cfprApSwPhysFcEpEntry 7 }

cfprApSwPhysFcEpIfRole OBJECT-TYPE
    SYNTAX       CfprApNetworkPortRole
    MAX-ACCESS   read-only
    STATUS       current
    DESCRIPTION
        "Cisco Firepower sw:PhysFcEp:ifRole managed object property"
    ::= { cfprApSwPhysFcEpEntry 8 }

cfprApSwPhysFcEpIfType OBJECT-TYPE
    SYNTAX       CfprApSwPIoEpIfType
    MAX-ACCESS   read-only
    STATUS       current
    DESCRIPTION
        "Cisco Firepower sw:PhysFcEp:ifType managed object property"
    ::= { cfprApSwPhysFcEpEntry 9 }

cfprApSwPhysFcEpLc OBJECT-TYPE
    SYNTAX       CfprApSwPIoEpLc
    MAX-ACCESS   read-only
    STATUS       current
    DESCRIPTION
        "Cisco Firepower sw:PhysFcEp:lc managed object property"
    ::= { cfprApSwPhysFcEpEntry 10 }

cfprApSwPhysFcEpLocale OBJECT-TYPE
    SYNTAX       CfprApNetworkLocale
    MAX-ACCESS   read-only
    STATUS       current
    DESCRIPTION
        "Cisco Firepower sw:PhysFcEp:locale managed object property"
    ::= { cfprApSwPhysFcEpEntry 11 }

cfprApSwPhysFcEpName OBJECT-TYPE
    SYNTAX       SnmpAdminString
    MAX-ACCESS   read-only
    STATUS       current
    DESCRIPTION
        "Cisco Firepower sw:PhysFcEp:name managed object property"
    ::= { cfprApSwPhysFcEpEntry 12 }

cfprApSwPhysFcEpPeerAggrPortId OBJECT-TYPE
    SYNTAX       Gauge32
    MAX-ACCESS   read-only
    STATUS       current
    DESCRIPTION
        "Cisco Firepower sw:PhysFcEp:peerAggrPortId managed
        object property"
    ::= { cfprApSwPhysFcEpEntry 13 }

cfprApSwPhysFcEpPeerChassisId OBJECT-TYPE
    SYNTAX       Gauge32
    MAX-ACCESS   read-only
    STATUS       current
    DESCRIPTION
        "Cisco Firepower sw:PhysFcEp:peerChassisId managed
        object property"
    ::= { cfprApSwPhysFcEpEntry 14 }

cfprApSwPhysFcEpPeerDn OBJECT-TYPE
    SYNTAX       SnmpAdminString
    MAX-ACCESS   read-only
    STATUS       current
    DESCRIPTION
        "Cisco Firepower sw:PhysFcEp:peerDn managed object property"
    ::= { cfprApSwPhysFcEpEntry 15 }

cfprApSwPhysFcEpPeerPortId OBJECT-TYPE
    SYNTAX       Gauge32
    MAX-ACCESS   read-only
    STATUS       current
    DESCRIPTION
        "Cisco Firepower sw:PhysFcEp:peerPortId managed object property"
    ::= { cfprApSwPhysFcEpEntry 16 }

cfprApSwPhysFcEpPeerSlotId OBJECT-TYPE
    SYNTAX       Gauge32
    MAX-ACCESS   read-only
    STATUS       current
    DESCRIPTION
        "Cisco Firepower sw:PhysFcEp:peerSlotId managed object property"
    ::= { cfprApSwPhysFcEpEntry 17 }

cfprApSwPhysFcEpPortId OBJECT-TYPE
    SYNTAX       Gauge32
    MAX-ACCESS   read-only
    STATUS       current
    DESCRIPTION
        "Cisco Firepower sw:PhysFcEp:portId managed object property"
    ::= { cfprApSwPhysFcEpEntry 18 }

cfprApSwPhysFcEpSlotId OBJECT-TYPE
    SYNTAX       Gauge32
    MAX-ACCESS   read-only
    STATUS       current
    DESCRIPTION
        "Cisco Firepower sw:PhysFcEp:slotId managed object property"
    ::= { cfprApSwPhysFcEpEntry 19 }

cfprApSwPhysFcEpSwitchId OBJECT-TYPE
    SYNTAX       CfprApNetworkSwitchId
    MAX-ACCESS   read-only
    STATUS       current
    DESCRIPTION
        "Cisco Firepower sw:PhysFcEp:switchId managed object property"
    ::= { cfprApSwPhysFcEpEntry 20 }

cfprApSwPhysFcEpTransport OBJECT-TYPE
    SYNTAX       CfprApNetworkTransport
    MAX-ACCESS   read-only
    STATUS       current
    DESCRIPTION
        "Cisco Firepower sw:PhysFcEp:transport managed object property"
    ::= { cfprApSwPhysFcEpEntry 21 }

cfprApSwPhysFcEpType OBJECT-TYPE
    SYNTAX       CfprApNetworkConnectionType
    MAX-ACCESS   read-only
    STATUS       current
    DESCRIPTION
        "Cisco Firepower sw:PhysFcEp:type managed object property"
    ::= { cfprApSwPhysFcEpEntry 22 }

cfprApSwPhysFsmTable OBJECT-TYPE
    SYNTAX           SEQUENCE OF CfprApSwPhysFsmEntry
    MAX-ACCESS       not-accessible
    STATUS           current
    DESCRIPTION
        "Cisco Firepower sw:PhysFsm managed object table"
    ::= { cfprApSwObjects 67 }

cfprApSwPhysFsmEntry OBJECT-TYPE
    SYNTAX           CfprApSwPhysFsmEntry
    MAX-ACCESS       not-accessible
    STATUS           current
    DESCRIPTION
        "Entry for the cfprApSwPhysFsmTable table."
    INDEX { cfprApSwPhysFsmInstanceId }
    ::= { cfprApSwPhysFsmTable 1 }

CfprApSwPhysFsmEntry ::= SEQUENCE {
    cfprApSwPhysFsmInstanceId                                        CfprApManagedObjectId,
    cfprApSwPhysFsmDn                                                CfprApManagedObjectDn,
    cfprApSwPhysFsmRn                                                SnmpAdminString,
    cfprApSwPhysFsmCompletionTime                                    DateAndTime,
    cfprApSwPhysFsmCurrentFsm                                        CfprApSwPhysFsmCurrentFsm,
    cfprApSwPhysFsmDescrData                                         SnmpAdminString,
    cfprApSwPhysFsmFsmStatus                                         CfprApFsmFsmStageStatus,
    cfprApSwPhysFsmProgress                                          Gauge32,
    cfprApSwPhysFsmRmtErrCode                                        Gauge32,
    cfprApSwPhysFsmRmtErrDescr                                       SnmpAdminString,
    cfprApSwPhysFsmRmtRslt                                           CfprApConditionRemoteInvRslt
}

cfprApSwPhysFsmInstanceId OBJECT-TYPE
    SYNTAX       CfprApManagedObjectId
    MAX-ACCESS   not-accessible
    STATUS       current
    DESCRIPTION
        "Instance identifier of the managed object."
    ::= { cfprApSwPhysFsmEntry 1 }

cfprApSwPhysFsmDn OBJECT-TYPE
    SYNTAX       CfprApManagedObjectDn
    MAX-ACCESS   read-only
    STATUS       current
    DESCRIPTION
        "Cisco Firepower sw:PhysFsm:dn managed object property"
    ::= { cfprApSwPhysFsmEntry 2 }

cfprApSwPhysFsmRn OBJECT-TYPE
    SYNTAX       SnmpAdminString
    MAX-ACCESS   read-only
    STATUS       current
    DESCRIPTION
        "Cisco Firepower sw:PhysFsm:rn managed object property"
    ::= { cfprApSwPhysFsmEntry 3 }

cfprApSwPhysFsmCompletionTime OBJECT-TYPE
    SYNTAX       DateAndTime
    MAX-ACCESS   read-only
    STATUS       current
    DESCRIPTION
        "Cisco Firepower sw:PhysFsm:completionTime managed
        object property"
    ::= { cfprApSwPhysFsmEntry 4 }

cfprApSwPhysFsmCurrentFsm OBJECT-TYPE
    SYNTAX       CfprApSwPhysFsmCurrentFsm
    MAX-ACCESS   read-only
    STATUS       current
    DESCRIPTION
        "Cisco Firepower sw:PhysFsm:currentFsm managed object property"
    ::= { cfprApSwPhysFsmEntry 5 }

cfprApSwPhysFsmDescrData OBJECT-TYPE
    SYNTAX       SnmpAdminString
    MAX-ACCESS   read-only
    STATUS       current
    DESCRIPTION
        "Cisco Firepower sw:PhysFsm:descr managed object property"
    ::= { cfprApSwPhysFsmEntry 6 }

cfprApSwPhysFsmFsmStatus OBJECT-TYPE
    SYNTAX       CfprApFsmFsmStageStatus
    MAX-ACCESS   read-only
    STATUS       current
    DESCRIPTION
        "Cisco Firepower sw:PhysFsm:fsmStatus managed object property"
    ::= { cfprApSwPhysFsmEntry 7 }

cfprApSwPhysFsmProgress OBJECT-TYPE
    SYNTAX       Gauge32
    MAX-ACCESS   read-only
    STATUS       current
    DESCRIPTION
        "Cisco Firepower sw:PhysFsm:progress managed object property"
    ::= { cfprApSwPhysFsmEntry 8 }

cfprApSwPhysFsmRmtErrCode OBJECT-TYPE
    SYNTAX       Gauge32
    MAX-ACCESS   read-only
    STATUS       current
    DESCRIPTION
        "Cisco Firepower sw:PhysFsm:rmtErrCode managed object property"
    ::= { cfprApSwPhysFsmEntry 9 }

cfprApSwPhysFsmRmtErrDescr OBJECT-TYPE
    SYNTAX       SnmpAdminString
    MAX-ACCESS   read-only
    STATUS       current
    DESCRIPTION
        "Cisco Firepower sw:PhysFsm:rmtErrDescr managed object property"
    ::= { cfprApSwPhysFsmEntry 10 }

cfprApSwPhysFsmRmtRslt OBJECT-TYPE
    SYNTAX       CfprApConditionRemoteInvRslt
    MAX-ACCESS   read-only
    STATUS       current
    DESCRIPTION
        "Cisco Firepower sw:PhysFsm:rmtRslt managed object property"
    ::= { cfprApSwPhysFsmEntry 11 }

cfprApSwPhysFsmStageTable OBJECT-TYPE
    SYNTAX           SEQUENCE OF CfprApSwPhysFsmStageEntry
    MAX-ACCESS       not-accessible
    STATUS           current
    DESCRIPTION
        "Cisco Firepower sw:PhysFsmStage managed object table"
    ::= { cfprApSwObjects 68 }

cfprApSwPhysFsmStageEntry OBJECT-TYPE
    SYNTAX           CfprApSwPhysFsmStageEntry
    MAX-ACCESS       not-accessible
    STATUS           current
    DESCRIPTION
        "Entry for the cfprApSwPhysFsmStageTable table."
    INDEX { cfprApSwPhysFsmStageInstanceId }
    ::= { cfprApSwPhysFsmStageTable 1 }

CfprApSwPhysFsmStageEntry ::= SEQUENCE {
    cfprApSwPhysFsmStageInstanceId                                   CfprApManagedObjectId,
    cfprApSwPhysFsmStageDn                                           CfprApManagedObjectDn,
    cfprApSwPhysFsmStageRn                                           SnmpAdminString,
    cfprApSwPhysFsmStageDescrData                                    SnmpAdminString,
    cfprApSwPhysFsmStageLastUpdateTime                               DateAndTime,
    cfprApSwPhysFsmStageName                                         CfprApSwPhysFsmStageName,
    cfprApSwPhysFsmStageOrder                                        Gauge32,
    cfprApSwPhysFsmStageRetry                                        Gauge32,
    cfprApSwPhysFsmStageStageStatus                                  CfprApFsmFsmStageStatus
}

cfprApSwPhysFsmStageInstanceId OBJECT-TYPE
    SYNTAX       CfprApManagedObjectId
    MAX-ACCESS   not-accessible
    STATUS       current
    DESCRIPTION
        "Instance identifier of the managed object."
    ::= { cfprApSwPhysFsmStageEntry 1 }

cfprApSwPhysFsmStageDn OBJECT-TYPE
    SYNTAX       CfprApManagedObjectDn
    MAX-ACCESS   read-only
    STATUS       current
    DESCRIPTION
        "Cisco Firepower sw:PhysFsmStage:dn managed object property"
    ::= { cfprApSwPhysFsmStageEntry 2 }

cfprApSwPhysFsmStageRn OBJECT-TYPE
    SYNTAX       SnmpAdminString
    MAX-ACCESS   read-only
    STATUS       current
    DESCRIPTION
        "Cisco Firepower sw:PhysFsmStage:rn managed object property"
    ::= { cfprApSwPhysFsmStageEntry 3 }

cfprApSwPhysFsmStageDescrData OBJECT-TYPE
    SYNTAX       SnmpAdminString
    MAX-ACCESS   read-only
    STATUS       current
    DESCRIPTION
        "Cisco Firepower sw:PhysFsmStage:descr managed object property"
    ::= { cfprApSwPhysFsmStageEntry 4 }

cfprApSwPhysFsmStageLastUpdateTime OBJECT-TYPE
    SYNTAX       DateAndTime
    MAX-ACCESS   read-only
    STATUS       current
    DESCRIPTION
        "Cisco Firepower sw:PhysFsmStage:lastUpdateTime
        managed object property"
    ::= { cfprApSwPhysFsmStageEntry 5 }

cfprApSwPhysFsmStageName OBJECT-TYPE
    SYNTAX       CfprApSwPhysFsmStageName
    MAX-ACCESS   read-only
    STATUS       current
    DESCRIPTION
        "Cisco Firepower sw:PhysFsmStage:name managed object property"
    ::= { cfprApSwPhysFsmStageEntry 6 }

cfprApSwPhysFsmStageOrder OBJECT-TYPE
    SYNTAX       Gauge32
    MAX-ACCESS   read-only
    STATUS       current
    DESCRIPTION
        "Cisco Firepower sw:PhysFsmStage:order managed object property"
    ::= { cfprApSwPhysFsmStageEntry 7 }

cfprApSwPhysFsmStageRetry OBJECT-TYPE
    SYNTAX       Gauge32
    MAX-ACCESS   read-only
    STATUS       current
    DESCRIPTION
        "Cisco Firepower sw:PhysFsmStage:retry managed object property"
    ::= { cfprApSwPhysFsmStageEntry 8 }

cfprApSwPhysFsmStageStageStatus OBJECT-TYPE
    SYNTAX       CfprApFsmFsmStageStatus
    MAX-ACCESS   read-only
    STATUS       current
    DESCRIPTION
        "Cisco Firepower sw:PhysFsmStage:stageStatus managed
        object property"
    ::= { cfprApSwPhysFsmStageEntry 9 }

cfprApSwPhysFsmTaskTable OBJECT-TYPE
    SYNTAX           SEQUENCE OF CfprApSwPhysFsmTaskEntry
    MAX-ACCESS       not-accessible
    STATUS           current
    DESCRIPTION
        "Cisco Firepower sw:PhysFsmTask managed object table"
    ::= { cfprApSwObjects 69 }

cfprApSwPhysFsmTaskEntry OBJECT-TYPE
    SYNTAX           CfprApSwPhysFsmTaskEntry
    MAX-ACCESS       not-accessible
    STATUS           current
    DESCRIPTION
        "Entry for the cfprApSwPhysFsmTaskTable table."
    INDEX { cfprApSwPhysFsmTaskInstanceId }
    ::= { cfprApSwPhysFsmTaskTable 1 }

CfprApSwPhysFsmTaskEntry ::= SEQUENCE {
    cfprApSwPhysFsmTaskInstanceId                                    CfprApManagedObjectId,
    cfprApSwPhysFsmTaskDn                                            CfprApManagedObjectDn,
    cfprApSwPhysFsmTaskRn                                            SnmpAdminString,
    cfprApSwPhysFsmTaskCompletion                                    CfprApFsmCompletion,
    cfprApSwPhysFsmTaskFlags                                         CfprApFsmFlags,
    cfprApSwPhysFsmTaskItem                                          CfprApSwPhysFsmTaskItem,
    cfprApSwPhysFsmTaskSeqId                                         Gauge32
}

cfprApSwPhysFsmTaskInstanceId OBJECT-TYPE
    SYNTAX       CfprApManagedObjectId
    MAX-ACCESS   not-accessible
    STATUS       current
    DESCRIPTION
        "Instance identifier of the managed object."
    ::= { cfprApSwPhysFsmTaskEntry 1 }

cfprApSwPhysFsmTaskDn OBJECT-TYPE
    SYNTAX       CfprApManagedObjectDn
    MAX-ACCESS   read-only
    STATUS       current
    DESCRIPTION
        "Cisco Firepower sw:PhysFsmTask:dn managed object property"
    ::= { cfprApSwPhysFsmTaskEntry 2 }

cfprApSwPhysFsmTaskRn OBJECT-TYPE
    SYNTAX       SnmpAdminString
    MAX-ACCESS   read-only
    STATUS       current
    DESCRIPTION
        "Cisco Firepower sw:PhysFsmTask:rn managed object property"
    ::= { cfprApSwPhysFsmTaskEntry 3 }

cfprApSwPhysFsmTaskCompletion OBJECT-TYPE
    SYNTAX       CfprApFsmCompletion
    MAX-ACCESS   read-only
    STATUS       current
    DESCRIPTION
        "Cisco Firepower sw:PhysFsmTask:completion managed
        object property"
    ::= { cfprApSwPhysFsmTaskEntry 4 }

cfprApSwPhysFsmTaskFlags OBJECT-TYPE
    SYNTAX       CfprApFsmFlags
    MAX-ACCESS   read-only
    STATUS       current
    DESCRIPTION
        "Cisco Firepower sw:PhysFsmTask:flags managed object property"
    ::= { cfprApSwPhysFsmTaskEntry 5 }

cfprApSwPhysFsmTaskItem OBJECT-TYPE
    SYNTAX       CfprApSwPhysFsmTaskItem
    MAX-ACCESS   read-only
    STATUS       current
    DESCRIPTION
        "Cisco Firepower sw:PhysFsmTask:item managed object property"
    ::= { cfprApSwPhysFsmTaskEntry 6 }

cfprApSwPhysFsmTaskSeqId OBJECT-TYPE
    SYNTAX       Gauge32
    MAX-ACCESS   read-only
    STATUS       current
    DESCRIPTION
        "Cisco Firepower sw:PhysFsmTask:seqId managed object property"
    ::= { cfprApSwPhysFsmTaskEntry 7 }

cfprApSwPortBreakoutTable OBJECT-TYPE
    SYNTAX           SEQUENCE OF CfprApSwPortBreakoutEntry
    MAX-ACCESS       not-accessible
    STATUS           current
    DESCRIPTION
        "Cisco Firepower sw:PortBreakout managed object table"
    ::= { cfprApSwObjects 70 }

cfprApSwPortBreakoutEntry OBJECT-TYPE
    SYNTAX           CfprApSwPortBreakoutEntry
    MAX-ACCESS       not-accessible
    STATUS           current
    DESCRIPTION
        "Entry for the cfprApSwPortBreakoutTable table."
    INDEX { cfprApSwPortBreakoutInstanceId }
    ::= { cfprApSwPortBreakoutTable 1 }

CfprApSwPortBreakoutEntry ::= SEQUENCE {
    cfprApSwPortBreakoutInstanceId                                   CfprApManagedObjectId,
    cfprApSwPortBreakoutDn                                           CfprApManagedObjectDn,
    cfprApSwPortBreakoutRn                                           SnmpAdminString,
    cfprApSwPortBreakoutBreakoutType                                 CfprApSwBreakoutType,
    cfprApSwPortBreakoutPortId                                       CfprApSwPortBreakoutPortId,
    cfprApSwPortBreakoutSlotId                                       CfprApSwPortBreakoutSlotId
}

cfprApSwPortBreakoutInstanceId OBJECT-TYPE
    SYNTAX       CfprApManagedObjectId
    MAX-ACCESS   not-accessible
    STATUS       current
    DESCRIPTION
        "Instance identifier of the managed object."
    ::= { cfprApSwPortBreakoutEntry 1 }

cfprApSwPortBreakoutDn OBJECT-TYPE
    SYNTAX       CfprApManagedObjectDn
    MAX-ACCESS   read-only
    STATUS       current
    DESCRIPTION
        "Cisco Firepower sw:PortBreakout:dn managed object property"
    ::= { cfprApSwPortBreakoutEntry 2 }

cfprApSwPortBreakoutRn OBJECT-TYPE
    SYNTAX       SnmpAdminString
    MAX-ACCESS   read-only
    STATUS       current
    DESCRIPTION
        "Cisco Firepower sw:PortBreakout:rn managed object property"
    ::= { cfprApSwPortBreakoutEntry 3 }

cfprApSwPortBreakoutBreakoutType OBJECT-TYPE
    SYNTAX       CfprApSwBreakoutType
    MAX-ACCESS   read-only
    STATUS       current
    DESCRIPTION
        "Cisco Firepower sw:PortBreakout:breakoutType managed
        object property"
    ::= { cfprApSwPortBreakoutEntry 4 }

cfprApSwPortBreakoutPortId OBJECT-TYPE
    SYNTAX       CfprApSwPortBreakoutPortId
    MAX-ACCESS   read-only
    STATUS       current
    DESCRIPTION
        "Cisco Firepower sw:PortBreakout:portId managed object property"
    ::= { cfprApSwPortBreakoutEntry 5 }

cfprApSwPortBreakoutSlotId OBJECT-TYPE
    SYNTAX       CfprApSwPortBreakoutSlotId
    MAX-ACCESS   read-only
    STATUS       current
    DESCRIPTION
        "Cisco Firepower sw:PortBreakout:slotId managed object property"
    ::= { cfprApSwPortBreakoutEntry 6 }

cfprApSwSspEthLanMonTable OBJECT-TYPE
    SYNTAX           SEQUENCE OF CfprApSwSspEthLanMonEntry
    MAX-ACCESS       not-accessible
    STATUS           current
    DESCRIPTION
        "Cisco Firepower sw:SspEthLanMon managed object table"
    ::= { cfprApSwObjects 71 }

cfprApSwSspEthLanMonEntry OBJECT-TYPE
    SYNTAX           CfprApSwSspEthLanMonEntry
    MAX-ACCESS       not-accessible
    STATUS           current
    DESCRIPTION
        "Entry for the cfprApSwSspEthLanMonTable table."
    INDEX { cfprApSwSspEthLanMonInstanceId }
    ::= { cfprApSwSspEthLanMonTable 1 }

CfprApSwSspEthLanMonEntry ::= SEQUENCE {
    cfprApSwSspEthLanMonInstanceId                                   CfprApManagedObjectId,
    cfprApSwSspEthLanMonDn                                           CfprApManagedObjectDn,
    cfprApSwSspEthLanMonRn                                           SnmpAdminString,
    cfprApSwSspEthLanMonLocale                                       CfprApSwSspMonDomainLocale,
    cfprApSwSspEthLanMonName                                         SnmpAdminString,
    cfprApSwSspEthLanMonSwitchId                                     CfprApNetworkSwitchId,
    cfprApSwSspEthLanMonTransport                                    CfprApSwSspEthLanMonTransport,
    cfprApSwSspEthLanMonType                                         CfprApSwSspLanMonType
}

cfprApSwSspEthLanMonInstanceId OBJECT-TYPE
    SYNTAX       CfprApManagedObjectId
    MAX-ACCESS   not-accessible
    STATUS       current
    DESCRIPTION
        "Instance identifier of the managed object."
    ::= { cfprApSwSspEthLanMonEntry 1 }

cfprApSwSspEthLanMonDn OBJECT-TYPE
    SYNTAX       CfprApManagedObjectDn
    MAX-ACCESS   read-only
    STATUS       current
    DESCRIPTION
        "Cisco Firepower sw:SspEthLanMon:dn managed object property"
    ::= { cfprApSwSspEthLanMonEntry 2 }

cfprApSwSspEthLanMonRn OBJECT-TYPE
    SYNTAX       SnmpAdminString
    MAX-ACCESS   read-only
    STATUS       current
    DESCRIPTION
        "Cisco Firepower sw:SspEthLanMon:rn managed object property"
    ::= { cfprApSwSspEthLanMonEntry 3 }

cfprApSwSspEthLanMonLocale OBJECT-TYPE
    SYNTAX       CfprApSwSspMonDomainLocale
    MAX-ACCESS   read-only
    STATUS       current
    DESCRIPTION
        "Cisco Firepower sw:SspEthLanMon:locale managed object property"
    ::= { cfprApSwSspEthLanMonEntry 4 }

cfprApSwSspEthLanMonName OBJECT-TYPE
    SYNTAX       SnmpAdminString
    MAX-ACCESS   read-only
    STATUS       current
    DESCRIPTION
        "Cisco Firepower sw:SspEthLanMon:name managed object property"
    ::= { cfprApSwSspEthLanMonEntry 5 }

cfprApSwSspEthLanMonSwitchId OBJECT-TYPE
    SYNTAX       CfprApNetworkSwitchId
    MAX-ACCESS   read-only
    STATUS       current
    DESCRIPTION
        "Cisco Firepower sw:SspEthLanMon:switchId managed object property"
    ::= { cfprApSwSspEthLanMonEntry 6 }

cfprApSwSspEthLanMonTransport OBJECT-TYPE
    SYNTAX       CfprApSwSspEthLanMonTransport
    MAX-ACCESS   read-only
    STATUS       current
    DESCRIPTION
        "Cisco Firepower sw:SspEthLanMon:transport managed
        object property"
    ::= { cfprApSwSspEthLanMonEntry 7 }

cfprApSwSspEthLanMonType OBJECT-TYPE
    SYNTAX       CfprApSwSspLanMonType
    MAX-ACCESS   read-only
    STATUS       current
    DESCRIPTION
        "Cisco Firepower sw:SspEthLanMon:type managed object property"
    ::= { cfprApSwSspEthLanMonEntry 8 }

cfprApSwSspEthMonTable OBJECT-TYPE
    SYNTAX           SEQUENCE OF CfprApSwSspEthMonEntry
    MAX-ACCESS       not-accessible
    STATUS           current
    DESCRIPTION
        "Cisco Firepower sw:SspEthMon managed object table"
    ::= { cfprApSwObjects 72 }

cfprApSwSspEthMonEntry OBJECT-TYPE
    SYNTAX           CfprApSwSspEthMonEntry
    MAX-ACCESS       not-accessible
    STATUS           current
    DESCRIPTION
        "Entry for the cfprApSwSspEthMonTable table."
    INDEX { cfprApSwSspEthMonInstanceId }
    ::= { cfprApSwSspEthMonTable 1 }

CfprApSwSspEthMonEntry ::= SEQUENCE {
    cfprApSwSspEthMonInstanceId                                      CfprApManagedObjectId,
    cfprApSwSspEthMonDn                                              CfprApManagedObjectDn,
    cfprApSwSspEthMonRn                                              SnmpAdminString,
    cfprApSwSspEthMonAdminState                                      CfprApSwSspMonAdminState,
    cfprApSwSspEthMonAppendFlag                                      CfprApFabricPktCaptureAppendFlag,
    cfprApSwSspEthMonDelPcap                                         CfprApSwSspMonDelPcap,
    cfprApSwSspEthMonFsmDescr                                        SnmpAdminString,
    cfprApSwSspEthMonFsmPrev                                         SnmpAdminString,
    cfprApSwSspEthMonFsmProgr                                        Gauge32,
    cfprApSwSspEthMonFsmRmtInvErrCode                                Gauge32,
    cfprApSwSspEthMonFsmRmtInvErrDescr                               SnmpAdminString,
    cfprApSwSspEthMonFsmRmtInvRslt                                   CfprApConditionRemoteInvRslt,
    cfprApSwSspEthMonFsmStageDescr                                   SnmpAdminString,
    cfprApSwSspEthMonFsmStamp                                        DateAndTime,
    cfprApSwSspEthMonFsmStatus                                       SnmpAdminString,
    cfprApSwSspEthMonFsmTry                                          Gauge32,
    cfprApSwSspEthMonLifeCycle                                       CfprApSwPktCaptureLifeCycle,
    cfprApSwSspEthMonName                                            SnmpAdminString,
    cfprApSwSspEthMonPeerDn                                          SnmpAdminString,
    cfprApSwSspEthMonSession                                         Gauge32,
    cfprApSwSspEthMonSessionMemUsage                                 Unsigned64,
    cfprApSwSspEthMonSwitchId                                        CfprApNetworkSwitchId,
    cfprApSwSspEthMonTransport                                       CfprApSwSspEthMonTransport,
    cfprApSwSspEthMonType                                            CfprApSwSspEthMonType
}

cfprApSwSspEthMonInstanceId OBJECT-TYPE
    SYNTAX       CfprApManagedObjectId
    MAX-ACCESS   not-accessible
    STATUS       current
    DESCRIPTION
        "Instance identifier of the managed object."
    ::= { cfprApSwSspEthMonEntry 1 }

cfprApSwSspEthMonDn OBJECT-TYPE
    SYNTAX       CfprApManagedObjectDn
    MAX-ACCESS   read-only
    STATUS       current
    DESCRIPTION
        "Cisco Firepower sw:SspEthMon:dn managed object property"
    ::= { cfprApSwSspEthMonEntry 2 }

cfprApSwSspEthMonRn OBJECT-TYPE
    SYNTAX       SnmpAdminString
    MAX-ACCESS   read-only
    STATUS       current
    DESCRIPTION
        "Cisco Firepower sw:SspEthMon:rn managed object property"
    ::= { cfprApSwSspEthMonEntry 3 }

cfprApSwSspEthMonAdminState OBJECT-TYPE
    SYNTAX       CfprApSwSspMonAdminState
    MAX-ACCESS   read-only
    STATUS       current
    DESCRIPTION
        "Cisco Firepower sw:SspEthMon:adminState managed object property"
    ::= { cfprApSwSspEthMonEntry 4 }

cfprApSwSspEthMonAppendFlag OBJECT-TYPE
    SYNTAX       CfprApFabricPktCaptureAppendFlag
    MAX-ACCESS   read-only
    STATUS       current
    DESCRIPTION
        "Cisco Firepower sw:SspEthMon:appendFlag managed object property"
    ::= { cfprApSwSspEthMonEntry 5 }

cfprApSwSspEthMonDelPcap OBJECT-TYPE
    SYNTAX       CfprApSwSspMonDelPcap
    MAX-ACCESS   read-only
    STATUS       current
    DESCRIPTION
        "Cisco Firepower sw:SspEthMon:delPcap managed object property"
    ::= { cfprApSwSspEthMonEntry 6 }

cfprApSwSspEthMonFsmDescr OBJECT-TYPE
    SYNTAX       SnmpAdminString
    MAX-ACCESS   read-only
    STATUS       current
    DESCRIPTION
        "Cisco Firepower sw:SspEthMon:fsmDescr managed object property"
    ::= { cfprApSwSspEthMonEntry 7 }

cfprApSwSspEthMonFsmPrev OBJECT-TYPE
    SYNTAX       SnmpAdminString
    MAX-ACCESS   read-only
    STATUS       current
    DESCRIPTION
        "Cisco Firepower sw:SspEthMon:fsmPrev managed object property"
    ::= { cfprApSwSspEthMonEntry 8 }

cfprApSwSspEthMonFsmProgr OBJECT-TYPE
    SYNTAX       Gauge32
    MAX-ACCESS   read-only
    STATUS       current
    DESCRIPTION
        "Cisco Firepower sw:SspEthMon:fsmProgr managed object property"
    ::= { cfprApSwSspEthMonEntry 9 }

cfprApSwSspEthMonFsmRmtInvErrCode OBJECT-TYPE
    SYNTAX       Gauge32
    MAX-ACCESS   read-only
    STATUS       current
    DESCRIPTION
        "Cisco Firepower sw:SspEthMon:fsmRmtInvErrCode
        managed object property"
    ::= { cfprApSwSspEthMonEntry 10 }

cfprApSwSspEthMonFsmRmtInvErrDescr OBJECT-TYPE
    SYNTAX       SnmpAdminString
    MAX-ACCESS   read-only
    STATUS       current
    DESCRIPTION
        "Cisco Firepower sw:SspEthMon:fsmRmtInvErrDescr
        managed object property"
    ::= { cfprApSwSspEthMonEntry 11 }

cfprApSwSspEthMonFsmRmtInvRslt OBJECT-TYPE
    SYNTAX       CfprApConditionRemoteInvRslt
    MAX-ACCESS   read-only
    STATUS       current
    DESCRIPTION
        "Cisco Firepower sw:SspEthMon:fsmRmtInvRslt managed
        object property"
    ::= { cfprApSwSspEthMonEntry 12 }

cfprApSwSspEthMonFsmStageDescr OBJECT-TYPE
    SYNTAX       SnmpAdminString
    MAX-ACCESS   read-only
    STATUS       current
    DESCRIPTION
        "Cisco Firepower sw:SspEthMon:fsmStageDescr managed
        object property"
    ::= { cfprApSwSspEthMonEntry 13 }

cfprApSwSspEthMonFsmStamp OBJECT-TYPE
    SYNTAX       DateAndTime
    MAX-ACCESS   read-only
    STATUS       current
    DESCRIPTION
        "Cisco Firepower sw:SspEthMon:fsmStamp managed object property"
    ::= { cfprApSwSspEthMonEntry 14 }

cfprApSwSspEthMonFsmStatus OBJECT-TYPE
    SYNTAX       SnmpAdminString
    MAX-ACCESS   read-only
    STATUS       current
    DESCRIPTION
        "Cisco Firepower sw:SspEthMon:fsmStatus managed object property"
    ::= { cfprApSwSspEthMonEntry 15 }

cfprApSwSspEthMonFsmTry OBJECT-TYPE
    SYNTAX       Gauge32
    MAX-ACCESS   read-only
    STATUS       current
    DESCRIPTION
        "Cisco Firepower sw:SspEthMon:fsmTry managed object property"
    ::= { cfprApSwSspEthMonEntry 16 }

cfprApSwSspEthMonLifeCycle OBJECT-TYPE
    SYNTAX       CfprApSwPktCaptureLifeCycle
    MAX-ACCESS   read-only
    STATUS       current
    DESCRIPTION
        "Cisco Firepower sw:SspEthMon:lifeCycle managed object property"
    ::= { cfprApSwSspEthMonEntry 17 }

cfprApSwSspEthMonName OBJECT-TYPE
    SYNTAX       SnmpAdminString
    MAX-ACCESS   read-only
    STATUS       current
    DESCRIPTION
        "Cisco Firepower sw:SspEthMon:name managed object property"
    ::= { cfprApSwSspEthMonEntry 18 }

cfprApSwSspEthMonPeerDn OBJECT-TYPE
    SYNTAX       SnmpAdminString
    MAX-ACCESS   read-only
    STATUS       current
    DESCRIPTION
        "Cisco Firepower sw:SspEthMon:peerDn managed object property"
    ::= { cfprApSwSspEthMonEntry 19 }

cfprApSwSspEthMonSession OBJECT-TYPE
    SYNTAX       Gauge32
    MAX-ACCESS   read-only
    STATUS       current
    DESCRIPTION
        "Cisco Firepower sw:SspEthMon:session managed object property"
    ::= { cfprApSwSspEthMonEntry 20 }

cfprApSwSspEthMonSessionMemUsage OBJECT-TYPE
    SYNTAX       Unsigned64
    MAX-ACCESS   read-only
    STATUS       current
    DESCRIPTION
        "Cisco Firepower sw:SspEthMon:sessionMemUsage managed
        object property"
    ::= { cfprApSwSspEthMonEntry 21 }

cfprApSwSspEthMonSwitchId OBJECT-TYPE
    SYNTAX       CfprApNetworkSwitchId
    MAX-ACCESS   read-only
    STATUS       current
    DESCRIPTION
        "Cisco Firepower sw:SspEthMon:switchId managed object property"
    ::= { cfprApSwSspEthMonEntry 22 }

cfprApSwSspEthMonTransport OBJECT-TYPE
    SYNTAX       CfprApSwSspEthMonTransport
    MAX-ACCESS   read-only
    STATUS       current
    DESCRIPTION
        "Cisco Firepower sw:SspEthMon:transport managed object property"
    ::= { cfprApSwSspEthMonEntry 23 }

cfprApSwSspEthMonType OBJECT-TYPE
    SYNTAX       CfprApSwSspEthMonType
    MAX-ACCESS   read-only
    STATUS       current
    DESCRIPTION
        "Cisco Firepower sw:SspEthMon:type managed object property"
    ::= { cfprApSwSspEthMonEntry 24 }

cfprApSwSspEthMonFilterEpTable OBJECT-TYPE
    SYNTAX           SEQUENCE OF CfprApSwSspEthMonFilterEpEntry
    MAX-ACCESS       not-accessible
    STATUS           current
    DESCRIPTION
        "Cisco Firepower sw:SspEthMonFilterEp managed object table"
    ::= { cfprApSwObjects 73 }

cfprApSwSspEthMonFilterEpEntry OBJECT-TYPE
    SYNTAX           CfprApSwSspEthMonFilterEpEntry
    MAX-ACCESS       not-accessible
    STATUS           current
    DESCRIPTION
        "Entry for the cfprApSwSspEthMonFilterEpTable table."
    INDEX { cfprApSwSspEthMonFilterEpInstanceId }
    ::= { cfprApSwSspEthMonFilterEpTable 1 }

CfprApSwSspEthMonFilterEpEntry ::= SEQUENCE {
    cfprApSwSspEthMonFilterEpInstanceId                              CfprApManagedObjectId,
    cfprApSwSspEthMonFilterEpDn                                      CfprApManagedObjectDn,
    cfprApSwSspEthMonFilterEpRn                                      SnmpAdminString,
    cfprApSwSspEthMonFilterEpDestIp                                  InetAddressIPv4,
    cfprApSwSspEthMonFilterEpDestMAC                                 MacAddress,
    cfprApSwSspEthMonFilterEpDestPort                                CfprApFabricPort,
    cfprApSwSspEthMonFilterEpEthertype                               Gauge32,
    cfprApSwSspEthMonFilterEpFilterFlag                              Gauge32,
    cfprApSwSspEthMonFilterEpIvlan                                   Gauge32,
    cfprApSwSspEthMonFilterEpLifeCycle                               CfprApSwPktCaptureLifeCycle,
    cfprApSwSspEthMonFilterEpNameId                                  SnmpAdminString,
    cfprApSwSspEthMonFilterEpOvlan                                   Gauge32,
    cfprApSwSspEthMonFilterEpPeerDn                                  SnmpAdminString,
    cfprApSwSspEthMonFilterEpProtocol                                Gauge32,
    cfprApSwSspEthMonFilterEpRefCount                                Gauge32,
    cfprApSwSspEthMonFilterEpSrcIp                                   InetAddressIPv4,
    cfprApSwSspEthMonFilterEpSrcMAC                                  MacAddress,
    cfprApSwSspEthMonFilterEpSrcPort                                 CfprApFabricPort
}

cfprApSwSspEthMonFilterEpInstanceId OBJECT-TYPE
    SYNTAX       CfprApManagedObjectId
    MAX-ACCESS   not-accessible
    STATUS       current
    DESCRIPTION
        "Instance identifier of the managed object."
    ::= { cfprApSwSspEthMonFilterEpEntry 1 }

cfprApSwSspEthMonFilterEpDn OBJECT-TYPE
    SYNTAX       CfprApManagedObjectDn
    MAX-ACCESS   read-only
    STATUS       current
    DESCRIPTION
        "Cisco Firepower sw:SspEthMonFilterEp:dn managed object property"
    ::= { cfprApSwSspEthMonFilterEpEntry 2 }

cfprApSwSspEthMonFilterEpRn OBJECT-TYPE
    SYNTAX       SnmpAdminString
    MAX-ACCESS   read-only
    STATUS       current
    DESCRIPTION
        "Cisco Firepower sw:SspEthMonFilterEp:rn managed object property"
    ::= { cfprApSwSspEthMonFilterEpEntry 3 }

cfprApSwSspEthMonFilterEpDestIp OBJECT-TYPE
    SYNTAX       InetAddressIPv4
    MAX-ACCESS   read-only
    STATUS       current
    DESCRIPTION
        "Cisco Firepower sw:SspEthMonFilterEp:destIp managed
        object property"
    ::= { cfprApSwSspEthMonFilterEpEntry 4 }

cfprApSwSspEthMonFilterEpDestMAC OBJECT-TYPE
    SYNTAX       MacAddress
    MAX-ACCESS   read-only
    STATUS       current
    DESCRIPTION
        "Cisco Firepower sw:SspEthMonFilterEp:destMAC managed
        object property"
    ::= { cfprApSwSspEthMonFilterEpEntry 5 }

cfprApSwSspEthMonFilterEpDestPort OBJECT-TYPE
    SYNTAX       CfprApFabricPort
    MAX-ACCESS   read-only
    STATUS       current
    DESCRIPTION
        "Cisco Firepower sw:SspEthMonFilterEp:destPort
        managed object property"
    ::= { cfprApSwSspEthMonFilterEpEntry 6 }

cfprApSwSspEthMonFilterEpEthertype OBJECT-TYPE
    SYNTAX       Gauge32
    MAX-ACCESS   read-only
    STATUS       current
    DESCRIPTION
        "Cisco Firepower sw:SspEthMonFilterEp:ethertype
        managed object property"
    ::= { cfprApSwSspEthMonFilterEpEntry 7 }

cfprApSwSspEthMonFilterEpFilterFlag OBJECT-TYPE
    SYNTAX       Gauge32
    MAX-ACCESS   read-only
    STATUS       current
    DESCRIPTION
        "Cisco Firepower sw:SspEthMonFilterEp:filterFlag
        managed object property"
    ::= { cfprApSwSspEthMonFilterEpEntry 8 }

cfprApSwSspEthMonFilterEpIvlan OBJECT-TYPE
    SYNTAX       Gauge32
    MAX-ACCESS   read-only
    STATUS       current
    DESCRIPTION
        "Cisco Firepower sw:SspEthMonFilterEp:ivlan managed
        object property"
    ::= { cfprApSwSspEthMonFilterEpEntry 9 }

cfprApSwSspEthMonFilterEpLifeCycle OBJECT-TYPE
    SYNTAX       CfprApSwPktCaptureLifeCycle
    MAX-ACCESS   read-only
    STATUS       current
    DESCRIPTION
        "Cisco Firepower sw:SspEthMonFilterEp:lifeCycle
        managed object property"
    ::= { cfprApSwSspEthMonFilterEpEntry 10 }

cfprApSwSspEthMonFilterEpNameId OBJECT-TYPE
    SYNTAX       SnmpAdminString
    MAX-ACCESS   read-only
    STATUS       current
    DESCRIPTION
        "Cisco Firepower sw:SspEthMonFilterEp:nameId managed
        object property"
    ::= { cfprApSwSspEthMonFilterEpEntry 11 }

cfprApSwSspEthMonFilterEpOvlan OBJECT-TYPE
    SYNTAX       Gauge32
    MAX-ACCESS   read-only
    STATUS       current
    DESCRIPTION
        "Cisco Firepower sw:SspEthMonFilterEp:ovlan managed
        object property"
    ::= { cfprApSwSspEthMonFilterEpEntry 12 }

cfprApSwSspEthMonFilterEpPeerDn OBJECT-TYPE
    SYNTAX       SnmpAdminString
    MAX-ACCESS   read-only
    STATUS       current
    DESCRIPTION
        "Cisco Firepower sw:SspEthMonFilterEp:peerDn managed
        object property"
    ::= { cfprApSwSspEthMonFilterEpEntry 13 }

cfprApSwSspEthMonFilterEpProtocol OBJECT-TYPE
    SYNTAX       Gauge32
    MAX-ACCESS   read-only
    STATUS       current
    DESCRIPTION
        "Cisco Firepower sw:SspEthMonFilterEp:protocol
        managed object property"
    ::= { cfprApSwSspEthMonFilterEpEntry 14 }

cfprApSwSspEthMonFilterEpRefCount OBJECT-TYPE
    SYNTAX       Gauge32
    MAX-ACCESS   read-only
    STATUS       current
    DESCRIPTION
        "Cisco Firepower sw:SspEthMonFilterEp:refCount
        managed object property"
    ::= { cfprApSwSspEthMonFilterEpEntry 15 }

cfprApSwSspEthMonFilterEpSrcIp OBJECT-TYPE
    SYNTAX       InetAddressIPv4
    MAX-ACCESS   read-only
    STATUS       current
    DESCRIPTION
        "Cisco Firepower sw:SspEthMonFilterEp:srcIp managed
        object property"
    ::= { cfprApSwSspEthMonFilterEpEntry 16 }

cfprApSwSspEthMonFilterEpSrcMAC OBJECT-TYPE
    SYNTAX       MacAddress
    MAX-ACCESS   read-only
    STATUS       current
    DESCRIPTION
        "Cisco Firepower sw:SspEthMonFilterEp:srcMAC managed
        object property"
    ::= { cfprApSwSspEthMonFilterEpEntry 17 }

cfprApSwSspEthMonFilterEpSrcPort OBJECT-TYPE
    SYNTAX       CfprApFabricPort
    MAX-ACCESS   read-only
    STATUS       current
    DESCRIPTION
        "Cisco Firepower sw:SspEthMonFilterEp:srcPort managed
        object property"
    ::= { cfprApSwSspEthMonFilterEpEntry 18 }

cfprApSwSspEthMonFsmTable OBJECT-TYPE
    SYNTAX           SEQUENCE OF CfprApSwSspEthMonFsmEntry
    MAX-ACCESS       not-accessible
    STATUS           current
    DESCRIPTION
        "Cisco Firepower sw:SspEthMonFsm managed object table"
    ::= { cfprApSwObjects 74 }

cfprApSwSspEthMonFsmEntry OBJECT-TYPE
    SYNTAX           CfprApSwSspEthMonFsmEntry
    MAX-ACCESS       not-accessible
    STATUS           current
    DESCRIPTION
        "Entry for the cfprApSwSspEthMonFsmTable table."
    INDEX { cfprApSwSspEthMonFsmInstanceId }
    ::= { cfprApSwSspEthMonFsmTable 1 }

CfprApSwSspEthMonFsmEntry ::= SEQUENCE {
    cfprApSwSspEthMonFsmInstanceId                                   CfprApManagedObjectId,
    cfprApSwSspEthMonFsmDn                                           CfprApManagedObjectDn,
    cfprApSwSspEthMonFsmRn                                           SnmpAdminString,
    cfprApSwSspEthMonFsmCompletionTime                               DateAndTime,
    cfprApSwSspEthMonFsmCurrentFsm                                   CfprApSwSspEthMonFsmCurrentFsm,
    cfprApSwSspEthMonFsmDescrData                                    SnmpAdminString,
    cfprApSwSspEthMonFsmFsmStatus                                    CfprApFsmFsmStageStatus,
    cfprApSwSspEthMonFsmProgress                                     Gauge32,
    cfprApSwSspEthMonFsmRmtErrCode                                   Gauge32,
    cfprApSwSspEthMonFsmRmtErrDescr                                  SnmpAdminString,
    cfprApSwSspEthMonFsmRmtRslt                                      CfprApConditionRemoteInvRslt
}

cfprApSwSspEthMonFsmInstanceId OBJECT-TYPE
    SYNTAX       CfprApManagedObjectId
    MAX-ACCESS   not-accessible
    STATUS       current
    DESCRIPTION
        "Instance identifier of the managed object."
    ::= { cfprApSwSspEthMonFsmEntry 1 }

cfprApSwSspEthMonFsmDn OBJECT-TYPE
    SYNTAX       CfprApManagedObjectDn
    MAX-ACCESS   read-only
    STATUS       current
    DESCRIPTION
        "Cisco Firepower sw:SspEthMonFsm:dn managed object property"
    ::= { cfprApSwSspEthMonFsmEntry 2 }

cfprApSwSspEthMonFsmRn OBJECT-TYPE
    SYNTAX       SnmpAdminString
    MAX-ACCESS   read-only
    STATUS       current
    DESCRIPTION
        "Cisco Firepower sw:SspEthMonFsm:rn managed object property"
    ::= { cfprApSwSspEthMonFsmEntry 3 }

cfprApSwSspEthMonFsmCompletionTime OBJECT-TYPE
    SYNTAX       DateAndTime
    MAX-ACCESS   read-only
    STATUS       current
    DESCRIPTION
        "Cisco Firepower sw:SspEthMonFsm:completionTime
        managed object property"
    ::= { cfprApSwSspEthMonFsmEntry 4 }

cfprApSwSspEthMonFsmCurrentFsm OBJECT-TYPE
    SYNTAX       CfprApSwSspEthMonFsmCurrentFsm
    MAX-ACCESS   read-only
    STATUS       current
    DESCRIPTION
        "Cisco Firepower sw:SspEthMonFsm:currentFsm managed
        object property"
    ::= { cfprApSwSspEthMonFsmEntry 5 }

cfprApSwSspEthMonFsmDescrData OBJECT-TYPE
    SYNTAX       SnmpAdminString
    MAX-ACCESS   read-only
    STATUS       current
    DESCRIPTION
        "Cisco Firepower sw:SspEthMonFsm:descr managed object property"
    ::= { cfprApSwSspEthMonFsmEntry 6 }

cfprApSwSspEthMonFsmFsmStatus OBJECT-TYPE
    SYNTAX       CfprApFsmFsmStageStatus
    MAX-ACCESS   read-only
    STATUS       current
    DESCRIPTION
        "Cisco Firepower sw:SspEthMonFsm:fsmStatus managed
        object property"
    ::= { cfprApSwSspEthMonFsmEntry 7 }

cfprApSwSspEthMonFsmProgress OBJECT-TYPE
    SYNTAX       Gauge32
    MAX-ACCESS   read-only
    STATUS       current
    DESCRIPTION
        "Cisco Firepower sw:SspEthMonFsm:progress managed object property"
    ::= { cfprApSwSspEthMonFsmEntry 8 }

cfprApSwSspEthMonFsmRmtErrCode OBJECT-TYPE
    SYNTAX       Gauge32
    MAX-ACCESS   read-only
    STATUS       current
    DESCRIPTION
        "Cisco Firepower sw:SspEthMonFsm:rmtErrCode managed
        object property"
    ::= { cfprApSwSspEthMonFsmEntry 9 }

cfprApSwSspEthMonFsmRmtErrDescr OBJECT-TYPE
    SYNTAX       SnmpAdminString
    MAX-ACCESS   read-only
    STATUS       current
    DESCRIPTION
        "Cisco Firepower sw:SspEthMonFsm:rmtErrDescr managed
        object property"
    ::= { cfprApSwSspEthMonFsmEntry 10 }

cfprApSwSspEthMonFsmRmtRslt OBJECT-TYPE
    SYNTAX       CfprApConditionRemoteInvRslt
    MAX-ACCESS   read-only
    STATUS       current
    DESCRIPTION
        "Cisco Firepower sw:SspEthMonFsm:rmtRslt managed object property"
    ::= { cfprApSwSspEthMonFsmEntry 11 }

cfprApSwSspEthMonFsmStageTable OBJECT-TYPE
    SYNTAX           SEQUENCE OF CfprApSwSspEthMonFsmStageEntry
    MAX-ACCESS       not-accessible
    STATUS           current
    DESCRIPTION
        "Cisco Firepower sw:SspEthMonFsmStage managed object table"
    ::= { cfprApSwObjects 75 }

cfprApSwSspEthMonFsmStageEntry OBJECT-TYPE
    SYNTAX           CfprApSwSspEthMonFsmStageEntry
    MAX-ACCESS       not-accessible
    STATUS           current
    DESCRIPTION
        "Entry for the cfprApSwSspEthMonFsmStageTable table."
    INDEX { cfprApSwSspEthMonFsmStageInstanceId }
    ::= { cfprApSwSspEthMonFsmStageTable 1 }

CfprApSwSspEthMonFsmStageEntry ::= SEQUENCE {
    cfprApSwSspEthMonFsmStageInstanceId                              CfprApManagedObjectId,
    cfprApSwSspEthMonFsmStageDn                                      CfprApManagedObjectDn,
    cfprApSwSspEthMonFsmStageRn                                      SnmpAdminString,
    cfprApSwSspEthMonFsmStageDescrData                               SnmpAdminString,
    cfprApSwSspEthMonFsmStageLastUpdateTime                          DateAndTime,
    cfprApSwSspEthMonFsmStageName                                    CfprApSwSspEthMonFsmStageName,
    cfprApSwSspEthMonFsmStageOrder                                   Gauge32,
    cfprApSwSspEthMonFsmStageRetry                                   Gauge32,
    cfprApSwSspEthMonFsmStageStageStatus                             CfprApFsmFsmStageStatus
}

cfprApSwSspEthMonFsmStageInstanceId OBJECT-TYPE
    SYNTAX       CfprApManagedObjectId
    MAX-ACCESS   not-accessible
    STATUS       current
    DESCRIPTION
        "Instance identifier of the managed object."
    ::= { cfprApSwSspEthMonFsmStageEntry 1 }

cfprApSwSspEthMonFsmStageDn OBJECT-TYPE
    SYNTAX       CfprApManagedObjectDn
    MAX-ACCESS   read-only
    STATUS       current
    DESCRIPTION
        "Cisco Firepower sw:SspEthMonFsmStage:dn managed object property"
    ::= { cfprApSwSspEthMonFsmStageEntry 2 }

cfprApSwSspEthMonFsmStageRn OBJECT-TYPE
    SYNTAX       SnmpAdminString
    MAX-ACCESS   read-only
    STATUS       current
    DESCRIPTION
        "Cisco Firepower sw:SspEthMonFsmStage:rn managed object property"
    ::= { cfprApSwSspEthMonFsmStageEntry 3 }

cfprApSwSspEthMonFsmStageDescrData OBJECT-TYPE
    SYNTAX       SnmpAdminString
    MAX-ACCESS   read-only
    STATUS       current
    DESCRIPTION
        "Cisco Firepower sw:SspEthMonFsmStage:descr managed
        object property"
    ::= { cfprApSwSspEthMonFsmStageEntry 4 }

cfprApSwSspEthMonFsmStageLastUpdateTime OBJECT-TYPE
    SYNTAX       DateAndTime
    MAX-ACCESS   read-only
    STATUS       current
    DESCRIPTION
        "Cisco Firepower sw:SspEthMonFsmStage:lastUpdateTime
        managed object property"
    ::= { cfprApSwSspEthMonFsmStageEntry 5 }

cfprApSwSspEthMonFsmStageName OBJECT-TYPE
    SYNTAX       CfprApSwSspEthMonFsmStageName
    MAX-ACCESS   read-only
    STATUS       current
    DESCRIPTION
        "Cisco Firepower sw:SspEthMonFsmStage:name managed
        object property"
    ::= { cfprApSwSspEthMonFsmStageEntry 6 }

cfprApSwSspEthMonFsmStageOrder OBJECT-TYPE
    SYNTAX       Gauge32
    MAX-ACCESS   read-only
    STATUS       current
    DESCRIPTION
        "Cisco Firepower sw:SspEthMonFsmStage:order managed
        object property"
    ::= { cfprApSwSspEthMonFsmStageEntry 7 }

cfprApSwSspEthMonFsmStageRetry OBJECT-TYPE
    SYNTAX       Gauge32
    MAX-ACCESS   read-only
    STATUS       current
    DESCRIPTION
        "Cisco Firepower sw:SspEthMonFsmStage:retry managed
        object property"
    ::= { cfprApSwSspEthMonFsmStageEntry 8 }

cfprApSwSspEthMonFsmStageStageStatus OBJECT-TYPE
    SYNTAX       CfprApFsmFsmStageStatus
    MAX-ACCESS   read-only
    STATUS       current
    DESCRIPTION
        "Cisco Firepower sw:SspEthMonFsmStage:stageStatus
        managed object property"
    ::= { cfprApSwSspEthMonFsmStageEntry 9 }

cfprApSwSspEthMonFsmTaskTable OBJECT-TYPE
    SYNTAX           SEQUENCE OF CfprApSwSspEthMonFsmTaskEntry
    MAX-ACCESS       not-accessible
    STATUS           current
    DESCRIPTION
        "Cisco Firepower sw:SspEthMonFsmTask managed object table"
    ::= { cfprApSwObjects 76 }

cfprApSwSspEthMonFsmTaskEntry OBJECT-TYPE
    SYNTAX           CfprApSwSspEthMonFsmTaskEntry
    MAX-ACCESS       not-accessible
    STATUS           current
    DESCRIPTION
        "Entry for the cfprApSwSspEthMonFsmTaskTable table."
    INDEX { cfprApSwSspEthMonFsmTaskInstanceId }
    ::= { cfprApSwSspEthMonFsmTaskTable 1 }

CfprApSwSspEthMonFsmTaskEntry ::= SEQUENCE {
    cfprApSwSspEthMonFsmTaskInstanceId                               CfprApManagedObjectId,
    cfprApSwSspEthMonFsmTaskDn                                       CfprApManagedObjectDn,
    cfprApSwSspEthMonFsmTaskRn                                       SnmpAdminString,
    cfprApSwSspEthMonFsmTaskCompletion                               CfprApFsmCompletion,
    cfprApSwSspEthMonFsmTaskFlags                                    CfprApFsmFlags,
    cfprApSwSspEthMonFsmTaskItem                                     CfprApSwSspEthMonFsmTaskItem,
    cfprApSwSspEthMonFsmTaskSeqId                                    Gauge32
}

cfprApSwSspEthMonFsmTaskInstanceId OBJECT-TYPE
    SYNTAX       CfprApManagedObjectId
    MAX-ACCESS   not-accessible
    STATUS       current
    DESCRIPTION
        "Instance identifier of the managed object."
    ::= { cfprApSwSspEthMonFsmTaskEntry 1 }

cfprApSwSspEthMonFsmTaskDn OBJECT-TYPE
    SYNTAX       CfprApManagedObjectDn
    MAX-ACCESS   read-only
    STATUS       current
    DESCRIPTION
        "Cisco Firepower sw:SspEthMonFsmTask:dn managed object property"
    ::= { cfprApSwSspEthMonFsmTaskEntry 2 }

cfprApSwSspEthMonFsmTaskRn OBJECT-TYPE
    SYNTAX       SnmpAdminString
    MAX-ACCESS   read-only
    STATUS       current
    DESCRIPTION
        "Cisco Firepower sw:SspEthMonFsmTask:rn managed object property"
    ::= { cfprApSwSspEthMonFsmTaskEntry 3 }

cfprApSwSspEthMonFsmTaskCompletion OBJECT-TYPE
    SYNTAX       CfprApFsmCompletion
    MAX-ACCESS   read-only
    STATUS       current
    DESCRIPTION
        "Cisco Firepower sw:SspEthMonFsmTask:completion
        managed object property"
    ::= { cfprApSwSspEthMonFsmTaskEntry 4 }

cfprApSwSspEthMonFsmTaskFlags OBJECT-TYPE
    SYNTAX       CfprApFsmFlags
    MAX-ACCESS   read-only
    STATUS       current
    DESCRIPTION
        "Cisco Firepower sw:SspEthMonFsmTask:flags managed
        object property"
    ::= { cfprApSwSspEthMonFsmTaskEntry 5 }

cfprApSwSspEthMonFsmTaskItem OBJECT-TYPE
    SYNTAX       CfprApSwSspEthMonFsmTaskItem
    MAX-ACCESS   read-only
    STATUS       current
    DESCRIPTION
        "Cisco Firepower sw:SspEthMonFsmTask:item managed object property"
    ::= { cfprApSwSspEthMonFsmTaskEntry 6 }

cfprApSwSspEthMonFsmTaskSeqId OBJECT-TYPE
    SYNTAX       Gauge32
    MAX-ACCESS   read-only
    STATUS       current
    DESCRIPTION
        "Cisco Firepower sw:SspEthMonFsmTask:seqId managed
        object property"
    ::= { cfprApSwSspEthMonFsmTaskEntry 7 }

cfprApSwSspEthMonSrcAppEpTable OBJECT-TYPE
    SYNTAX           SEQUENCE OF CfprApSwSspEthMonSrcAppEpEntry
    MAX-ACCESS       not-accessible
    STATUS           current
    DESCRIPTION
        "Cisco Firepower sw:SspEthMonSrcAppEp managed object table"
    ::= { cfprApSwObjects 77 }

cfprApSwSspEthMonSrcAppEpEntry OBJECT-TYPE
    SYNTAX           CfprApSwSspEthMonSrcAppEpEntry
    MAX-ACCESS       not-accessible
    STATUS           current
    DESCRIPTION
        "Entry for the cfprApSwSspEthMonSrcAppEpTable table."
    INDEX { cfprApSwSspEthMonSrcAppEpInstanceId }
    ::= { cfprApSwSspEthMonSrcAppEpTable 1 }

CfprApSwSspEthMonSrcAppEpEntry ::= SEQUENCE {
    cfprApSwSspEthMonSrcAppEpInstanceId                              CfprApManagedObjectId,
    cfprApSwSspEthMonSrcAppEpDn                                      CfprApManagedObjectDn,
    cfprApSwSspEthMonSrcAppEpRn                                      SnmpAdminString,
    cfprApSwSspEthMonSrcAppEpAppName                                 SnmpAdminString,
    cfprApSwSspEthMonSrcAppEpExternalPortDn                          SnmpAdminString,
    cfprApSwSspEthMonSrcAppEpFilter                                  SnmpAdminString,
    cfprApSwSspEthMonSrcAppEpFilterDn                                SnmpAdminString,
    cfprApSwSspEthMonSrcAppEpLifeCycle                               CfprApSwPktCaptureLifeCycle,
    cfprApSwSspEthMonSrcAppEpLinkName                                SnmpAdminString,
    cfprApSwSspEthMonSrcAppEpPcapfile                                SnmpAdminString,
    cfprApSwSspEthMonSrcAppEpPcapfilename                            SnmpAdminString,
    cfprApSwSspEthMonSrcAppEpPcapsize                                Gauge32,
    cfprApSwSspEthMonSrcAppEpPeerDn                                  SnmpAdminString,
    cfprApSwSspEthMonSrcAppEpPortChannelDn                           SnmpAdminString,
    cfprApSwSspEthMonSrcAppEpPortName                                SnmpAdminString,
    cfprApSwSspEthMonSrcAppEpSlotId                                  Gauge32
}

cfprApSwSspEthMonSrcAppEpInstanceId OBJECT-TYPE
    SYNTAX       CfprApManagedObjectId
    MAX-ACCESS   not-accessible
    STATUS       current
    DESCRIPTION
        "Instance identifier of the managed object."
    ::= { cfprApSwSspEthMonSrcAppEpEntry 1 }

cfprApSwSspEthMonSrcAppEpDn OBJECT-TYPE
    SYNTAX       CfprApManagedObjectDn
    MAX-ACCESS   read-only
    STATUS       current
    DESCRIPTION
        "Cisco Firepower sw:SspEthMonSrcAppEp:dn managed object property"
    ::= { cfprApSwSspEthMonSrcAppEpEntry 2 }

cfprApSwSspEthMonSrcAppEpRn OBJECT-TYPE
    SYNTAX       SnmpAdminString
    MAX-ACCESS   read-only
    STATUS       current
    DESCRIPTION
        "Cisco Firepower sw:SspEthMonSrcAppEp:rn managed object property"
    ::= { cfprApSwSspEthMonSrcAppEpEntry 3 }

cfprApSwSspEthMonSrcAppEpAppName OBJECT-TYPE
    SYNTAX       SnmpAdminString
    MAX-ACCESS   read-only
    STATUS       current
    DESCRIPTION
        "Cisco Firepower sw:SspEthMonSrcAppEp:appName managed
        object property"
    ::= { cfprApSwSspEthMonSrcAppEpEntry 4 }

cfprApSwSspEthMonSrcAppEpExternalPortDn OBJECT-TYPE
    SYNTAX       SnmpAdminString
    MAX-ACCESS   read-only
    STATUS       current
    DESCRIPTION
        "Cisco Firepower sw:SspEthMonSrcAppEp:externalPortDn
        managed object property"
    ::= { cfprApSwSspEthMonSrcAppEpEntry 5 }

cfprApSwSspEthMonSrcAppEpFilter OBJECT-TYPE
    SYNTAX       SnmpAdminString
    MAX-ACCESS   read-only
    STATUS       current
    DESCRIPTION
        "Cisco Firepower sw:SspEthMonSrcAppEp:filter managed
        object property"
    ::= { cfprApSwSspEthMonSrcAppEpEntry 6 }

cfprApSwSspEthMonSrcAppEpFilterDn OBJECT-TYPE
    SYNTAX       SnmpAdminString
    MAX-ACCESS   read-only
    STATUS       current
    DESCRIPTION
        "Cisco Firepower sw:SspEthMonSrcAppEp:filterDn
        managed object property"
    ::= { cfprApSwSspEthMonSrcAppEpEntry 7 }

cfprApSwSspEthMonSrcAppEpLifeCycle OBJECT-TYPE
    SYNTAX       CfprApSwPktCaptureLifeCycle
    MAX-ACCESS   read-only
    STATUS       current
    DESCRIPTION
        "Cisco Firepower sw:SspEthMonSrcAppEp:lifeCycle
        managed object property"
    ::= { cfprApSwSspEthMonSrcAppEpEntry 8 }

cfprApSwSspEthMonSrcAppEpLinkName OBJECT-TYPE
    SYNTAX       SnmpAdminString
    MAX-ACCESS   read-only
    STATUS       current
    DESCRIPTION
        "Cisco Firepower sw:SspEthMonSrcAppEp:linkName
        managed object property"
    ::= { cfprApSwSspEthMonSrcAppEpEntry 9 }

cfprApSwSspEthMonSrcAppEpPcapfile OBJECT-TYPE
    SYNTAX       SnmpAdminString
    MAX-ACCESS   read-only
    STATUS       current
    DESCRIPTION
        "Cisco Firepower sw:SspEthMonSrcAppEp:pcapfile
        managed object property"
    ::= { cfprApSwSspEthMonSrcAppEpEntry 10 }

cfprApSwSspEthMonSrcAppEpPcapfilename OBJECT-TYPE
    SYNTAX       SnmpAdminString
    MAX-ACCESS   read-only
    STATUS       current
    DESCRIPTION
        "Cisco Firepower sw:SspEthMonSrcAppEp:pcapfilename
        managed object property"
    ::= { cfprApSwSspEthMonSrcAppEpEntry 11 }

cfprApSwSspEthMonSrcAppEpPcapsize OBJECT-TYPE
    SYNTAX       Gauge32
    MAX-ACCESS   read-only
    STATUS       current
    DESCRIPTION
        "Cisco Firepower sw:SspEthMonSrcAppEp:pcapsize
        managed object property"
    ::= { cfprApSwSspEthMonSrcAppEpEntry 12 }

cfprApSwSspEthMonSrcAppEpPeerDn OBJECT-TYPE
    SYNTAX       SnmpAdminString
    MAX-ACCESS   read-only
    STATUS       current
    DESCRIPTION
        "Cisco Firepower sw:SspEthMonSrcAppEp:peerDn managed
        object property"
    ::= { cfprApSwSspEthMonSrcAppEpEntry 13 }

cfprApSwSspEthMonSrcAppEpPortChannelDn OBJECT-TYPE
    SYNTAX       SnmpAdminString
    MAX-ACCESS   read-only
    STATUS       current
    DESCRIPTION
        "Cisco Firepower sw:SspEthMonSrcAppEp:portChannelDn
        managed object property"
    ::= { cfprApSwSspEthMonSrcAppEpEntry 14 }

cfprApSwSspEthMonSrcAppEpPortName OBJECT-TYPE
    SYNTAX       SnmpAdminString
    MAX-ACCESS   read-only
    STATUS       current
    DESCRIPTION
        "Cisco Firepower sw:SspEthMonSrcAppEp:portName
        managed object property"
    ::= { cfprApSwSspEthMonSrcAppEpEntry 15 }

cfprApSwSspEthMonSrcAppEpSlotId OBJECT-TYPE
    SYNTAX       Gauge32
    MAX-ACCESS   read-only
    STATUS       current
    DESCRIPTION
        "Cisco Firepower sw:SspEthMonSrcAppEp:slotId managed
        object property"
    ::= { cfprApSwSspEthMonSrcAppEpEntry 16 }

cfprApSwSspEthMonSrcAppLinksEpTable OBJECT-TYPE
    SYNTAX           SEQUENCE OF CfprApSwSspEthMonSrcAppLinksEpEntry
    MAX-ACCESS       not-accessible
    STATUS           current
    DESCRIPTION
        "Cisco Firepower sw:SspEthMonSrcAppLinksEp managed object table"
    ::= { cfprApSwObjects 78 }

cfprApSwSspEthMonSrcAppLinksEpEntry OBJECT-TYPE
    SYNTAX           CfprApSwSspEthMonSrcAppLinksEpEntry
    MAX-ACCESS       not-accessible
    STATUS           current
    DESCRIPTION
        "Entry for the cfprApSwSspEthMonSrcAppLinksEpTable table."
    INDEX { cfprApSwSspEthMonSrcAppLinksEpInstanceId }
    ::= { cfprApSwSspEthMonSrcAppLinksEpTable 1 }

CfprApSwSspEthMonSrcAppLinksEpEntry ::= SEQUENCE {
    cfprApSwSspEthMonSrcAppLinksEpInstanceId                         CfprApManagedObjectId,
    cfprApSwSspEthMonSrcAppLinksEpDn                                 CfprApManagedObjectDn,
    cfprApSwSspEthMonSrcAppLinksEpRn                                 SnmpAdminString,
    cfprApSwSspEthMonSrcAppLinksEpChassisId                          Gauge32,
    cfprApSwSspEthMonSrcAppLinksEpEqAggrPortId                       Gauge32,
    cfprApSwSspEthMonSrcAppLinksEpEqPortId                           Gauge32,
    cfprApSwSspEthMonSrcAppLinksEpEqSlotId                           Gauge32,
    cfprApSwSspEthMonSrcAppLinksEpFilter                             SnmpAdminString,
    cfprApSwSspEthMonSrcAppLinksEpFilterDn                           SnmpAdminString,
    cfprApSwSspEthMonSrcAppLinksEpLifeCycle                          CfprApSwPktCaptureLifeCycle,
    cfprApSwSspEthMonSrcAppLinksEpName                               SnmpAdminString,
    cfprApSwSspEthMonSrcAppLinksEpPcapfile                           SnmpAdminString,
    cfprApSwSspEthMonSrcAppLinksEpPcapfilename                       SnmpAdminString,
    cfprApSwSspEthMonSrcAppLinksEpPcapsize                           Gauge32,
    cfprApSwSspEthMonSrcAppLinksEpSwitchId                           CfprApNetworkSwitchId,
    cfprApSwSspEthMonSrcAppLinksEpVlan                               Gauge32,
    cfprApSwSspEthMonSrcAppLinksEpVnicName1                          SnmpAdminString
}

cfprApSwSspEthMonSrcAppLinksEpInstanceId OBJECT-TYPE
    SYNTAX       CfprApManagedObjectId
    MAX-ACCESS   not-accessible
    STATUS       current
    DESCRIPTION
        "Instance identifier of the managed object."
    ::= { cfprApSwSspEthMonSrcAppLinksEpEntry 1 }

cfprApSwSspEthMonSrcAppLinksEpDn OBJECT-TYPE
    SYNTAX       CfprApManagedObjectDn
    MAX-ACCESS   read-only
    STATUS       current
    DESCRIPTION
        "Cisco Firepower sw:SspEthMonSrcAppLinksEp:dn managed
        object property"
    ::= { cfprApSwSspEthMonSrcAppLinksEpEntry 2 }

cfprApSwSspEthMonSrcAppLinksEpRn OBJECT-TYPE
    SYNTAX       SnmpAdminString
    MAX-ACCESS   read-only
    STATUS       current
    DESCRIPTION
        "Cisco Firepower sw:SspEthMonSrcAppLinksEp:rn managed
        object property"
    ::= { cfprApSwSspEthMonSrcAppLinksEpEntry 3 }

cfprApSwSspEthMonSrcAppLinksEpChassisId OBJECT-TYPE
    SYNTAX       Gauge32
    MAX-ACCESS   read-only
    STATUS       current
    DESCRIPTION
        "Cisco Firepower sw:SspEthMonSrcAppLinksEp:chassisId
        managed object property"
    ::= { cfprApSwSspEthMonSrcAppLinksEpEntry 4 }

cfprApSwSspEthMonSrcAppLinksEpEqAggrPortId OBJECT-TYPE
    SYNTAX       Gauge32
    MAX-ACCESS   read-only
    STATUS       current
    DESCRIPTION
        "Cisco Firepower sw:SspEthMonSrcAppLinksEp:eqAggrPortId
        managed object property"
    ::= { cfprApSwSspEthMonSrcAppLinksEpEntry 5 }

cfprApSwSspEthMonSrcAppLinksEpEqPortId OBJECT-TYPE
    SYNTAX       Gauge32
    MAX-ACCESS   read-only
    STATUS       current
    DESCRIPTION
        "Cisco Firepower sw:SspEthMonSrcAppLinksEp:eqPortId
        managed object property"
    ::= { cfprApSwSspEthMonSrcAppLinksEpEntry 6 }

cfprApSwSspEthMonSrcAppLinksEpEqSlotId OBJECT-TYPE
    SYNTAX       Gauge32
    MAX-ACCESS   read-only
    STATUS       current
    DESCRIPTION
        "Cisco Firepower sw:SspEthMonSrcAppLinksEp:eqSlotId
        managed object property"
    ::= { cfprApSwSspEthMonSrcAppLinksEpEntry 7 }

cfprApSwSspEthMonSrcAppLinksEpFilter OBJECT-TYPE
    SYNTAX       SnmpAdminString
    MAX-ACCESS   read-only
    STATUS       current
    DESCRIPTION
        "Cisco Firepower sw:SspEthMonSrcAppLinksEp:filter
        managed object property"
    ::= { cfprApSwSspEthMonSrcAppLinksEpEntry 8 }

cfprApSwSspEthMonSrcAppLinksEpFilterDn OBJECT-TYPE
    SYNTAX       SnmpAdminString
    MAX-ACCESS   read-only
    STATUS       current
    DESCRIPTION
        "Cisco Firepower sw:SspEthMonSrcAppLinksEp:filterDn
        managed object property"
    ::= { cfprApSwSspEthMonSrcAppLinksEpEntry 9 }

cfprApSwSspEthMonSrcAppLinksEpLifeCycle OBJECT-TYPE
    SYNTAX       CfprApSwPktCaptureLifeCycle
    MAX-ACCESS   read-only
    STATUS       current
    DESCRIPTION
        "Cisco Firepower sw:SspEthMonSrcAppLinksEp:lifeCycle
        managed object property"
    ::= { cfprApSwSspEthMonSrcAppLinksEpEntry 10 }

cfprApSwSspEthMonSrcAppLinksEpName OBJECT-TYPE
    SYNTAX       SnmpAdminString
    MAX-ACCESS   read-only
    STATUS       current
    DESCRIPTION
        "Cisco Firepower sw:SspEthMonSrcAppLinksEp:name
        managed object property"
    ::= { cfprApSwSspEthMonSrcAppLinksEpEntry 11 }

cfprApSwSspEthMonSrcAppLinksEpPcapfile OBJECT-TYPE
    SYNTAX       SnmpAdminString
    MAX-ACCESS   read-only
    STATUS       current
    DESCRIPTION
        "Cisco Firepower sw:SspEthMonSrcAppLinksEp:pcapfile
        managed object property"
    ::= { cfprApSwSspEthMonSrcAppLinksEpEntry 12 }

cfprApSwSspEthMonSrcAppLinksEpPcapfilename OBJECT-TYPE
    SYNTAX       SnmpAdminString
    MAX-ACCESS   read-only
    STATUS       current
    DESCRIPTION
        "Cisco Firepower sw:SspEthMonSrcAppLinksEp:pcapfilename
        managed object property"
    ::= { cfprApSwSspEthMonSrcAppLinksEpEntry 13 }

cfprApSwSspEthMonSrcAppLinksEpPcapsize OBJECT-TYPE
    SYNTAX       Gauge32
    MAX-ACCESS   read-only
    STATUS       current
    DESCRIPTION
        "Cisco Firepower sw:SspEthMonSrcAppLinksEp:pcapsize
        managed object property"
    ::= { cfprApSwSspEthMonSrcAppLinksEpEntry 14 }

cfprApSwSspEthMonSrcAppLinksEpSwitchId OBJECT-TYPE
    SYNTAX       CfprApNetworkSwitchId
    MAX-ACCESS   read-only
    STATUS       current
    DESCRIPTION
        "Cisco Firepower sw:SspEthMonSrcAppLinksEp:switchId
        managed object property"
    ::= { cfprApSwSspEthMonSrcAppLinksEpEntry 15 }

cfprApSwSspEthMonSrcAppLinksEpVlan OBJECT-TYPE
    SYNTAX       Gauge32
    MAX-ACCESS   read-only
    STATUS       current
    DESCRIPTION
        "Cisco Firepower sw:SspEthMonSrcAppLinksEp:vlan
        managed object property"
    ::= { cfprApSwSspEthMonSrcAppLinksEpEntry 16 }

cfprApSwSspEthMonSrcAppLinksEpVnicName1 OBJECT-TYPE
    SYNTAX       SnmpAdminString
    MAX-ACCESS   read-only
    STATUS       current
    DESCRIPTION
        "Cisco Firepower sw:SspEthMonSrcAppLinksEp:vnicName1
        managed object property"
    ::= { cfprApSwSspEthMonSrcAppLinksEpEntry 17 }

cfprApSwSspEthMonSrcPhyEpTable OBJECT-TYPE
    SYNTAX           SEQUENCE OF CfprApSwSspEthMonSrcPhyEpEntry
    MAX-ACCESS       not-accessible
    STATUS           current
    DESCRIPTION
        "Cisco Firepower sw:SspEthMonSrcPhyEp managed object table"
    ::= { cfprApSwObjects 79 }

cfprApSwSspEthMonSrcPhyEpEntry OBJECT-TYPE
    SYNTAX           CfprApSwSspEthMonSrcPhyEpEntry
    MAX-ACCESS       not-accessible
    STATUS           current
    DESCRIPTION
        "Entry for the cfprApSwSspEthMonSrcPhyEpTable table."
    INDEX { cfprApSwSspEthMonSrcPhyEpInstanceId }
    ::= { cfprApSwSspEthMonSrcPhyEpTable 1 }

CfprApSwSspEthMonSrcPhyEpEntry ::= SEQUENCE {
    cfprApSwSspEthMonSrcPhyEpInstanceId                              CfprApManagedObjectId,
    cfprApSwSspEthMonSrcPhyEpDn                                      CfprApManagedObjectDn,
    cfprApSwSspEthMonSrcPhyEpRn                                      SnmpAdminString,
    cfprApSwSspEthMonSrcPhyEpAggrPortId                              Gauge32,
    cfprApSwSspEthMonSrcPhyEpChassisId                               Gauge32,
    cfprApSwSspEthMonSrcPhyEpFilter                                  SnmpAdminString,
    cfprApSwSspEthMonSrcPhyEpFilterDn                                SnmpAdminString,
    cfprApSwSspEthMonSrcPhyEpFsmDescr                                SnmpAdminString,
    cfprApSwSspEthMonSrcPhyEpFsmPrev                                 SnmpAdminString,
    cfprApSwSspEthMonSrcPhyEpFsmProgr                                Gauge32,
    cfprApSwSspEthMonSrcPhyEpFsmRmtInvErrCode                        Gauge32,
    cfprApSwSspEthMonSrcPhyEpFsmRmtInvErrDescr                       SnmpAdminString,
    cfprApSwSspEthMonSrcPhyEpFsmRmtInvRslt                           CfprApConditionRemoteInvRslt,
    cfprApSwSspEthMonSrcPhyEpFsmStageDescr                           SnmpAdminString,
    cfprApSwSspEthMonSrcPhyEpFsmStamp                                DateAndTime,
    cfprApSwSspEthMonSrcPhyEpFsmStatus                               SnmpAdminString,
    cfprApSwSspEthMonSrcPhyEpFsmTry                                  Gauge32,
    cfprApSwSspEthMonSrcPhyEpLifeCycle                               CfprApSwPktCaptureLifeCycle,
    cfprApSwSspEthMonSrcPhyEpPcapfile                                SnmpAdminString,
    cfprApSwSspEthMonSrcPhyEpPcapfilename                            SnmpAdminString,
    cfprApSwSspEthMonSrcPhyEpPcapsize                                Gauge32,
    cfprApSwSspEthMonSrcPhyEpPeerDn                                  SnmpAdminString,
    cfprApSwSspEthMonSrcPhyEpPortId                                  Gauge32,
    cfprApSwSspEthMonSrcPhyEpSlotId                                  Gauge32,
    cfprApSwSspEthMonSrcPhyEpSwitchId                                CfprApNetworkSwitchId
}

cfprApSwSspEthMonSrcPhyEpInstanceId OBJECT-TYPE
    SYNTAX       CfprApManagedObjectId
    MAX-ACCESS   not-accessible
    STATUS       current
    DESCRIPTION
        "Instance identifier of the managed object."
    ::= { cfprApSwSspEthMonSrcPhyEpEntry 1 }

cfprApSwSspEthMonSrcPhyEpDn OBJECT-TYPE
    SYNTAX       CfprApManagedObjectDn
    MAX-ACCESS   read-only
    STATUS       current
    DESCRIPTION
        "Cisco Firepower sw:SspEthMonSrcPhyEp:dn managed object property"
    ::= { cfprApSwSspEthMonSrcPhyEpEntry 2 }

cfprApSwSspEthMonSrcPhyEpRn OBJECT-TYPE
    SYNTAX       SnmpAdminString
    MAX-ACCESS   read-only
    STATUS       current
    DESCRIPTION
        "Cisco Firepower sw:SspEthMonSrcPhyEp:rn managed object property"
    ::= { cfprApSwSspEthMonSrcPhyEpEntry 3 }

cfprApSwSspEthMonSrcPhyEpAggrPortId OBJECT-TYPE
    SYNTAX       Gauge32
    MAX-ACCESS   read-only
    STATUS       current
    DESCRIPTION
        "Cisco Firepower sw:SspEthMonSrcPhyEp:aggrPortId
        managed object property"
    ::= { cfprApSwSspEthMonSrcPhyEpEntry 4 }

cfprApSwSspEthMonSrcPhyEpChassisId OBJECT-TYPE
    SYNTAX       Gauge32
    MAX-ACCESS   read-only
    STATUS       current
    DESCRIPTION
        "Cisco Firepower sw:SspEthMonSrcPhyEp:chassisId
        managed object property"
    ::= { cfprApSwSspEthMonSrcPhyEpEntry 5 }

cfprApSwSspEthMonSrcPhyEpFilter OBJECT-TYPE
    SYNTAX       SnmpAdminString
    MAX-ACCESS   read-only
    STATUS       current
    DESCRIPTION
        "Cisco Firepower sw:SspEthMonSrcPhyEp:filter managed
        object property"
    ::= { cfprApSwSspEthMonSrcPhyEpEntry 6 }

cfprApSwSspEthMonSrcPhyEpFilterDn OBJECT-TYPE
    SYNTAX       SnmpAdminString
    MAX-ACCESS   read-only
    STATUS       current
    DESCRIPTION
        "Cisco Firepower sw:SspEthMonSrcPhyEp:filterDn
        managed object property"
    ::= { cfprApSwSspEthMonSrcPhyEpEntry 7 }

cfprApSwSspEthMonSrcPhyEpFsmDescr OBJECT-TYPE
    SYNTAX       SnmpAdminString
    MAX-ACCESS   read-only
    STATUS       current
    DESCRIPTION
        "Cisco Firepower sw:SspEthMonSrcPhyEp:fsmDescr
        managed object property"
    ::= { cfprApSwSspEthMonSrcPhyEpEntry 8 }

cfprApSwSspEthMonSrcPhyEpFsmPrev OBJECT-TYPE
    SYNTAX       SnmpAdminString
    MAX-ACCESS   read-only
    STATUS       current
    DESCRIPTION
        "Cisco Firepower sw:SspEthMonSrcPhyEp:fsmPrev managed
        object property"
    ::= { cfprApSwSspEthMonSrcPhyEpEntry 9 }

cfprApSwSspEthMonSrcPhyEpFsmProgr OBJECT-TYPE
    SYNTAX       Gauge32
    MAX-ACCESS   read-only
    STATUS       current
    DESCRIPTION
        "Cisco Firepower sw:SspEthMonSrcPhyEp:fsmProgr
        managed object property"
    ::= { cfprApSwSspEthMonSrcPhyEpEntry 10 }

cfprApSwSspEthMonSrcPhyEpFsmRmtInvErrCode OBJECT-TYPE
    SYNTAX       Gauge32
    MAX-ACCESS   read-only
    STATUS       current
    DESCRIPTION
        "Cisco Firepower sw:SspEthMonSrcPhyEp:fsmRmtInvErrCode
        managed object property"
    ::= { cfprApSwSspEthMonSrcPhyEpEntry 11 }

cfprApSwSspEthMonSrcPhyEpFsmRmtInvErrDescr OBJECT-TYPE
    SYNTAX       SnmpAdminString
    MAX-ACCESS   read-only
    STATUS       current
    DESCRIPTION
        "Cisco Firepower sw:SspEthMonSrcPhyEp:fsmRmtInvErrDescr
        managed object property"
    ::= { cfprApSwSspEthMonSrcPhyEpEntry 12 }

cfprApSwSspEthMonSrcPhyEpFsmRmtInvRslt OBJECT-TYPE
    SYNTAX       CfprApConditionRemoteInvRslt
    MAX-ACCESS   read-only
    STATUS       current
    DESCRIPTION
        "Cisco Firepower sw:SspEthMonSrcPhyEp:fsmRmtInvRslt
        managed object property"
    ::= { cfprApSwSspEthMonSrcPhyEpEntry 13 }

cfprApSwSspEthMonSrcPhyEpFsmStageDescr OBJECT-TYPE
    SYNTAX       SnmpAdminString
    MAX-ACCESS   read-only
    STATUS       current
    DESCRIPTION
        "Cisco Firepower sw:SspEthMonSrcPhyEp:fsmStageDescr
        managed object property"
    ::= { cfprApSwSspEthMonSrcPhyEpEntry 14 }

cfprApSwSspEthMonSrcPhyEpFsmStamp OBJECT-TYPE
    SYNTAX       DateAndTime
    MAX-ACCESS   read-only
    STATUS       current
    DESCRIPTION
        "Cisco Firepower sw:SspEthMonSrcPhyEp:fsmStamp
        managed object property"
    ::= { cfprApSwSspEthMonSrcPhyEpEntry 15 }

cfprApSwSspEthMonSrcPhyEpFsmStatus OBJECT-TYPE
    SYNTAX       SnmpAdminString
    MAX-ACCESS   read-only
    STATUS       current
    DESCRIPTION
        "Cisco Firepower sw:SspEthMonSrcPhyEp:fsmStatus
        managed object property"
    ::= { cfprApSwSspEthMonSrcPhyEpEntry 16 }

cfprApSwSspEthMonSrcPhyEpFsmTry OBJECT-TYPE
    SYNTAX       Gauge32
    MAX-ACCESS   read-only
    STATUS       current
    DESCRIPTION
        "Cisco Firepower sw:SspEthMonSrcPhyEp:fsmTry managed
        object property"
    ::= { cfprApSwSspEthMonSrcPhyEpEntry 17 }

cfprApSwSspEthMonSrcPhyEpLifeCycle OBJECT-TYPE
    SYNTAX       CfprApSwPktCaptureLifeCycle
    MAX-ACCESS   read-only
    STATUS       current
    DESCRIPTION
        "Cisco Firepower sw:SspEthMonSrcPhyEp:lifeCycle
        managed object property"
    ::= { cfprApSwSspEthMonSrcPhyEpEntry 18 }

cfprApSwSspEthMonSrcPhyEpPcapfile OBJECT-TYPE
    SYNTAX       SnmpAdminString
    MAX-ACCESS   read-only
    STATUS       current
    DESCRIPTION
        "Cisco Firepower sw:SspEthMonSrcPhyEp:pcapfile
        managed object property"
    ::= { cfprApSwSspEthMonSrcPhyEpEntry 19 }

cfprApSwSspEthMonSrcPhyEpPcapfilename OBJECT-TYPE
    SYNTAX       SnmpAdminString
    MAX-ACCESS   read-only
    STATUS       current
    DESCRIPTION
        "Cisco Firepower sw:SspEthMonSrcPhyEp:pcapfilename
        managed object property"
    ::= { cfprApSwSspEthMonSrcPhyEpEntry 20 }

cfprApSwSspEthMonSrcPhyEpPcapsize OBJECT-TYPE
    SYNTAX       Gauge32
    MAX-ACCESS   read-only
    STATUS       current
    DESCRIPTION
        "Cisco Firepower sw:SspEthMonSrcPhyEp:pcapsize
        managed object property"
    ::= { cfprApSwSspEthMonSrcPhyEpEntry 21 }

cfprApSwSspEthMonSrcPhyEpPeerDn OBJECT-TYPE
    SYNTAX       SnmpAdminString
    MAX-ACCESS   read-only
    STATUS       current
    DESCRIPTION
        "Cisco Firepower sw:SspEthMonSrcPhyEp:peerDn managed
        object property"
    ::= { cfprApSwSspEthMonSrcPhyEpEntry 22 }

cfprApSwSspEthMonSrcPhyEpPortId OBJECT-TYPE
    SYNTAX       Gauge32
    MAX-ACCESS   read-only
    STATUS       current
    DESCRIPTION
        "Cisco Firepower sw:SspEthMonSrcPhyEp:portId managed
        object property"
    ::= { cfprApSwSspEthMonSrcPhyEpEntry 23 }

cfprApSwSspEthMonSrcPhyEpSlotId OBJECT-TYPE
    SYNTAX       Gauge32
    MAX-ACCESS   read-only
    STATUS       current
    DESCRIPTION
        "Cisco Firepower sw:SspEthMonSrcPhyEp:slotId managed
        object property"
    ::= { cfprApSwSspEthMonSrcPhyEpEntry 24 }

cfprApSwSspEthMonSrcPhyEpSwitchId OBJECT-TYPE
    SYNTAX       CfprApNetworkSwitchId
    MAX-ACCESS   read-only
    STATUS       current
    DESCRIPTION
        "Cisco Firepower sw:SspEthMonSrcPhyEp:switchId
        managed object property"
    ::= { cfprApSwSspEthMonSrcPhyEpEntry 25 }

cfprApSwSspEthMonSrcPhyEpFsmTable OBJECT-TYPE
    SYNTAX           SEQUENCE OF CfprApSwSspEthMonSrcPhyEpFsmEntry
    MAX-ACCESS       not-accessible
    STATUS           current
    DESCRIPTION
        "Cisco Firepower sw:SspEthMonSrcPhyEpFsm managed object table"
    ::= { cfprApSwObjects 80 }

cfprApSwSspEthMonSrcPhyEpFsmEntry OBJECT-TYPE
    SYNTAX           CfprApSwSspEthMonSrcPhyEpFsmEntry
    MAX-ACCESS       not-accessible
    STATUS           current
    DESCRIPTION
        "Entry for the cfprApSwSspEthMonSrcPhyEpFsmTable table."
    INDEX { cfprApSwSspEthMonSrcPhyEpFsmInstanceId }
    ::= { cfprApSwSspEthMonSrcPhyEpFsmTable 1 }

CfprApSwSspEthMonSrcPhyEpFsmEntry ::= SEQUENCE {
    cfprApSwSspEthMonSrcPhyEpFsmInstanceId                           CfprApManagedObjectId,
    cfprApSwSspEthMonSrcPhyEpFsmDn                                   CfprApManagedObjectDn,
    cfprApSwSspEthMonSrcPhyEpFsmRn                                   SnmpAdminString,
    cfprApSwSspEthMonSrcPhyEpFsmCompletionTime                       DateAndTime,
    cfprApSwSspEthMonSrcPhyEpFsmCurrentFsm                           CfprApSwSspEthMonSrcPhyEpFsmCurrentFsm,
    cfprApSwSspEthMonSrcPhyEpFsmDescrData                            SnmpAdminString,
    cfprApSwSspEthMonSrcPhyEpFsmFsmStatus                            CfprApFsmFsmStageStatus,
    cfprApSwSspEthMonSrcPhyEpFsmProgress                             Gauge32,
    cfprApSwSspEthMonSrcPhyEpFsmRmtErrCode                           Gauge32,
    cfprApSwSspEthMonSrcPhyEpFsmRmtErrDescr                          SnmpAdminString,
    cfprApSwSspEthMonSrcPhyEpFsmRmtRslt                              CfprApConditionRemoteInvRslt
}

cfprApSwSspEthMonSrcPhyEpFsmInstanceId OBJECT-TYPE
    SYNTAX       CfprApManagedObjectId
    MAX-ACCESS   not-accessible
    STATUS       current
    DESCRIPTION
        "Instance identifier of the managed object."
    ::= { cfprApSwSspEthMonSrcPhyEpFsmEntry 1 }

cfprApSwSspEthMonSrcPhyEpFsmDn OBJECT-TYPE
    SYNTAX       CfprApManagedObjectDn
    MAX-ACCESS   read-only
    STATUS       current
    DESCRIPTION
        "Cisco Firepower sw:SspEthMonSrcPhyEpFsm:dn managed
        object property"
    ::= { cfprApSwSspEthMonSrcPhyEpFsmEntry 2 }

cfprApSwSspEthMonSrcPhyEpFsmRn OBJECT-TYPE
    SYNTAX       SnmpAdminString
    MAX-ACCESS   read-only
    STATUS       current
    DESCRIPTION
        "Cisco Firepower sw:SspEthMonSrcPhyEpFsm:rn managed
        object property"
    ::= { cfprApSwSspEthMonSrcPhyEpFsmEntry 3 }

cfprApSwSspEthMonSrcPhyEpFsmCompletionTime OBJECT-TYPE
    SYNTAX       DateAndTime
    MAX-ACCESS   read-only
    STATUS       current
    DESCRIPTION
        "Cisco Firepower sw:SspEthMonSrcPhyEpFsm:completionTime
        managed object property"
    ::= { cfprApSwSspEthMonSrcPhyEpFsmEntry 4 }

cfprApSwSspEthMonSrcPhyEpFsmCurrentFsm OBJECT-TYPE
    SYNTAX       CfprApSwSspEthMonSrcPhyEpFsmCurrentFsm
    MAX-ACCESS   read-only
    STATUS       current
    DESCRIPTION
        "Cisco Firepower sw:SspEthMonSrcPhyEpFsm:currentFsm
        managed object property"
    ::= { cfprApSwSspEthMonSrcPhyEpFsmEntry 5 }

cfprApSwSspEthMonSrcPhyEpFsmDescrData OBJECT-TYPE
    SYNTAX       SnmpAdminString
    MAX-ACCESS   read-only
    STATUS       current
    DESCRIPTION
        "Cisco Firepower sw:SspEthMonSrcPhyEpFsm:descr
        managed object property"
    ::= { cfprApSwSspEthMonSrcPhyEpFsmEntry 6 }

cfprApSwSspEthMonSrcPhyEpFsmFsmStatus OBJECT-TYPE
    SYNTAX       CfprApFsmFsmStageStatus
    MAX-ACCESS   read-only
    STATUS       current
    DESCRIPTION
        "Cisco Firepower sw:SspEthMonSrcPhyEpFsm:fsmStatus
        managed object property"
    ::= { cfprApSwSspEthMonSrcPhyEpFsmEntry 7 }

cfprApSwSspEthMonSrcPhyEpFsmProgress OBJECT-TYPE
    SYNTAX       Gauge32
    MAX-ACCESS   read-only
    STATUS       current
    DESCRIPTION
        "Cisco Firepower sw:SspEthMonSrcPhyEpFsm:progress
        managed object property"
    ::= { cfprApSwSspEthMonSrcPhyEpFsmEntry 8 }

cfprApSwSspEthMonSrcPhyEpFsmRmtErrCode OBJECT-TYPE
    SYNTAX       Gauge32
    MAX-ACCESS   read-only
    STATUS       current
    DESCRIPTION
        "Cisco Firepower sw:SspEthMonSrcPhyEpFsm:rmtErrCode
        managed object property"
    ::= { cfprApSwSspEthMonSrcPhyEpFsmEntry 9 }

cfprApSwSspEthMonSrcPhyEpFsmRmtErrDescr OBJECT-TYPE
    SYNTAX       SnmpAdminString
    MAX-ACCESS   read-only
    STATUS       current
    DESCRIPTION
        "Cisco Firepower sw:SspEthMonSrcPhyEpFsm:rmtErrDescr
        managed object property"
    ::= { cfprApSwSspEthMonSrcPhyEpFsmEntry 10 }

cfprApSwSspEthMonSrcPhyEpFsmRmtRslt OBJECT-TYPE
    SYNTAX       CfprApConditionRemoteInvRslt
    MAX-ACCESS   read-only
    STATUS       current
    DESCRIPTION
        "Cisco Firepower sw:SspEthMonSrcPhyEpFsm:rmtRslt
        managed object property"
    ::= { cfprApSwSspEthMonSrcPhyEpFsmEntry 11 }

cfprApSwSspEthMonSrcPhyEpFsmStageTable OBJECT-TYPE
    SYNTAX           SEQUENCE OF CfprApSwSspEthMonSrcPhyEpFsmStageEntry
    MAX-ACCESS       not-accessible
    STATUS           current
    DESCRIPTION
        "Cisco Firepower sw:SspEthMonSrcPhyEpFsmStage managed
        object table"
    ::= { cfprApSwObjects 81 }

cfprApSwSspEthMonSrcPhyEpFsmStageEntry OBJECT-TYPE
    SYNTAX           CfprApSwSspEthMonSrcPhyEpFsmStageEntry
    MAX-ACCESS       not-accessible
    STATUS           current
    DESCRIPTION
        "Entry for the cfprApSwSspEthMonSrcPhyEpFsmStageTable table."
    INDEX { cfprApSwSspEthMonSrcPhyEpFsmStageInstanceId }
    ::= { cfprApSwSspEthMonSrcPhyEpFsmStageTable 1 }

CfprApSwSspEthMonSrcPhyEpFsmStageEntry ::= SEQUENCE {
    cfprApSwSspEthMonSrcPhyEpFsmStageInstanceId                      CfprApManagedObjectId,
    cfprApSwSspEthMonSrcPhyEpFsmStageDn                              CfprApManagedObjectDn,
    cfprApSwSspEthMonSrcPhyEpFsmStageRn                              SnmpAdminString,
    cfprApSwSspEthMonSrcPhyEpFsmStageDescrData                       SnmpAdminString,
    cfprApSwSspEthMonSrcPhyEpFsmStageLastUpdateTime                  DateAndTime,
    cfprApSwSspEthMonSrcPhyEpFsmStageName                            CfprApSwSspEthMonSrcPhyEpFsmStageName,
    cfprApSwSspEthMonSrcPhyEpFsmStageOrder                           Gauge32,
    cfprApSwSspEthMonSrcPhyEpFsmStageRetry                           Gauge32,
    cfprApSwSspEthMonSrcPhyEpFsmStageStageStatus                     CfprApFsmFsmStageStatus
}

cfprApSwSspEthMonSrcPhyEpFsmStageInstanceId OBJECT-TYPE
    SYNTAX       CfprApManagedObjectId
    MAX-ACCESS   not-accessible
    STATUS       current
    DESCRIPTION
        "Instance identifier of the managed object."
    ::= { cfprApSwSspEthMonSrcPhyEpFsmStageEntry 1 }

cfprApSwSspEthMonSrcPhyEpFsmStageDn OBJECT-TYPE
    SYNTAX       CfprApManagedObjectDn
    MAX-ACCESS   read-only
    STATUS       current
    DESCRIPTION
        "Cisco Firepower sw:SspEthMonSrcPhyEpFsmStage:dn
        managed object property"
    ::= { cfprApSwSspEthMonSrcPhyEpFsmStageEntry 2 }

cfprApSwSspEthMonSrcPhyEpFsmStageRn OBJECT-TYPE
    SYNTAX       SnmpAdminString
    MAX-ACCESS   read-only
    STATUS       current
    DESCRIPTION
        "Cisco Firepower sw:SspEthMonSrcPhyEpFsmStage:rn
        managed object property"
    ::= { cfprApSwSspEthMonSrcPhyEpFsmStageEntry 3 }

cfprApSwSspEthMonSrcPhyEpFsmStageDescrData OBJECT-TYPE
    SYNTAX       SnmpAdminString
    MAX-ACCESS   read-only
    STATUS       current
    DESCRIPTION
        "Cisco Firepower sw:SspEthMonSrcPhyEpFsmStage:descr
        managed object property"
    ::= { cfprApSwSspEthMonSrcPhyEpFsmStageEntry 4 }

cfprApSwSspEthMonSrcPhyEpFsmStageLastUpdateTime OBJECT-TYPE
    SYNTAX       DateAndTime
    MAX-ACCESS   read-only
    STATUS       current
    DESCRIPTION
        "Cisco Firepower sw:SspEthMonSrcPhyEpFsmStage:lastUpdateTime
        managed object property"
    ::= { cfprApSwSspEthMonSrcPhyEpFsmStageEntry 5 }

cfprApSwSspEthMonSrcPhyEpFsmStageName OBJECT-TYPE
    SYNTAX       CfprApSwSspEthMonSrcPhyEpFsmStageName
    MAX-ACCESS   read-only
    STATUS       current
    DESCRIPTION
        "Cisco Firepower sw:SspEthMonSrcPhyEpFsmStage:name
        managed object property"
    ::= { cfprApSwSspEthMonSrcPhyEpFsmStageEntry 6 }

cfprApSwSspEthMonSrcPhyEpFsmStageOrder OBJECT-TYPE
    SYNTAX       Gauge32
    MAX-ACCESS   read-only
    STATUS       current
    DESCRIPTION
        "Cisco Firepower sw:SspEthMonSrcPhyEpFsmStage:order
        managed object property"
    ::= { cfprApSwSspEthMonSrcPhyEpFsmStageEntry 7 }

cfprApSwSspEthMonSrcPhyEpFsmStageRetry OBJECT-TYPE
    SYNTAX       Gauge32
    MAX-ACCESS   read-only
    STATUS       current
    DESCRIPTION
        "Cisco Firepower sw:SspEthMonSrcPhyEpFsmStage:retry
        managed object property"
    ::= { cfprApSwSspEthMonSrcPhyEpFsmStageEntry 8 }

cfprApSwSspEthMonSrcPhyEpFsmStageStageStatus OBJECT-TYPE
    SYNTAX       CfprApFsmFsmStageStatus
    MAX-ACCESS   read-only
    STATUS       current
    DESCRIPTION
        "Cisco Firepower sw:SspEthMonSrcPhyEpFsmStage:stageStatus
        managed object property"
    ::= { cfprApSwSspEthMonSrcPhyEpFsmStageEntry 9 }

cfprApSwSspEthMonSrcPhyEpFsmTaskTable OBJECT-TYPE
    SYNTAX           SEQUENCE OF CfprApSwSspEthMonSrcPhyEpFsmTaskEntry
    MAX-ACCESS       not-accessible
    STATUS           current
    DESCRIPTION
        "Cisco Firepower sw:SspEthMonSrcPhyEpFsmTask managed object table"
    ::= { cfprApSwObjects 82 }

cfprApSwSspEthMonSrcPhyEpFsmTaskEntry OBJECT-TYPE
    SYNTAX           CfprApSwSspEthMonSrcPhyEpFsmTaskEntry
    MAX-ACCESS       not-accessible
    STATUS           current
    DESCRIPTION
        "Entry for the cfprApSwSspEthMonSrcPhyEpFsmTaskTable table."
    INDEX { cfprApSwSspEthMonSrcPhyEpFsmTaskInstanceId }
    ::= { cfprApSwSspEthMonSrcPhyEpFsmTaskTable 1 }

CfprApSwSspEthMonSrcPhyEpFsmTaskEntry ::= SEQUENCE {
    cfprApSwSspEthMonSrcPhyEpFsmTaskInstanceId                       CfprApManagedObjectId,
    cfprApSwSspEthMonSrcPhyEpFsmTaskDn                               CfprApManagedObjectDn,
    cfprApSwSspEthMonSrcPhyEpFsmTaskRn                               SnmpAdminString,
    cfprApSwSspEthMonSrcPhyEpFsmTaskCompletion                       CfprApFsmCompletion,
    cfprApSwSspEthMonSrcPhyEpFsmTaskFlags                            CfprApFsmFlags,
    cfprApSwSspEthMonSrcPhyEpFsmTaskItem                             CfprApSwSspEthMonSrcPhyEpFsmTaskItem,
    cfprApSwSspEthMonSrcPhyEpFsmTaskSeqId                            Gauge32
}

cfprApSwSspEthMonSrcPhyEpFsmTaskInstanceId OBJECT-TYPE
    SYNTAX       CfprApManagedObjectId
    MAX-ACCESS   not-accessible
    STATUS       current
    DESCRIPTION
        "Instance identifier of the managed object."
    ::= { cfprApSwSspEthMonSrcPhyEpFsmTaskEntry 1 }

cfprApSwSspEthMonSrcPhyEpFsmTaskDn OBJECT-TYPE
    SYNTAX       CfprApManagedObjectDn
    MAX-ACCESS   read-only
    STATUS       current
    DESCRIPTION
        "Cisco Firepower sw:SspEthMonSrcPhyEpFsmTask:dn
        managed object property"
    ::= { cfprApSwSspEthMonSrcPhyEpFsmTaskEntry 2 }

cfprApSwSspEthMonSrcPhyEpFsmTaskRn OBJECT-TYPE
    SYNTAX       SnmpAdminString
    MAX-ACCESS   read-only
    STATUS       current
    DESCRIPTION
        "Cisco Firepower sw:SspEthMonSrcPhyEpFsmTask:rn
        managed object property"
    ::= { cfprApSwSspEthMonSrcPhyEpFsmTaskEntry 3 }

cfprApSwSspEthMonSrcPhyEpFsmTaskCompletion OBJECT-TYPE
    SYNTAX       CfprApFsmCompletion
    MAX-ACCESS   read-only
    STATUS       current
    DESCRIPTION
        "Cisco Firepower sw:SspEthMonSrcPhyEpFsmTask:completion
        managed object property"
    ::= { cfprApSwSspEthMonSrcPhyEpFsmTaskEntry 4 }

cfprApSwSspEthMonSrcPhyEpFsmTaskFlags OBJECT-TYPE
    SYNTAX       CfprApFsmFlags
    MAX-ACCESS   read-only
    STATUS       current
    DESCRIPTION
        "Cisco Firepower sw:SspEthMonSrcPhyEpFsmTask:flags
        managed object property"
    ::= { cfprApSwSspEthMonSrcPhyEpFsmTaskEntry 5 }

cfprApSwSspEthMonSrcPhyEpFsmTaskItem OBJECT-TYPE
    SYNTAX       CfprApSwSspEthMonSrcPhyEpFsmTaskItem
    MAX-ACCESS   read-only
    STATUS       current
    DESCRIPTION
        "Cisco Firepower sw:SspEthMonSrcPhyEpFsmTask:item
        managed object property"
    ::= { cfprApSwSspEthMonSrcPhyEpFsmTaskEntry 6 }

cfprApSwSspEthMonSrcPhyEpFsmTaskSeqId OBJECT-TYPE
    SYNTAX       Gauge32
    MAX-ACCESS   read-only
    STATUS       current
    DESCRIPTION
        "Cisco Firepower sw:SspEthMonSrcPhyEpFsmTask:seqId
        managed object property"
    ::= { cfprApSwSspEthMonSrcPhyEpFsmTaskEntry 7 }

cfprApSwSubGroupTable OBJECT-TYPE
    SYNTAX           SEQUENCE OF CfprApSwSubGroupEntry
    MAX-ACCESS       not-accessible
    STATUS           current
    DESCRIPTION
        "Cisco Firepower sw:SubGroup managed object table"
    ::= { cfprApSwObjects 83 }

cfprApSwSubGroupEntry OBJECT-TYPE
    SYNTAX           CfprApSwSubGroupEntry
    MAX-ACCESS       not-accessible
    STATUS           current
    DESCRIPTION
        "Entry for the cfprApSwSubGroupTable table."
    INDEX { cfprApSwSubGroupInstanceId }
    ::= { cfprApSwSubGroupTable 1 }

CfprApSwSubGroupEntry ::= SEQUENCE {
    cfprApSwSubGroupInstanceId                                       CfprApManagedObjectId,
    cfprApSwSubGroupDn                                               CfprApManagedObjectDn,
    cfprApSwSubGroupRn                                               SnmpAdminString,
    cfprApSwSubGroupAggrPortId                                       CfprApSwSubGroupAggrPortId,
    cfprApSwSubGroupLicGP                                            Unsigned64,
    cfprApSwSubGroupLicState                                         CfprApLicenseState,
    cfprApSwSubGroupLocale                                           CfprApNetworkLocale,
    cfprApSwSubGroupName                                             SnmpAdminString,
    cfprApSwSubGroupSlotId                                           CfprApSwSubGroupSlotId,
    cfprApSwSubGroupSwitchId                                         CfprApNetworkSwitchId,
    cfprApSwSubGroupTransport                                        CfprApNetworkTransport,
    cfprApSwSubGroupType                                             CfprApNetworkConnectionType
}

cfprApSwSubGroupInstanceId OBJECT-TYPE
    SYNTAX       CfprApManagedObjectId
    MAX-ACCESS   not-accessible
    STATUS       current
    DESCRIPTION
        "Instance identifier of the managed object."
    ::= { cfprApSwSubGroupEntry 1 }

cfprApSwSubGroupDn OBJECT-TYPE
    SYNTAX       CfprApManagedObjectDn
    MAX-ACCESS   read-only
    STATUS       current
    DESCRIPTION
        "Cisco Firepower sw:SubGroup:dn managed object property"
    ::= { cfprApSwSubGroupEntry 2 }

cfprApSwSubGroupRn OBJECT-TYPE
    SYNTAX       SnmpAdminString
    MAX-ACCESS   read-only
    STATUS       current
    DESCRIPTION
        "Cisco Firepower sw:SubGroup:rn managed object property"
    ::= { cfprApSwSubGroupEntry 3 }

cfprApSwSubGroupAggrPortId OBJECT-TYPE
    SYNTAX       CfprApSwSubGroupAggrPortId
    MAX-ACCESS   read-only
    STATUS       current
    DESCRIPTION
        "Cisco Firepower sw:SubGroup:aggrPortId managed object property"
    ::= { cfprApSwSubGroupEntry 4 }

cfprApSwSubGroupLicGP OBJECT-TYPE
    SYNTAX       Unsigned64
    MAX-ACCESS   read-only
    STATUS       current
    DESCRIPTION
        "Cisco Firepower sw:SubGroup:licGP managed object property"
    ::= { cfprApSwSubGroupEntry 5 }

cfprApSwSubGroupLicState OBJECT-TYPE
    SYNTAX       CfprApLicenseState
    MAX-ACCESS   read-only
    STATUS       current
    DESCRIPTION
        "Cisco Firepower sw:SubGroup:licState managed object property"
    ::= { cfprApSwSubGroupEntry 6 }

cfprApSwSubGroupLocale OBJECT-TYPE
    SYNTAX       CfprApNetworkLocale
    MAX-ACCESS   read-only
    STATUS       current
    DESCRIPTION
        "Cisco Firepower sw:SubGroup:locale managed object property"
    ::= { cfprApSwSubGroupEntry 7 }

cfprApSwSubGroupName OBJECT-TYPE
    SYNTAX       SnmpAdminString
    MAX-ACCESS   read-only
    STATUS       current
    DESCRIPTION
        "Cisco Firepower sw:SubGroup:name managed object property"
    ::= { cfprApSwSubGroupEntry 8 }

cfprApSwSubGroupSlotId OBJECT-TYPE
    SYNTAX       CfprApSwSubGroupSlotId
    MAX-ACCESS   read-only
    STATUS       current
    DESCRIPTION
        "Cisco Firepower sw:SubGroup:slotId managed object property"
    ::= { cfprApSwSubGroupEntry 9 }

cfprApSwSubGroupSwitchId OBJECT-TYPE
    SYNTAX       CfprApNetworkSwitchId
    MAX-ACCESS   read-only
    STATUS       current
    DESCRIPTION
        "Cisco Firepower sw:SubGroup:switchId managed object property"
    ::= { cfprApSwSubGroupEntry 10 }

cfprApSwSubGroupTransport OBJECT-TYPE
    SYNTAX       CfprApNetworkTransport
    MAX-ACCESS   read-only
    STATUS       current
    DESCRIPTION
        "Cisco Firepower sw:SubGroup:transport managed object property"
    ::= { cfprApSwSubGroupEntry 11 }

cfprApSwSubGroupType OBJECT-TYPE
    SYNTAX       CfprApNetworkConnectionType
    MAX-ACCESS   read-only
    STATUS       current
    DESCRIPTION
        "Cisco Firepower sw:SubGroup:type managed object property"
    ::= { cfprApSwSubGroupEntry 12 }

cfprApSwSystemStatsTable OBJECT-TYPE
    SYNTAX           SEQUENCE OF CfprApSwSystemStatsEntry
    MAX-ACCESS       not-accessible
    STATUS           current
    DESCRIPTION
        "Cisco Firepower sw:SystemStats managed object table"
    ::= { cfprApSwObjects 84 }

cfprApSwSystemStatsEntry OBJECT-TYPE
    SYNTAX           CfprApSwSystemStatsEntry
    MAX-ACCESS       not-accessible
    STATUS           current
    DESCRIPTION
        "Entry for the cfprApSwSystemStatsTable table."
    INDEX { cfprApSwSystemStatsInstanceId }
    ::= { cfprApSwSystemStatsTable 1 }

CfprApSwSystemStatsEntry ::= SEQUENCE {
    cfprApSwSystemStatsInstanceId                                    CfprApManagedObjectId,
    cfprApSwSystemStatsDn                                            CfprApManagedObjectDn,
    cfprApSwSystemStatsRn                                            SnmpAdminString,
    cfprApSwSystemStatsIntervals                                     Gauge32,
    cfprApSwSystemStatsLoad                                          INTEGER,
    cfprApSwSystemStatsLoadAvg                                       INTEGER,
    cfprApSwSystemStatsLoadMax                                       INTEGER,
    cfprApSwSystemStatsLoadMin                                       INTEGER,
    cfprApSwSystemStatsMemAvailable                                  Gauge32,
    cfprApSwSystemStatsMemAvailableAvg                               Gauge32,
    cfprApSwSystemStatsMemAvailableMax                               Gauge32,
    cfprApSwSystemStatsMemAvailableMin                               Gauge32,
    cfprApSwSystemStatsMemCached                                     Gauge32,
    cfprApSwSystemStatsMemCachedAvg                                  Gauge32,
    cfprApSwSystemStatsMemCachedMax                                  Gauge32,
    cfprApSwSystemStatsMemCachedMin                                  Gauge32,
    cfprApSwSystemStatsSuspect                                       TruthValue,
    cfprApSwSystemStatsThresholded                                   CfprApSwSystemStatsThresholded,
    cfprApSwSystemStatsTimeCollected                                 DateAndTime,
    cfprApSwSystemStatsUpdate                                        Gauge32
}

cfprApSwSystemStatsInstanceId OBJECT-TYPE
    SYNTAX       CfprApManagedObjectId
    MAX-ACCESS   not-accessible
    STATUS       current
    DESCRIPTION
        "Instance identifier of the managed object."
    ::= { cfprApSwSystemStatsEntry 1 }

cfprApSwSystemStatsDn OBJECT-TYPE
    SYNTAX       CfprApManagedObjectDn
    MAX-ACCESS   read-only
    STATUS       current
    DESCRIPTION
        "Cisco Firepower sw:SystemStats:dn managed object property"
    ::= { cfprApSwSystemStatsEntry 2 }

cfprApSwSystemStatsRn OBJECT-TYPE
    SYNTAX       SnmpAdminString
    MAX-ACCESS   read-only
    STATUS       current
    DESCRIPTION
        "Cisco Firepower sw:SystemStats:rn managed object property"
    ::= { cfprApSwSystemStatsEntry 3 }

cfprApSwSystemStatsIntervals OBJECT-TYPE
    SYNTAX       Gauge32
    MAX-ACCESS   read-only
    STATUS       current
    DESCRIPTION
        "Cisco Firepower sw:SystemStats:intervals managed object property"
    ::= { cfprApSwSystemStatsEntry 4 }

cfprApSwSystemStatsLoad OBJECT-TYPE
    SYNTAX       INTEGER
    MAX-ACCESS   read-only
    STATUS       current
    DESCRIPTION
        "Cisco Firepower sw:SystemStats:load managed object property"
    ::= { cfprApSwSystemStatsEntry 5 }

cfprApSwSystemStatsLoadAvg OBJECT-TYPE
    SYNTAX       INTEGER
    MAX-ACCESS   read-only
    STATUS       current
    DESCRIPTION
        "Cisco Firepower sw:SystemStats:loadAvg managed object property"
    ::= { cfprApSwSystemStatsEntry 6 }

cfprApSwSystemStatsLoadMax OBJECT-TYPE
    SYNTAX       INTEGER
    MAX-ACCESS   read-only
    STATUS       current
    DESCRIPTION
        "Cisco Firepower sw:SystemStats:loadMax managed object property"
    ::= { cfprApSwSystemStatsEntry 7 }

cfprApSwSystemStatsLoadMin OBJECT-TYPE
    SYNTAX       INTEGER
    MAX-ACCESS   read-only
    STATUS       current
    DESCRIPTION
        "Cisco Firepower sw:SystemStats:loadMin managed object property"
    ::= { cfprApSwSystemStatsEntry 8 }

cfprApSwSystemStatsMemAvailable OBJECT-TYPE
    SYNTAX       Gauge32
    MAX-ACCESS   read-only
    STATUS       current
    DESCRIPTION
        "Cisco Firepower sw:SystemStats:memAvailable managed
        object property"
    ::= { cfprApSwSystemStatsEntry 9 }

cfprApSwSystemStatsMemAvailableAvg OBJECT-TYPE
    SYNTAX       Gauge32
    MAX-ACCESS   read-only
    STATUS       current
    DESCRIPTION
        "Cisco Firepower sw:SystemStats:memAvailableAvg
        managed object property"
    ::= { cfprApSwSystemStatsEntry 10 }

cfprApSwSystemStatsMemAvailableMax OBJECT-TYPE
    SYNTAX       Gauge32
    MAX-ACCESS   read-only
    STATUS       current
    DESCRIPTION
        "Cisco Firepower sw:SystemStats:memAvailableMax
        managed object property"
    ::= { cfprApSwSystemStatsEntry 11 }

cfprApSwSystemStatsMemAvailableMin OBJECT-TYPE
    SYNTAX       Gauge32
    MAX-ACCESS   read-only
    STATUS       current
    DESCRIPTION
        "Cisco Firepower sw:SystemStats:memAvailableMin
        managed object property"
    ::= { cfprApSwSystemStatsEntry 12 }

cfprApSwSystemStatsMemCached OBJECT-TYPE
    SYNTAX       Gauge32
    MAX-ACCESS   read-only
    STATUS       current
    DESCRIPTION
        "Cisco Firepower sw:SystemStats:memCached managed object property"
    ::= { cfprApSwSystemStatsEntry 13 }

cfprApSwSystemStatsMemCachedAvg OBJECT-TYPE
    SYNTAX       Gauge32
    MAX-ACCESS   read-only
    STATUS       current
    DESCRIPTION
        "Cisco Firepower sw:SystemStats:memCachedAvg managed
        object property"
    ::= { cfprApSwSystemStatsEntry 14 }

cfprApSwSystemStatsMemCachedMax OBJECT-TYPE
    SYNTAX       Gauge32
    MAX-ACCESS   read-only
    STATUS       current
    DESCRIPTION
        "Cisco Firepower sw:SystemStats:memCachedMax managed
        object property"
    ::= { cfprApSwSystemStatsEntry 15 }

cfprApSwSystemStatsMemCachedMin OBJECT-TYPE
    SYNTAX       Gauge32
    MAX-ACCESS   read-only
    STATUS       current
    DESCRIPTION
        "Cisco Firepower sw:SystemStats:memCachedMin managed
        object property"
    ::= { cfprApSwSystemStatsEntry 16 }

cfprApSwSystemStatsSuspect OBJECT-TYPE
    SYNTAX       TruthValue
    MAX-ACCESS   read-only
    STATUS       current
    DESCRIPTION
        "Cisco Firepower sw:SystemStats:suspect managed object property"
    ::= { cfprApSwSystemStatsEntry 17 }

cfprApSwSystemStatsThresholded OBJECT-TYPE
    SYNTAX       CfprApSwSystemStatsThresholded
    MAX-ACCESS   read-only
    STATUS       current
    DESCRIPTION
        "Cisco Firepower sw:SystemStats:thresholded managed
        object property"
    ::= { cfprApSwSystemStatsEntry 18 }

cfprApSwSystemStatsTimeCollected OBJECT-TYPE
    SYNTAX       DateAndTime
    MAX-ACCESS   read-only
    STATUS       current
    DESCRIPTION
        "Cisco Firepower sw:SystemStats:timeCollected managed
        object property"
    ::= { cfprApSwSystemStatsEntry 19 }

cfprApSwSystemStatsUpdate OBJECT-TYPE
    SYNTAX       Gauge32
    MAX-ACCESS   read-only
    STATUS       current
    DESCRIPTION
        "Cisco Firepower sw:SystemStats:update managed object property"
    ::= { cfprApSwSystemStatsEntry 20 }

cfprApSwSystemStatsHistTable OBJECT-TYPE
    SYNTAX           SEQUENCE OF CfprApSwSystemStatsHistEntry
    MAX-ACCESS       not-accessible
    STATUS           current
    DESCRIPTION
        "Cisco Firepower sw:SystemStatsHist managed object table"
    ::= { cfprApSwObjects 85 }

cfprApSwSystemStatsHistEntry OBJECT-TYPE
    SYNTAX           CfprApSwSystemStatsHistEntry
    MAX-ACCESS       not-accessible
    STATUS           current
    DESCRIPTION
        "Entry for the cfprApSwSystemStatsHistTable table."
    INDEX { cfprApSwSystemStatsHistInstanceId }
    ::= { cfprApSwSystemStatsHistTable 1 }

CfprApSwSystemStatsHistEntry ::= SEQUENCE {
    cfprApSwSystemStatsHistInstanceId                                CfprApManagedObjectId,
    cfprApSwSystemStatsHistDn                                        CfprApManagedObjectDn,
    cfprApSwSystemStatsHistRn                                        SnmpAdminString,
    cfprApSwSystemStatsHistId                                        Unsigned64,
    cfprApSwSystemStatsHistLoad                                      INTEGER,
    cfprApSwSystemStatsHistLoadAvg                                   INTEGER,
    cfprApSwSystemStatsHistLoadMax                                   INTEGER,
    cfprApSwSystemStatsHistLoadMin                                   INTEGER,
    cfprApSwSystemStatsHistMemAvailable                              Gauge32,
    cfprApSwSystemStatsHistMemAvailableAvg                           Gauge32,
    cfprApSwSystemStatsHistMemAvailableMax                           Gauge32,
    cfprApSwSystemStatsHistMemAvailableMin                           Gauge32,
    cfprApSwSystemStatsHistMemCached                                 Gauge32,
    cfprApSwSystemStatsHistMemCachedAvg                              Gauge32,
    cfprApSwSystemStatsHistMemCachedMax                              Gauge32,
    cfprApSwSystemStatsHistMemCachedMin                              Gauge32,
    cfprApSwSystemStatsHistMostRecent                                TruthValue,
    cfprApSwSystemStatsHistSuspect                                   TruthValue,
    cfprApSwSystemStatsHistThresholded                               CfprApSwSystemStatsHistThresholded,
    cfprApSwSystemStatsHistTimeCollected                             DateAndTime
}

cfprApSwSystemStatsHistInstanceId OBJECT-TYPE
    SYNTAX       CfprApManagedObjectId
    MAX-ACCESS   not-accessible
    STATUS       current
    DESCRIPTION
        "Instance identifier of the managed object."
    ::= { cfprApSwSystemStatsHistEntry 1 }

cfprApSwSystemStatsHistDn OBJECT-TYPE
    SYNTAX       CfprApManagedObjectDn
    MAX-ACCESS   read-only
    STATUS       current
    DESCRIPTION
        "Cisco Firepower sw:SystemStatsHist:dn managed object property"
    ::= { cfprApSwSystemStatsHistEntry 2 }

cfprApSwSystemStatsHistRn OBJECT-TYPE
    SYNTAX       SnmpAdminString
    MAX-ACCESS   read-only
    STATUS       current
    DESCRIPTION
        "Cisco Firepower sw:SystemStatsHist:rn managed object property"
    ::= { cfprApSwSystemStatsHistEntry 3 }

cfprApSwSystemStatsHistId OBJECT-TYPE
    SYNTAX       Unsigned64
    MAX-ACCESS   read-only
    STATUS       current
    DESCRIPTION
        "Cisco Firepower sw:SystemStatsHist:id managed object property"
    ::= { cfprApSwSystemStatsHistEntry 4 }

cfprApSwSystemStatsHistLoad OBJECT-TYPE
    SYNTAX       INTEGER
    MAX-ACCESS   read-only
    STATUS       current
    DESCRIPTION
        "Cisco Firepower sw:SystemStatsHist:load managed object property"
    ::= { cfprApSwSystemStatsHistEntry 5 }

cfprApSwSystemStatsHistLoadAvg OBJECT-TYPE
    SYNTAX       INTEGER
    MAX-ACCESS   read-only
    STATUS       current
    DESCRIPTION
        "Cisco Firepower sw:SystemStatsHist:loadAvg managed
        object property"
    ::= { cfprApSwSystemStatsHistEntry 6 }

cfprApSwSystemStatsHistLoadMax OBJECT-TYPE
    SYNTAX       INTEGER
    MAX-ACCESS   read-only
    STATUS       current
    DESCRIPTION
        "Cisco Firepower sw:SystemStatsHist:loadMax managed
        object property"
    ::= { cfprApSwSystemStatsHistEntry 7 }

cfprApSwSystemStatsHistLoadMin OBJECT-TYPE
    SYNTAX       INTEGER
    MAX-ACCESS   read-only
    STATUS       current
    DESCRIPTION
        "Cisco Firepower sw:SystemStatsHist:loadMin managed
        object property"
    ::= { cfprApSwSystemStatsHistEntry 8 }

cfprApSwSystemStatsHistMemAvailable OBJECT-TYPE
    SYNTAX       Gauge32
    MAX-ACCESS   read-only
    STATUS       current
    DESCRIPTION
        "Cisco Firepower sw:SystemStatsHist:memAvailable
        managed object property"
    ::= { cfprApSwSystemStatsHistEntry 9 }

cfprApSwSystemStatsHistMemAvailableAvg OBJECT-TYPE
    SYNTAX       Gauge32
    MAX-ACCESS   read-only
    STATUS       current
    DESCRIPTION
        "Cisco Firepower sw:SystemStatsHist:memAvailableAvg
        managed object property"
    ::= { cfprApSwSystemStatsHistEntry 10 }

cfprApSwSystemStatsHistMemAvailableMax OBJECT-TYPE
    SYNTAX       Gauge32
    MAX-ACCESS   read-only
    STATUS       current
    DESCRIPTION
        "Cisco Firepower sw:SystemStatsHist:memAvailableMax
        managed object property"
    ::= { cfprApSwSystemStatsHistEntry 11 }

cfprApSwSystemStatsHistMemAvailableMin OBJECT-TYPE
    SYNTAX       Gauge32
    MAX-ACCESS   read-only
    STATUS       current
    DESCRIPTION
        "Cisco Firepower sw:SystemStatsHist:memAvailableMin
        managed object property"
    ::= { cfprApSwSystemStatsHistEntry 12 }

cfprApSwSystemStatsHistMemCached OBJECT-TYPE
    SYNTAX       Gauge32
    MAX-ACCESS   read-only
    STATUS       current
    DESCRIPTION
        "Cisco Firepower sw:SystemStatsHist:memCached managed
        object property"
    ::= { cfprApSwSystemStatsHistEntry 13 }

cfprApSwSystemStatsHistMemCachedAvg OBJECT-TYPE
    SYNTAX       Gauge32
    MAX-ACCESS   read-only
    STATUS       current
    DESCRIPTION
        "Cisco Firepower sw:SystemStatsHist:memCachedAvg
        managed object property"
    ::= { cfprApSwSystemStatsHistEntry 14 }

cfprApSwSystemStatsHistMemCachedMax OBJECT-TYPE
    SYNTAX       Gauge32
    MAX-ACCESS   read-only
    STATUS       current
    DESCRIPTION
        "Cisco Firepower sw:SystemStatsHist:memCachedMax
        managed object property"
    ::= { cfprApSwSystemStatsHistEntry 15 }

cfprApSwSystemStatsHistMemCachedMin OBJECT-TYPE
    SYNTAX       Gauge32
    MAX-ACCESS   read-only
    STATUS       current
    DESCRIPTION
        "Cisco Firepower sw:SystemStatsHist:memCachedMin
        managed object property"
    ::= { cfprApSwSystemStatsHistEntry 16 }

cfprApSwSystemStatsHistMostRecent OBJECT-TYPE
    SYNTAX       TruthValue
    MAX-ACCESS   read-only
    STATUS       current
    DESCRIPTION
        "Cisco Firepower sw:SystemStatsHist:mostRecent
        managed object property"
    ::= { cfprApSwSystemStatsHistEntry 17 }

cfprApSwSystemStatsHistSuspect OBJECT-TYPE
    SYNTAX       TruthValue
    MAX-ACCESS   read-only
    STATUS       current
    DESCRIPTION
        "Cisco Firepower sw:SystemStatsHist:suspect managed
        object property"
    ::= { cfprApSwSystemStatsHistEntry 18 }

cfprApSwSystemStatsHistThresholded OBJECT-TYPE
    SYNTAX       CfprApSwSystemStatsHistThresholded
    MAX-ACCESS   read-only
    STATUS       current
    DESCRIPTION
        "Cisco Firepower sw:SystemStatsHist:thresholded
        managed object property"
    ::= { cfprApSwSystemStatsHistEntry 19 }

cfprApSwSystemStatsHistTimeCollected OBJECT-TYPE
    SYNTAX       DateAndTime
    MAX-ACCESS   read-only
    STATUS       current
    DESCRIPTION
        "Cisco Firepower sw:SystemStatsHist:timeCollected
        managed object property"
    ::= { cfprApSwSystemStatsHistEntry 20 }

cfprApSwUlanTable OBJECT-TYPE
    SYNTAX           SEQUENCE OF CfprApSwUlanEntry
    MAX-ACCESS       not-accessible
    STATUS           current
    DESCRIPTION
        "Cisco Firepower sw:Ulan managed object table"
    ::= { cfprApSwObjects 86 }

cfprApSwUlanEntry OBJECT-TYPE
    SYNTAX           CfprApSwUlanEntry
    MAX-ACCESS       not-accessible
    STATUS           current
    DESCRIPTION
        "Entry for the cfprApSwUlanTable table."
    INDEX { cfprApSwUlanInstanceId }
    ::= { cfprApSwUlanTable 1 }

CfprApSwUlanEntry ::= SEQUENCE {
    cfprApSwUlanInstanceId                                           CfprApManagedObjectId,
    cfprApSwUlanDn                                                   CfprApManagedObjectDn,
    cfprApSwUlanRn                                                   SnmpAdminString,
    cfprApSwUlanAssocPrimaryVlanState                                CfprApFabricVlanAssocPrimaryVlanState,
    cfprApSwUlanAssocPrimaryVlanSwitchId                             CfprApFabricAVlanAssocPrimaryVlanSwitchId,
    cfprApSwUlanEpDn                                                 SnmpAdminString,
    cfprApSwUlanId                                                   Gauge32,
    cfprApSwUlanIfRole                                               CfprApFabricVnetEpIfRole,
    cfprApSwUlanIfType                                               CfprApNetworkVnetEpIfType,
    cfprApSwUlanLocale                                               CfprApFabricVnetEpLocale,
    cfprApSwUlanName                                                 SnmpAdminString,
    cfprApSwUlanOperState                                            CfprApFabricVlanOperState,
    cfprApSwUlanOverlapStateForA                                     CfprApFabricVlanOverlapState,
    cfprApSwUlanOverlapStateForB                                     CfprApFabricVlanOverlapState,
    cfprApSwUlanPeerDn                                               SnmpAdminString,
    cfprApSwUlanPolicyOwner                                          CfprApFabricVnetEpPolicyOwner,
    cfprApSwUlanPubNwDn                                              SnmpAdminString,
    cfprApSwUlanPubNwId                                              Gauge32,
    cfprApSwUlanPubNwName                                            SnmpAdminString,
    cfprApSwUlanPurpose                                              CfprApSwUlanPurpose,
    cfprApSwUlanSharing                                              CfprApFabricAVlanSharing,
    cfprApSwUlanSwitchId                                             CfprApNetworkSwitchId,
    cfprApSwUlanTransport                                            CfprApFabricAVlanTransport,
    cfprApSwUlanType                                                 CfprApFabricAVlanType,
    cfprApSwUlanVlanType                                             CfprApFabricEpVlanVlanType
}

cfprApSwUlanInstanceId OBJECT-TYPE
    SYNTAX       CfprApManagedObjectId
    MAX-ACCESS   not-accessible
    STATUS       current
    DESCRIPTION
        "Instance identifier of the managed object."
    ::= { cfprApSwUlanEntry 1 }

cfprApSwUlanDn OBJECT-TYPE
    SYNTAX       CfprApManagedObjectDn
    MAX-ACCESS   read-only
    STATUS       current
    DESCRIPTION
        "Cisco Firepower sw:Ulan:dn managed object property"
    ::= { cfprApSwUlanEntry 2 }

cfprApSwUlanRn OBJECT-TYPE
    SYNTAX       SnmpAdminString
    MAX-ACCESS   read-only
    STATUS       current
    DESCRIPTION
        "Cisco Firepower sw:Ulan:rn managed object property"
    ::= { cfprApSwUlanEntry 3 }

cfprApSwUlanAssocPrimaryVlanState OBJECT-TYPE
    SYNTAX       CfprApFabricVlanAssocPrimaryVlanState
    MAX-ACCESS   read-only
    STATUS       current
    DESCRIPTION
        "Cisco Firepower sw:Ulan:assocPrimaryVlanState
        managed object property"
    ::= { cfprApSwUlanEntry 4 }

cfprApSwUlanAssocPrimaryVlanSwitchId OBJECT-TYPE
    SYNTAX       CfprApFabricAVlanAssocPrimaryVlanSwitchId
    MAX-ACCESS   read-only
    STATUS       current
    DESCRIPTION
        "Cisco Firepower sw:Ulan:assocPrimaryVlanSwitchId
        managed object property"
    ::= { cfprApSwUlanEntry 5 }

cfprApSwUlanEpDn OBJECT-TYPE
    SYNTAX       SnmpAdminString
    MAX-ACCESS   read-only
    STATUS       current
    DESCRIPTION
        "Cisco Firepower sw:Ulan:epDn managed object property"
    ::= { cfprApSwUlanEntry 6 }

cfprApSwUlanId OBJECT-TYPE
    SYNTAX       Gauge32
    MAX-ACCESS   read-only
    STATUS       current
    DESCRIPTION
        "Cisco Firepower sw:Ulan:id managed object property"
    ::= { cfprApSwUlanEntry 7 }

cfprApSwUlanIfRole OBJECT-TYPE
    SYNTAX       CfprApFabricVnetEpIfRole
    MAX-ACCESS   read-only
    STATUS       current
    DESCRIPTION
        "Cisco Firepower sw:Ulan:ifRole managed object property"
    ::= { cfprApSwUlanEntry 8 }

cfprApSwUlanIfType OBJECT-TYPE
    SYNTAX       CfprApNetworkVnetEpIfType
    MAX-ACCESS   read-only
    STATUS       current
    DESCRIPTION
        "Cisco Firepower sw:Ulan:ifType managed object property"
    ::= { cfprApSwUlanEntry 9 }

cfprApSwUlanLocale OBJECT-TYPE
    SYNTAX       CfprApFabricVnetEpLocale
    MAX-ACCESS   read-only
    STATUS       current
    DESCRIPTION
        "Cisco Firepower sw:Ulan:locale managed object property"
    ::= { cfprApSwUlanEntry 10 }

cfprApSwUlanName OBJECT-TYPE
    SYNTAX       SnmpAdminString
    MAX-ACCESS   read-only
    STATUS       current
    DESCRIPTION
        "Cisco Firepower sw:Ulan:name managed object property"
    ::= { cfprApSwUlanEntry 11 }

cfprApSwUlanOperState OBJECT-TYPE
    SYNTAX       CfprApFabricVlanOperState
    MAX-ACCESS   read-only
    STATUS       current
    DESCRIPTION
        "Cisco Firepower sw:Ulan:operState managed object property"
    ::= { cfprApSwUlanEntry 12 }

cfprApSwUlanOverlapStateForA OBJECT-TYPE
    SYNTAX       CfprApFabricVlanOverlapState
    MAX-ACCESS   read-only
    STATUS       current
    DESCRIPTION
        "Cisco Firepower sw:Ulan:overlapStateForA managed object property"
    ::= { cfprApSwUlanEntry 13 }

cfprApSwUlanOverlapStateForB OBJECT-TYPE
    SYNTAX       CfprApFabricVlanOverlapState
    MAX-ACCESS   read-only
    STATUS       current
    DESCRIPTION
        "Cisco Firepower sw:Ulan:overlapStateForB managed object property"
    ::= { cfprApSwUlanEntry 14 }

cfprApSwUlanPeerDn OBJECT-TYPE
    SYNTAX       SnmpAdminString
    MAX-ACCESS   read-only
    STATUS       current
    DESCRIPTION
        "Cisco Firepower sw:Ulan:peerDn managed object property"
    ::= { cfprApSwUlanEntry 15 }

cfprApSwUlanPolicyOwner OBJECT-TYPE
    SYNTAX       CfprApFabricVnetEpPolicyOwner
    MAX-ACCESS   read-only
    STATUS       current
    DESCRIPTION
        "Cisco Firepower sw:Ulan:policyOwner managed object property"
    ::= { cfprApSwUlanEntry 16 }

cfprApSwUlanPubNwDn OBJECT-TYPE
    SYNTAX       SnmpAdminString
    MAX-ACCESS   read-only
    STATUS       current
    DESCRIPTION
        "Cisco Firepower sw:Ulan:pubNwDn managed object property"
    ::= { cfprApSwUlanEntry 17 }

cfprApSwUlanPubNwId OBJECT-TYPE
    SYNTAX       Gauge32
    MAX-ACCESS   read-only
    STATUS       current
    DESCRIPTION
        "Cisco Firepower sw:Ulan:pubNwId managed object property"
    ::= { cfprApSwUlanEntry 18 }

cfprApSwUlanPubNwName OBJECT-TYPE
    SYNTAX       SnmpAdminString
    MAX-ACCESS   read-only
    STATUS       current
    DESCRIPTION
        "Cisco Firepower sw:Ulan:pubNwName managed object property"
    ::= { cfprApSwUlanEntry 19 }

cfprApSwUlanPurpose OBJECT-TYPE
    SYNTAX       CfprApSwUlanPurpose
    MAX-ACCESS   read-only
    STATUS       current
    DESCRIPTION
        "Cisco Firepower sw:Ulan:purpose managed object property"
    ::= { cfprApSwUlanEntry 20 }

cfprApSwUlanSharing OBJECT-TYPE
    SYNTAX       CfprApFabricAVlanSharing
    MAX-ACCESS   read-only
    STATUS       current
    DESCRIPTION
        "Cisco Firepower sw:Ulan:sharing managed object property"
    ::= { cfprApSwUlanEntry 21 }

cfprApSwUlanSwitchId OBJECT-TYPE
    SYNTAX       CfprApNetworkSwitchId
    MAX-ACCESS   read-only
    STATUS       current
    DESCRIPTION
        "Cisco Firepower sw:Ulan:switchId managed object property"
    ::= { cfprApSwUlanEntry 22 }

cfprApSwUlanTransport OBJECT-TYPE
    SYNTAX       CfprApFabricAVlanTransport
    MAX-ACCESS   read-only
    STATUS       current
    DESCRIPTION
        "Cisco Firepower sw:Ulan:transport managed object property"
    ::= { cfprApSwUlanEntry 23 }

cfprApSwUlanType OBJECT-TYPE
    SYNTAX       CfprApFabricAVlanType
    MAX-ACCESS   read-only
    STATUS       current
    DESCRIPTION
        "Cisco Firepower sw:Ulan:type managed object property"
    ::= { cfprApSwUlanEntry 24 }

cfprApSwUlanVlanType OBJECT-TYPE
    SYNTAX       CfprApFabricEpVlanVlanType
    MAX-ACCESS   read-only
    STATUS       current
    DESCRIPTION
        "Cisco Firepower sw:Ulan:vlanType managed object property"
    ::= { cfprApSwUlanEntry 25 }

cfprApSwUtilityDomainTable OBJECT-TYPE
    SYNTAX           SEQUENCE OF CfprApSwUtilityDomainEntry
    MAX-ACCESS       not-accessible
    STATUS           current
    DESCRIPTION
        "Cisco Firepower sw:UtilityDomain managed object table"
    ::= { cfprApSwObjects 87 }

cfprApSwUtilityDomainEntry OBJECT-TYPE
    SYNTAX           CfprApSwUtilityDomainEntry
    MAX-ACCESS       not-accessible
    STATUS           current
    DESCRIPTION
        "Entry for the cfprApSwUtilityDomainTable table."
    INDEX { cfprApSwUtilityDomainInstanceId }
    ::= { cfprApSwUtilityDomainTable 1 }

CfprApSwUtilityDomainEntry ::= SEQUENCE {
    cfprApSwUtilityDomainInstanceId                                  CfprApManagedObjectId,
    cfprApSwUtilityDomainDn                                          CfprApManagedObjectDn,
    cfprApSwUtilityDomainRn                                          SnmpAdminString,
    cfprApSwUtilityDomainFsmDescr                                    SnmpAdminString,
    cfprApSwUtilityDomainFsmPrev                                     SnmpAdminString,
    cfprApSwUtilityDomainFsmProgr                                    Gauge32,
    cfprApSwUtilityDomainFsmRmtInvErrCode                            Gauge32,
    cfprApSwUtilityDomainFsmRmtInvErrDescr                           SnmpAdminString,
    cfprApSwUtilityDomainFsmRmtInvRslt                               CfprApConditionRemoteInvRslt,
    cfprApSwUtilityDomainFsmStageDescr                               SnmpAdminString,
    cfprApSwUtilityDomainFsmStamp                                    DateAndTime,
    cfprApSwUtilityDomainFsmStatus                                   SnmpAdminString,
    cfprApSwUtilityDomainFsmTry                                      Gauge32,
    cfprApSwUtilityDomainLocale                                      CfprApSwUtilityDomainLocale,
    cfprApSwUtilityDomainName                                        SnmpAdminString,
    cfprApSwUtilityDomainSwitchId                                    CfprApNetworkSwitchId,
    cfprApSwUtilityDomainTransport                                   CfprApNetworkTransport,
    cfprApSwUtilityDomainType                                        CfprApSwUtilityDomainType
}

cfprApSwUtilityDomainInstanceId OBJECT-TYPE
    SYNTAX       CfprApManagedObjectId
    MAX-ACCESS   not-accessible
    STATUS       current
    DESCRIPTION
        "Instance identifier of the managed object."
    ::= { cfprApSwUtilityDomainEntry 1 }

cfprApSwUtilityDomainDn OBJECT-TYPE
    SYNTAX       CfprApManagedObjectDn
    MAX-ACCESS   read-only
    STATUS       current
    DESCRIPTION
        "Cisco Firepower sw:UtilityDomain:dn managed object property"
    ::= { cfprApSwUtilityDomainEntry 2 }

cfprApSwUtilityDomainRn OBJECT-TYPE
    SYNTAX       SnmpAdminString
    MAX-ACCESS   read-only
    STATUS       current
    DESCRIPTION
        "Cisco Firepower sw:UtilityDomain:rn managed object property"
    ::= { cfprApSwUtilityDomainEntry 3 }

cfprApSwUtilityDomainFsmDescr OBJECT-TYPE
    SYNTAX       SnmpAdminString
    MAX-ACCESS   read-only
    STATUS       current
    DESCRIPTION
        "Cisco Firepower sw:UtilityDomain:fsmDescr managed
        object property"
    ::= { cfprApSwUtilityDomainEntry 4 }

cfprApSwUtilityDomainFsmPrev OBJECT-TYPE
    SYNTAX       SnmpAdminString
    MAX-ACCESS   read-only
    STATUS       current
    DESCRIPTION
        "Cisco Firepower sw:UtilityDomain:fsmPrev managed object property"
    ::= { cfprApSwUtilityDomainEntry 5 }

cfprApSwUtilityDomainFsmProgr OBJECT-TYPE
    SYNTAX       Gauge32
    MAX-ACCESS   read-only
    STATUS       current
    DESCRIPTION
        "Cisco Firepower sw:UtilityDomain:fsmProgr managed
        object property"
    ::= { cfprApSwUtilityDomainEntry 6 }

cfprApSwUtilityDomainFsmRmtInvErrCode OBJECT-TYPE
    SYNTAX       Gauge32
    MAX-ACCESS   read-only
    STATUS       current
    DESCRIPTION
        "Cisco Firepower sw:UtilityDomain:fsmRmtInvErrCode
        managed object property"
    ::= { cfprApSwUtilityDomainEntry 7 }

cfprApSwUtilityDomainFsmRmtInvErrDescr OBJECT-TYPE
    SYNTAX       SnmpAdminString
    MAX-ACCESS   read-only
    STATUS       current
    DESCRIPTION
        "Cisco Firepower sw:UtilityDomain:fsmRmtInvErrDescr
        managed object property"
    ::= { cfprApSwUtilityDomainEntry 8 }

cfprApSwUtilityDomainFsmRmtInvRslt OBJECT-TYPE
    SYNTAX       CfprApConditionRemoteInvRslt
    MAX-ACCESS   read-only
    STATUS       current
    DESCRIPTION
        "Cisco Firepower sw:UtilityDomain:fsmRmtInvRslt
        managed object property"
    ::= { cfprApSwUtilityDomainEntry 9 }

cfprApSwUtilityDomainFsmStageDescr OBJECT-TYPE
    SYNTAX       SnmpAdminString
    MAX-ACCESS   read-only
    STATUS       current
    DESCRIPTION
        "Cisco Firepower sw:UtilityDomain:fsmStageDescr
        managed object property"
    ::= { cfprApSwUtilityDomainEntry 10 }

cfprApSwUtilityDomainFsmStamp OBJECT-TYPE
    SYNTAX       DateAndTime
    MAX-ACCESS   read-only
    STATUS       current
    DESCRIPTION
        "Cisco Firepower sw:UtilityDomain:fsmStamp managed
        object property"
    ::= { cfprApSwUtilityDomainEntry 11 }

cfprApSwUtilityDomainFsmStatus OBJECT-TYPE
    SYNTAX       SnmpAdminString
    MAX-ACCESS   read-only
    STATUS       current
    DESCRIPTION
        "Cisco Firepower sw:UtilityDomain:fsmStatus managed
        object property"
    ::= { cfprApSwUtilityDomainEntry 12 }

cfprApSwUtilityDomainFsmTry OBJECT-TYPE
    SYNTAX       Gauge32
    MAX-ACCESS   read-only
    STATUS       current
    DESCRIPTION
        "Cisco Firepower sw:UtilityDomain:fsmTry managed object property"
    ::= { cfprApSwUtilityDomainEntry 13 }

cfprApSwUtilityDomainLocale OBJECT-TYPE
    SYNTAX       CfprApSwUtilityDomainLocale
    MAX-ACCESS   read-only
    STATUS       current
    DESCRIPTION
        "Cisco Firepower sw:UtilityDomain:locale managed object property"
    ::= { cfprApSwUtilityDomainEntry 14 }

cfprApSwUtilityDomainName OBJECT-TYPE
    SYNTAX       SnmpAdminString
    MAX-ACCESS   read-only
    STATUS       current
    DESCRIPTION
        "Cisco Firepower sw:UtilityDomain:name managed object property"
    ::= { cfprApSwUtilityDomainEntry 15 }

cfprApSwUtilityDomainSwitchId OBJECT-TYPE
    SYNTAX       CfprApNetworkSwitchId
    MAX-ACCESS   read-only
    STATUS       current
    DESCRIPTION
        "Cisco Firepower sw:UtilityDomain:switchId managed
        object property"
    ::= { cfprApSwUtilityDomainEntry 16 }

cfprApSwUtilityDomainTransport OBJECT-TYPE
    SYNTAX       CfprApNetworkTransport
    MAX-ACCESS   read-only
    STATUS       current
    DESCRIPTION
        "Cisco Firepower sw:UtilityDomain:transport managed
        object property"
    ::= { cfprApSwUtilityDomainEntry 17 }

cfprApSwUtilityDomainType OBJECT-TYPE
    SYNTAX       CfprApSwUtilityDomainType
    MAX-ACCESS   read-only
    STATUS       current
    DESCRIPTION
        "Cisco Firepower sw:UtilityDomain:type managed object property"
    ::= { cfprApSwUtilityDomainEntry 18 }

cfprApSwUtilityDomainFsmTable OBJECT-TYPE
    SYNTAX           SEQUENCE OF CfprApSwUtilityDomainFsmEntry
    MAX-ACCESS       not-accessible
    STATUS           current
    DESCRIPTION
        "Cisco Firepower sw:UtilityDomainFsm managed object table"
    ::= { cfprApSwObjects 88 }

cfprApSwUtilityDomainFsmEntry OBJECT-TYPE
    SYNTAX           CfprApSwUtilityDomainFsmEntry
    MAX-ACCESS       not-accessible
    STATUS           current
    DESCRIPTION
        "Entry for the cfprApSwUtilityDomainFsmTable table."
    INDEX { cfprApSwUtilityDomainFsmInstanceId }
    ::= { cfprApSwUtilityDomainFsmTable 1 }

CfprApSwUtilityDomainFsmEntry ::= SEQUENCE {
    cfprApSwUtilityDomainFsmInstanceId                               CfprApManagedObjectId,
    cfprApSwUtilityDomainFsmDn                                       CfprApManagedObjectDn,
    cfprApSwUtilityDomainFsmRn                                       SnmpAdminString,
    cfprApSwUtilityDomainFsmCompletionTime                           DateAndTime,
    cfprApSwUtilityDomainFsmCurrentFsm                               CfprApSwUtilityDomainFsmCurrentFsm,
    cfprApSwUtilityDomainFsmDescrData                                SnmpAdminString,
    cfprApSwUtilityDomainFsmFsmStatus                                CfprApFsmFsmStageStatus,
    cfprApSwUtilityDomainFsmProgress                                 Gauge32,
    cfprApSwUtilityDomainFsmRmtErrCode                               Gauge32,
    cfprApSwUtilityDomainFsmRmtErrDescr                              SnmpAdminString,
    cfprApSwUtilityDomainFsmRmtRslt                                  CfprApConditionRemoteInvRslt
}

cfprApSwUtilityDomainFsmInstanceId OBJECT-TYPE
    SYNTAX       CfprApManagedObjectId
    MAX-ACCESS   not-accessible
    STATUS       current
    DESCRIPTION
        "Instance identifier of the managed object."
    ::= { cfprApSwUtilityDomainFsmEntry 1 }

cfprApSwUtilityDomainFsmDn OBJECT-TYPE
    SYNTAX       CfprApManagedObjectDn
    MAX-ACCESS   read-only
    STATUS       current
    DESCRIPTION
        "Cisco Firepower sw:UtilityDomainFsm:dn managed object property"
    ::= { cfprApSwUtilityDomainFsmEntry 2 }

cfprApSwUtilityDomainFsmRn OBJECT-TYPE
    SYNTAX       SnmpAdminString
    MAX-ACCESS   read-only
    STATUS       current
    DESCRIPTION
        "Cisco Firepower sw:UtilityDomainFsm:rn managed object property"
    ::= { cfprApSwUtilityDomainFsmEntry 3 }

cfprApSwUtilityDomainFsmCompletionTime OBJECT-TYPE
    SYNTAX       DateAndTime
    MAX-ACCESS   read-only
    STATUS       current
    DESCRIPTION
        "Cisco Firepower sw:UtilityDomainFsm:completionTime
        managed object property"
    ::= { cfprApSwUtilityDomainFsmEntry 4 }

cfprApSwUtilityDomainFsmCurrentFsm OBJECT-TYPE
    SYNTAX       CfprApSwUtilityDomainFsmCurrentFsm
    MAX-ACCESS   read-only
    STATUS       current
    DESCRIPTION
        "Cisco Firepower sw:UtilityDomainFsm:currentFsm
        managed object property"
    ::= { cfprApSwUtilityDomainFsmEntry 5 }

cfprApSwUtilityDomainFsmDescrData OBJECT-TYPE
    SYNTAX       SnmpAdminString
    MAX-ACCESS   read-only
    STATUS       current
    DESCRIPTION
        "Cisco Firepower sw:UtilityDomainFsm:descr managed
        object property"
    ::= { cfprApSwUtilityDomainFsmEntry 6 }

cfprApSwUtilityDomainFsmFsmStatus OBJECT-TYPE
    SYNTAX       CfprApFsmFsmStageStatus
    MAX-ACCESS   read-only
    STATUS       current
    DESCRIPTION
        "Cisco Firepower sw:UtilityDomainFsm:fsmStatus
        managed object property"
    ::= { cfprApSwUtilityDomainFsmEntry 7 }

cfprApSwUtilityDomainFsmProgress OBJECT-TYPE
    SYNTAX       Gauge32
    MAX-ACCESS   read-only
    STATUS       current
    DESCRIPTION
        "Cisco Firepower sw:UtilityDomainFsm:progress managed
        object property"
    ::= { cfprApSwUtilityDomainFsmEntry 8 }

cfprApSwUtilityDomainFsmRmtErrCode OBJECT-TYPE
    SYNTAX       Gauge32
    MAX-ACCESS   read-only
    STATUS       current
    DESCRIPTION
        "Cisco Firepower sw:UtilityDomainFsm:rmtErrCode
        managed object property"
    ::= { cfprApSwUtilityDomainFsmEntry 9 }

cfprApSwUtilityDomainFsmRmtErrDescr OBJECT-TYPE
    SYNTAX       SnmpAdminString
    MAX-ACCESS   read-only
    STATUS       current
    DESCRIPTION
        "Cisco Firepower sw:UtilityDomainFsm:rmtErrDescr
        managed object property"
    ::= { cfprApSwUtilityDomainFsmEntry 10 }

cfprApSwUtilityDomainFsmRmtRslt OBJECT-TYPE
    SYNTAX       CfprApConditionRemoteInvRslt
    MAX-ACCESS   read-only
    STATUS       current
    DESCRIPTION
        "Cisco Firepower sw:UtilityDomainFsm:rmtRslt managed
        object property"
    ::= { cfprApSwUtilityDomainFsmEntry 11 }

cfprApSwUtilityDomainFsmStageTable OBJECT-TYPE
    SYNTAX           SEQUENCE OF CfprApSwUtilityDomainFsmStageEntry
    MAX-ACCESS       not-accessible
    STATUS           current
    DESCRIPTION
        "Cisco Firepower sw:UtilityDomainFsmStage managed object table"
    ::= { cfprApSwObjects 89 }

cfprApSwUtilityDomainFsmStageEntry OBJECT-TYPE
    SYNTAX           CfprApSwUtilityDomainFsmStageEntry
    MAX-ACCESS       not-accessible
    STATUS           current
    DESCRIPTION
        "Entry for the cfprApSwUtilityDomainFsmStageTable table."
    INDEX { cfprApSwUtilityDomainFsmStageInstanceId }
    ::= { cfprApSwUtilityDomainFsmStageTable 1 }

CfprApSwUtilityDomainFsmStageEntry ::= SEQUENCE {
    cfprApSwUtilityDomainFsmStageInstanceId                          CfprApManagedObjectId,
    cfprApSwUtilityDomainFsmStageDn                                  CfprApManagedObjectDn,
    cfprApSwUtilityDomainFsmStageRn                                  SnmpAdminString,
    cfprApSwUtilityDomainFsmStageDescrData                           SnmpAdminString,
    cfprApSwUtilityDomainFsmStageLastUpdateTime                      DateAndTime,
    cfprApSwUtilityDomainFsmStageName                                CfprApSwUtilityDomainFsmStageName,
    cfprApSwUtilityDomainFsmStageOrder                               Gauge32,
    cfprApSwUtilityDomainFsmStageRetry                               Gauge32,
    cfprApSwUtilityDomainFsmStageStageStatus                         CfprApFsmFsmStageStatus
}

cfprApSwUtilityDomainFsmStageInstanceId OBJECT-TYPE
    SYNTAX       CfprApManagedObjectId
    MAX-ACCESS   not-accessible
    STATUS       current
    DESCRIPTION
        "Instance identifier of the managed object."
    ::= { cfprApSwUtilityDomainFsmStageEntry 1 }

cfprApSwUtilityDomainFsmStageDn OBJECT-TYPE
    SYNTAX       CfprApManagedObjectDn
    MAX-ACCESS   read-only
    STATUS       current
    DESCRIPTION
        "Cisco Firepower sw:UtilityDomainFsmStage:dn managed
        object property"
    ::= { cfprApSwUtilityDomainFsmStageEntry 2 }

cfprApSwUtilityDomainFsmStageRn OBJECT-TYPE
    SYNTAX       SnmpAdminString
    MAX-ACCESS   read-only
    STATUS       current
    DESCRIPTION
        "Cisco Firepower sw:UtilityDomainFsmStage:rn managed
        object property"
    ::= { cfprApSwUtilityDomainFsmStageEntry 3 }

cfprApSwUtilityDomainFsmStageDescrData OBJECT-TYPE
    SYNTAX       SnmpAdminString
    MAX-ACCESS   read-only
    STATUS       current
    DESCRIPTION
        "Cisco Firepower sw:UtilityDomainFsmStage:descr
        managed object property"
    ::= { cfprApSwUtilityDomainFsmStageEntry 4 }

cfprApSwUtilityDomainFsmStageLastUpdateTime OBJECT-TYPE
    SYNTAX       DateAndTime
    MAX-ACCESS   read-only
    STATUS       current
    DESCRIPTION
        "Cisco Firepower sw:UtilityDomainFsmStage:lastUpdateTime
        managed object property"
    ::= { cfprApSwUtilityDomainFsmStageEntry 5 }

cfprApSwUtilityDomainFsmStageName OBJECT-TYPE
    SYNTAX       CfprApSwUtilityDomainFsmStageName
    MAX-ACCESS   read-only
    STATUS       current
    DESCRIPTION
        "Cisco Firepower sw:UtilityDomainFsmStage:name
        managed object property"
    ::= { cfprApSwUtilityDomainFsmStageEntry 6 }

cfprApSwUtilityDomainFsmStageOrder OBJECT-TYPE
    SYNTAX       Gauge32
    MAX-ACCESS   read-only
    STATUS       current
    DESCRIPTION
        "Cisco Firepower sw:UtilityDomainFsmStage:order
        managed object property"
    ::= { cfprApSwUtilityDomainFsmStageEntry 7 }

cfprApSwUtilityDomainFsmStageRetry OBJECT-TYPE
    SYNTAX       Gauge32
    MAX-ACCESS   read-only
    STATUS       current
    DESCRIPTION
        "Cisco Firepower sw:UtilityDomainFsmStage:retry
        managed object property"
    ::= { cfprApSwUtilityDomainFsmStageEntry 8 }

cfprApSwUtilityDomainFsmStageStageStatus OBJECT-TYPE
    SYNTAX       CfprApFsmFsmStageStatus
    MAX-ACCESS   read-only
    STATUS       current
    DESCRIPTION
        "Cisco Firepower sw:UtilityDomainFsmStage:stageStatus
        managed object property"
    ::= { cfprApSwUtilityDomainFsmStageEntry 9 }

cfprApSwUtilityDomainFsmTaskTable OBJECT-TYPE
    SYNTAX           SEQUENCE OF CfprApSwUtilityDomainFsmTaskEntry
    MAX-ACCESS       not-accessible
    STATUS           current
    DESCRIPTION
        "Cisco Firepower sw:UtilityDomainFsmTask managed object table"
    ::= { cfprApSwObjects 90 }

cfprApSwUtilityDomainFsmTaskEntry OBJECT-TYPE
    SYNTAX           CfprApSwUtilityDomainFsmTaskEntry
    MAX-ACCESS       not-accessible
    STATUS           current
    DESCRIPTION
        "Entry for the cfprApSwUtilityDomainFsmTaskTable table."
    INDEX { cfprApSwUtilityDomainFsmTaskInstanceId }
    ::= { cfprApSwUtilityDomainFsmTaskTable 1 }

CfprApSwUtilityDomainFsmTaskEntry ::= SEQUENCE {
    cfprApSwUtilityDomainFsmTaskInstanceId                           CfprApManagedObjectId,
    cfprApSwUtilityDomainFsmTaskDn                                   CfprApManagedObjectDn,
    cfprApSwUtilityDomainFsmTaskRn                                   SnmpAdminString,
    cfprApSwUtilityDomainFsmTaskCompletion                           CfprApFsmCompletion,
    cfprApSwUtilityDomainFsmTaskFlags                                CfprApFsmFlags,
    cfprApSwUtilityDomainFsmTaskItem                                 CfprApSwUtilityDomainFsmTaskItem,
    cfprApSwUtilityDomainFsmTaskSeqId                                Gauge32
}

cfprApSwUtilityDomainFsmTaskInstanceId OBJECT-TYPE
    SYNTAX       CfprApManagedObjectId
    MAX-ACCESS   not-accessible
    STATUS       current
    DESCRIPTION
        "Instance identifier of the managed object."
    ::= { cfprApSwUtilityDomainFsmTaskEntry 1 }

cfprApSwUtilityDomainFsmTaskDn OBJECT-TYPE
    SYNTAX       CfprApManagedObjectDn
    MAX-ACCESS   read-only
    STATUS       current
    DESCRIPTION
        "Cisco Firepower sw:UtilityDomainFsmTask:dn managed
        object property"
    ::= { cfprApSwUtilityDomainFsmTaskEntry 2 }

cfprApSwUtilityDomainFsmTaskRn OBJECT-TYPE
    SYNTAX       SnmpAdminString
    MAX-ACCESS   read-only
    STATUS       current
    DESCRIPTION
        "Cisco Firepower sw:UtilityDomainFsmTask:rn managed
        object property"
    ::= { cfprApSwUtilityDomainFsmTaskEntry 3 }

cfprApSwUtilityDomainFsmTaskCompletion OBJECT-TYPE
    SYNTAX       CfprApFsmCompletion
    MAX-ACCESS   read-only
    STATUS       current
    DESCRIPTION
        "Cisco Firepower sw:UtilityDomainFsmTask:completion
        managed object property"
    ::= { cfprApSwUtilityDomainFsmTaskEntry 4 }

cfprApSwUtilityDomainFsmTaskFlags OBJECT-TYPE
    SYNTAX       CfprApFsmFlags
    MAX-ACCESS   read-only
    STATUS       current
    DESCRIPTION
        "Cisco Firepower sw:UtilityDomainFsmTask:flags
        managed object property"
    ::= { cfprApSwUtilityDomainFsmTaskEntry 5 }

cfprApSwUtilityDomainFsmTaskItem OBJECT-TYPE
    SYNTAX       CfprApSwUtilityDomainFsmTaskItem
    MAX-ACCESS   read-only
    STATUS       current
    DESCRIPTION
        "Cisco Firepower sw:UtilityDomainFsmTask:item managed
        object property"
    ::= { cfprApSwUtilityDomainFsmTaskEntry 6 }

cfprApSwUtilityDomainFsmTaskSeqId OBJECT-TYPE
    SYNTAX       Gauge32
    MAX-ACCESS   read-only
    STATUS       current
    DESCRIPTION
        "Cisco Firepower sw:UtilityDomainFsmTask:seqId
        managed object property"
    ::= { cfprApSwUtilityDomainFsmTaskEntry 7 }

cfprApSwVlanTable OBJECT-TYPE
    SYNTAX           SEQUENCE OF CfprApSwVlanEntry
    MAX-ACCESS       not-accessible
    STATUS           current
    DESCRIPTION
        "Cisco Firepower sw:Vlan managed object table"
    ::= { cfprApSwObjects 92 }

cfprApSwVlanEntry OBJECT-TYPE
    SYNTAX           CfprApSwVlanEntry
    MAX-ACCESS       not-accessible
    STATUS           current
    DESCRIPTION
        "Entry for the cfprApSwVlanTable table."
    INDEX { cfprApSwVlanInstanceId }
    ::= { cfprApSwVlanTable 1 }

CfprApSwVlanEntry ::= SEQUENCE {
    cfprApSwVlanInstanceId                                           CfprApManagedObjectId,
    cfprApSwVlanDn                                                   CfprApManagedObjectDn,
    cfprApSwVlanRn                                                   SnmpAdminString,
    cfprApSwVlanAssocPrimaryVlanState                                CfprApFabricVlanAssocPrimaryVlanState,
    cfprApSwVlanAssocPrimaryVlanSwitchId                             CfprApFabricAVlanAssocPrimaryVlanSwitchId,
    cfprApSwVlanCompressionType                                      CfprApSwVlanCompType,
    cfprApSwVlanEpDn                                                 SnmpAdminString,
    cfprApSwVlanId                                                   Gauge32,
    cfprApSwVlanIfRole                                               CfprApFabricVnetEpIfRole,
    cfprApSwVlanIfType                                               CfprApNetworkVnetEpIfType,
    cfprApSwVlanLc                                                   CfprApSwVlanLc,
    cfprApSwVlanLocale                                               CfprApFabricVnetEpLocale,
    cfprApSwVlanMonTrafDir                                           CfprApFabricTrafficDirection,
    cfprApSwVlanName                                                 SnmpAdminString,
    cfprApSwVlanOperState                                            CfprApFabricVlanOperState,
    cfprApSwVlanOverlapStateForA                                     CfprApFabricVlanOverlapState,
    cfprApSwVlanOverlapStateForB                                     CfprApFabricVlanOverlapState,
    cfprApSwVlanPeerDn                                               SnmpAdminString,
    cfprApSwVlanPolicyOwner                                          CfprApFabricVnetEpPolicyOwner,
    cfprApSwVlanPubNwDn                                              SnmpAdminString,
    cfprApSwVlanPubNwId                                              Gauge32,
    cfprApSwVlanPubNwName                                            SnmpAdminString,
    cfprApSwVlanQuerierIpAddrs                                       InetAddressIPv4,
    cfprApSwVlanSecVlanPerPrimaryVlanCount                           Gauge32,
    cfprApSwVlanSecVlanPerPrimaryVlanCountStatus                     CfprApNetworkVlanCountStatus,
    cfprApSwVlanSharing                                              CfprApFabricAVlanSharing,
    cfprApSwVlanSnoopingEnabled                                      TruthValue,
    cfprApSwVlanSwitchId                                             CfprApNetworkSwitchId,
    cfprApSwVlanTransport                                            CfprApFabricAVlanTransport,
    cfprApSwVlanType                                                 CfprApFabricAVlanType,
    cfprApSwVlanVlanType                                             CfprApFabricEpVlanVlanType
}

cfprApSwVlanInstanceId OBJECT-TYPE
    SYNTAX       CfprApManagedObjectId
    MAX-ACCESS   not-accessible
    STATUS       current
    DESCRIPTION
        "Instance identifier of the managed object."
    ::= { cfprApSwVlanEntry 1 }

cfprApSwVlanDn OBJECT-TYPE
    SYNTAX       CfprApManagedObjectDn
    MAX-ACCESS   read-only
    STATUS       current
    DESCRIPTION
        "Cisco Firepower sw:Vlan:dn managed object property"
    ::= { cfprApSwVlanEntry 2 }

cfprApSwVlanRn OBJECT-TYPE
    SYNTAX       SnmpAdminString
    MAX-ACCESS   read-only
    STATUS       current
    DESCRIPTION
        "Cisco Firepower sw:Vlan:rn managed object property"
    ::= { cfprApSwVlanEntry 3 }

cfprApSwVlanAssocPrimaryVlanState OBJECT-TYPE
    SYNTAX       CfprApFabricVlanAssocPrimaryVlanState
    MAX-ACCESS   read-only
    STATUS       current
    DESCRIPTION
        "Cisco Firepower sw:Vlan:assocPrimaryVlanState
        managed object property"
    ::= { cfprApSwVlanEntry 4 }

cfprApSwVlanAssocPrimaryVlanSwitchId OBJECT-TYPE
    SYNTAX       CfprApFabricAVlanAssocPrimaryVlanSwitchId
    MAX-ACCESS   read-only
    STATUS       current
    DESCRIPTION
        "Cisco Firepower sw:Vlan:assocPrimaryVlanSwitchId
        managed object property"
    ::= { cfprApSwVlanEntry 5 }

cfprApSwVlanCompressionType OBJECT-TYPE
    SYNTAX       CfprApSwVlanCompType
    MAX-ACCESS   read-only
    STATUS       current
    DESCRIPTION
        "Cisco Firepower sw:Vlan:compressionType managed object property"
    ::= { cfprApSwVlanEntry 6 }

cfprApSwVlanEpDn OBJECT-TYPE
    SYNTAX       SnmpAdminString
    MAX-ACCESS   read-only
    STATUS       current
    DESCRIPTION
        "Cisco Firepower sw:Vlan:epDn managed object property"
    ::= { cfprApSwVlanEntry 7 }

cfprApSwVlanId OBJECT-TYPE
    SYNTAX       Gauge32
    MAX-ACCESS   read-only
    STATUS       current
    DESCRIPTION
        "Cisco Firepower sw:Vlan:id managed object property"
    ::= { cfprApSwVlanEntry 8 }

cfprApSwVlanIfRole OBJECT-TYPE
    SYNTAX       CfprApFabricVnetEpIfRole
    MAX-ACCESS   read-only
    STATUS       current
    DESCRIPTION
        "Cisco Firepower sw:Vlan:ifRole managed object property"
    ::= { cfprApSwVlanEntry 9 }

cfprApSwVlanIfType OBJECT-TYPE
    SYNTAX       CfprApNetworkVnetEpIfType
    MAX-ACCESS   read-only
    STATUS       current
    DESCRIPTION
        "Cisco Firepower sw:Vlan:ifType managed object property"
    ::= { cfprApSwVlanEntry 10 }

cfprApSwVlanLc OBJECT-TYPE
    SYNTAX       CfprApSwVlanLc
    MAX-ACCESS   read-only
    STATUS       current
    DESCRIPTION
        "Cisco Firepower sw:Vlan:lc managed object property"
    ::= { cfprApSwVlanEntry 11 }

cfprApSwVlanLocale OBJECT-TYPE
    SYNTAX       CfprApFabricVnetEpLocale
    MAX-ACCESS   read-only
    STATUS       current
    DESCRIPTION
        "Cisco Firepower sw:Vlan:locale managed object property"
    ::= { cfprApSwVlanEntry 12 }

cfprApSwVlanMonTrafDir OBJECT-TYPE
    SYNTAX       CfprApFabricTrafficDirection
    MAX-ACCESS   read-only
    STATUS       current
    DESCRIPTION
        "Cisco Firepower sw:Vlan:monTrafDir managed object property"
    ::= { cfprApSwVlanEntry 13 }

cfprApSwVlanName OBJECT-TYPE
    SYNTAX       SnmpAdminString
    MAX-ACCESS   read-only
    STATUS       current
    DESCRIPTION
        "Cisco Firepower sw:Vlan:name managed object property"
    ::= { cfprApSwVlanEntry 14 }

cfprApSwVlanOperState OBJECT-TYPE
    SYNTAX       CfprApFabricVlanOperState
    MAX-ACCESS   read-only
    STATUS       current
    DESCRIPTION
        "Cisco Firepower sw:Vlan:operState managed object property"
    ::= { cfprApSwVlanEntry 15 }

cfprApSwVlanOverlapStateForA OBJECT-TYPE
    SYNTAX       CfprApFabricVlanOverlapState
    MAX-ACCESS   read-only
    STATUS       current
    DESCRIPTION
        "Cisco Firepower sw:Vlan:overlapStateForA managed object property"
    ::= { cfprApSwVlanEntry 16 }

cfprApSwVlanOverlapStateForB OBJECT-TYPE
    SYNTAX       CfprApFabricVlanOverlapState
    MAX-ACCESS   read-only
    STATUS       current
    DESCRIPTION
        "Cisco Firepower sw:Vlan:overlapStateForB managed object property"
    ::= { cfprApSwVlanEntry 17 }

cfprApSwVlanPeerDn OBJECT-TYPE
    SYNTAX       SnmpAdminString
    MAX-ACCESS   read-only
    STATUS       current
    DESCRIPTION
        "Cisco Firepower sw:Vlan:peerDn managed object property"
    ::= { cfprApSwVlanEntry 18 }

cfprApSwVlanPolicyOwner OBJECT-TYPE
    SYNTAX       CfprApFabricVnetEpPolicyOwner
    MAX-ACCESS   read-only
    STATUS       current
    DESCRIPTION
        "Cisco Firepower sw:Vlan:policyOwner managed object property"
    ::= { cfprApSwVlanEntry 19 }

cfprApSwVlanPubNwDn OBJECT-TYPE
    SYNTAX       SnmpAdminString
    MAX-ACCESS   read-only
    STATUS       current
    DESCRIPTION
        "Cisco Firepower sw:Vlan:pubNwDn managed object property"
    ::= { cfprApSwVlanEntry 20 }

cfprApSwVlanPubNwId OBJECT-TYPE
    SYNTAX       Gauge32
    MAX-ACCESS   read-only
    STATUS       current
    DESCRIPTION
        "Cisco Firepower sw:Vlan:pubNwId managed object property"
    ::= { cfprApSwVlanEntry 21 }

cfprApSwVlanPubNwName OBJECT-TYPE
    SYNTAX       SnmpAdminString
    MAX-ACCESS   read-only
    STATUS       current
    DESCRIPTION
        "Cisco Firepower sw:Vlan:pubNwName managed object property"
    ::= { cfprApSwVlanEntry 22 }

cfprApSwVlanQuerierIpAddrs OBJECT-TYPE
    SYNTAX       InetAddressIPv4
    MAX-ACCESS   read-only
    STATUS       current
    DESCRIPTION
        "Cisco Firepower sw:Vlan:querierIpAddrs managed object property"
    ::= { cfprApSwVlanEntry 23 }

cfprApSwVlanSecVlanPerPrimaryVlanCount OBJECT-TYPE
    SYNTAX       Gauge32
    MAX-ACCESS   read-only
    STATUS       current
    DESCRIPTION
        "Cisco Firepower sw:Vlan:secVlanPerPrimaryVlanCount
        managed object property"
    ::= { cfprApSwVlanEntry 24 }

cfprApSwVlanSecVlanPerPrimaryVlanCountStatus OBJECT-TYPE
    SYNTAX       CfprApNetworkVlanCountStatus
    MAX-ACCESS   read-only
    STATUS       current
    DESCRIPTION
        "Cisco Firepower sw:Vlan:secVlanPerPrimaryVlanCountStatus
        managed object property"
    ::= { cfprApSwVlanEntry 25 }

cfprApSwVlanSharing OBJECT-TYPE
    SYNTAX       CfprApFabricAVlanSharing
    MAX-ACCESS   read-only
    STATUS       current
    DESCRIPTION
        "Cisco Firepower sw:Vlan:sharing managed object property"
    ::= { cfprApSwVlanEntry 26 }

cfprApSwVlanSnoopingEnabled OBJECT-TYPE
    SYNTAX       TruthValue
    MAX-ACCESS   read-only
    STATUS       current
    DESCRIPTION
        "Cisco Firepower sw:Vlan:snoopingEnabled managed object property"
    ::= { cfprApSwVlanEntry 27 }

cfprApSwVlanSwitchId OBJECT-TYPE
    SYNTAX       CfprApNetworkSwitchId
    MAX-ACCESS   read-only
    STATUS       current
    DESCRIPTION
        "Cisco Firepower sw:Vlan:switchId managed object property"
    ::= { cfprApSwVlanEntry 28 }

cfprApSwVlanTransport OBJECT-TYPE
    SYNTAX       CfprApFabricAVlanTransport
    MAX-ACCESS   read-only
    STATUS       current
    DESCRIPTION
        "Cisco Firepower sw:Vlan:transport managed object property"
    ::= { cfprApSwVlanEntry 29 }

cfprApSwVlanType OBJECT-TYPE
    SYNTAX       CfprApFabricAVlanType
    MAX-ACCESS   read-only
    STATUS       current
    DESCRIPTION
        "Cisco Firepower sw:Vlan:type managed object property"
    ::= { cfprApSwVlanEntry 30 }

cfprApSwVlanVlanType OBJECT-TYPE
    SYNTAX       CfprApFabricEpVlanVlanType
    MAX-ACCESS   read-only
    STATUS       current
    DESCRIPTION
        "Cisco Firepower sw:Vlan:vlanType managed object property"
    ::= { cfprApSwVlanEntry 31 }

cfprApSwVlanGroupTable OBJECT-TYPE
    SYNTAX           SEQUENCE OF CfprApSwVlanGroupEntry
    MAX-ACCESS       not-accessible
    STATUS           current
    DESCRIPTION
        "Cisco Firepower sw:VlanGroup managed object table"
    ::= { cfprApSwObjects 93 }

cfprApSwVlanGroupEntry OBJECT-TYPE
    SYNTAX           CfprApSwVlanGroupEntry
    MAX-ACCESS       not-accessible
    STATUS           current
    DESCRIPTION
        "Entry for the cfprApSwVlanGroupTable table."
    INDEX { cfprApSwVlanGroupInstanceId }
    ::= { cfprApSwVlanGroupTable 1 }

CfprApSwVlanGroupEntry ::= SEQUENCE {
    cfprApSwVlanGroupInstanceId                                      CfprApManagedObjectId,
    cfprApSwVlanGroupDn                                              CfprApManagedObjectDn,
    cfprApSwVlanGroupRn                                              SnmpAdminString,
    cfprApSwVlanGroupId                                              Gauge32,
    cfprApSwVlanGroupPeerDn                                          SnmpAdminString,
    cfprApSwVlanGroupSwitchId                                        CfprApNetworkSwitchId,
    cfprApSwVlanGroupType                                            CfprApSwVlanGroupType
}

cfprApSwVlanGroupInstanceId OBJECT-TYPE
    SYNTAX       CfprApManagedObjectId
    MAX-ACCESS   not-accessible
    STATUS       current
    DESCRIPTION
        "Instance identifier of the managed object."
    ::= { cfprApSwVlanGroupEntry 1 }

cfprApSwVlanGroupDn OBJECT-TYPE
    SYNTAX       CfprApManagedObjectDn
    MAX-ACCESS   read-only
    STATUS       current
    DESCRIPTION
        "Cisco Firepower sw:VlanGroup:dn managed object property"
    ::= { cfprApSwVlanGroupEntry 2 }

cfprApSwVlanGroupRn OBJECT-TYPE
    SYNTAX       SnmpAdminString
    MAX-ACCESS   read-only
    STATUS       current
    DESCRIPTION
        "Cisco Firepower sw:VlanGroup:rn managed object property"
    ::= { cfprApSwVlanGroupEntry 3 }

cfprApSwVlanGroupId OBJECT-TYPE
    SYNTAX       Gauge32
    MAX-ACCESS   read-only
    STATUS       current
    DESCRIPTION
        "Cisco Firepower sw:VlanGroup:id managed object property"
    ::= { cfprApSwVlanGroupEntry 4 }

cfprApSwVlanGroupPeerDn OBJECT-TYPE
    SYNTAX       SnmpAdminString
    MAX-ACCESS   read-only
    STATUS       current
    DESCRIPTION
        "Cisco Firepower sw:VlanGroup:peerDn managed object property"
    ::= { cfprApSwVlanGroupEntry 5 }

cfprApSwVlanGroupSwitchId OBJECT-TYPE
    SYNTAX       CfprApNetworkSwitchId
    MAX-ACCESS   read-only
    STATUS       current
    DESCRIPTION
        "Cisco Firepower sw:VlanGroup:switchId managed object property"
    ::= { cfprApSwVlanGroupEntry 6 }

cfprApSwVlanGroupType OBJECT-TYPE
    SYNTAX       CfprApSwVlanGroupType
    MAX-ACCESS   read-only
    STATUS       current
    DESCRIPTION
        "Cisco Firepower sw:VlanGroup:type managed object property"
    ::= { cfprApSwVlanGroupEntry 7 }

cfprApSwVlanPortNsTable OBJECT-TYPE
    SYNTAX           SEQUENCE OF CfprApSwVlanPortNsEntry
    MAX-ACCESS       not-accessible
    STATUS           current
    DESCRIPTION
        "Cisco Firepower sw:VlanPortNs managed object table"
    ::= { cfprApSwObjects 94 }

cfprApSwVlanPortNsEntry OBJECT-TYPE
    SYNTAX           CfprApSwVlanPortNsEntry
    MAX-ACCESS       not-accessible
    STATUS           current
    DESCRIPTION
        "Entry for the cfprApSwVlanPortNsTable table."
    INDEX { cfprApSwVlanPortNsInstanceId }
    ::= { cfprApSwVlanPortNsTable 1 }

CfprApSwVlanPortNsEntry ::= SEQUENCE {
    cfprApSwVlanPortNsInstanceId                                     CfprApManagedObjectId,
    cfprApSwVlanPortNsDn                                             CfprApManagedObjectDn,
    cfprApSwVlanPortNsRn                                             SnmpAdminString,
    cfprApSwVlanPortNsAccessVlanPortCount                            Gauge32,
    cfprApSwVlanPortNsAllocStatus                                    CfprApSwVlanPortNsAllocStatus,
    cfprApSwVlanPortNsBorderVlanPortCount                            Gauge32,
    cfprApSwVlanPortNsConfigStatus                                   CfprApSwConfigStatus,
    cfprApSwVlanPortNsLimit                                          Gauge32,
    cfprApSwVlanPortNsSwitchId                                       CfprApNetworkSwitchId,
    cfprApSwVlanPortNsTotalVlanPortCount                             Gauge32,
    cfprApSwVlanPortNsVlanCompOffLimit                               Gauge32,
    cfprApSwVlanPortNsVlanCompOnLimit                                Gauge32
}

cfprApSwVlanPortNsInstanceId OBJECT-TYPE
    SYNTAX       CfprApManagedObjectId
    MAX-ACCESS   not-accessible
    STATUS       current
    DESCRIPTION
        "Instance identifier of the managed object."
    ::= { cfprApSwVlanPortNsEntry 1 }

cfprApSwVlanPortNsDn OBJECT-TYPE
    SYNTAX       CfprApManagedObjectDn
    MAX-ACCESS   read-only
    STATUS       current
    DESCRIPTION
        "Cisco Firepower sw:VlanPortNs:dn managed object property"
    ::= { cfprApSwVlanPortNsEntry 2 }

cfprApSwVlanPortNsRn OBJECT-TYPE
    SYNTAX       SnmpAdminString
    MAX-ACCESS   read-only
    STATUS       current
    DESCRIPTION
        "Cisco Firepower sw:VlanPortNs:rn managed object property"
    ::= { cfprApSwVlanPortNsEntry 3 }

cfprApSwVlanPortNsAccessVlanPortCount OBJECT-TYPE
    SYNTAX       Gauge32
    MAX-ACCESS   read-only
    STATUS       current
    DESCRIPTION
        "Cisco Firepower sw:VlanPortNs:accessVlanPortCount
        managed object property"
    ::= { cfprApSwVlanPortNsEntry 4 }

cfprApSwVlanPortNsAllocStatus OBJECT-TYPE
    SYNTAX       CfprApSwVlanPortNsAllocStatus
    MAX-ACCESS   read-only
    STATUS       current
    DESCRIPTION
        "Cisco Firepower sw:VlanPortNs:allocStatus managed
        object property"
    ::= { cfprApSwVlanPortNsEntry 5 }

cfprApSwVlanPortNsBorderVlanPortCount OBJECT-TYPE
    SYNTAX       Gauge32
    MAX-ACCESS   read-only
    STATUS       current
    DESCRIPTION
        "Cisco Firepower sw:VlanPortNs:borderVlanPortCount
        managed object property"
    ::= { cfprApSwVlanPortNsEntry 6 }

cfprApSwVlanPortNsConfigStatus OBJECT-TYPE
    SYNTAX       CfprApSwConfigStatus
    MAX-ACCESS   read-only
    STATUS       current
    DESCRIPTION
        "Cisco Firepower sw:VlanPortNs:configStatus managed
        object property"
    ::= { cfprApSwVlanPortNsEntry 7 }

cfprApSwVlanPortNsLimit OBJECT-TYPE
    SYNTAX       Gauge32
    MAX-ACCESS   read-only
    STATUS       current
    DESCRIPTION
        "Cisco Firepower sw:VlanPortNs:limit managed object property"
    ::= { cfprApSwVlanPortNsEntry 8 }

cfprApSwVlanPortNsSwitchId OBJECT-TYPE
    SYNTAX       CfprApNetworkSwitchId
    MAX-ACCESS   read-only
    STATUS       current
    DESCRIPTION
        "Cisco Firepower sw:VlanPortNs:switchId managed object property"
    ::= { cfprApSwVlanPortNsEntry 9 }

cfprApSwVlanPortNsTotalVlanPortCount OBJECT-TYPE
    SYNTAX       Gauge32
    MAX-ACCESS   read-only
    STATUS       current
    DESCRIPTION
        "Cisco Firepower sw:VlanPortNs:totalVlanPortCount
        managed object property"
    ::= { cfprApSwVlanPortNsEntry 10 }

cfprApSwVlanPortNsVlanCompOffLimit OBJECT-TYPE
    SYNTAX       Gauge32
    MAX-ACCESS   read-only
    STATUS       current
    DESCRIPTION
        "Cisco Firepower sw:VlanPortNs:vlanCompOffLimit
        managed object property"
    ::= { cfprApSwVlanPortNsEntry 11 }

cfprApSwVlanPortNsVlanCompOnLimit OBJECT-TYPE
    SYNTAX       Gauge32
    MAX-ACCESS   read-only
    STATUS       current
    DESCRIPTION
        "Cisco Firepower sw:VlanPortNs:vlanCompOnLimit
        managed object property"
    ::= { cfprApSwVlanPortNsEntry 12 }

cfprApSwVlanPortNsOverrideTable OBJECT-TYPE
    SYNTAX           SEQUENCE OF CfprApSwVlanPortNsOverrideEntry
    MAX-ACCESS       not-accessible
    STATUS           current
    DESCRIPTION
        "Cisco Firepower sw:VlanPortNsOverride managed object table"
    ::= { cfprApSwObjects 95 }

cfprApSwVlanPortNsOverrideEntry OBJECT-TYPE
    SYNTAX           CfprApSwVlanPortNsOverrideEntry
    MAX-ACCESS       not-accessible
    STATUS           current
    DESCRIPTION
        "Entry for the cfprApSwVlanPortNsOverrideTable table."
    INDEX { cfprApSwVlanPortNsOverrideInstanceId }
    ::= { cfprApSwVlanPortNsOverrideTable 1 }

CfprApSwVlanPortNsOverrideEntry ::= SEQUENCE {
    cfprApSwVlanPortNsOverrideInstanceId                             CfprApManagedObjectId,
    cfprApSwVlanPortNsOverrideDn                                     CfprApManagedObjectDn,
    cfprApSwVlanPortNsOverrideRn                                     SnmpAdminString,
    cfprApSwVlanPortNsOverrideLimit                                  Gauge32
}

cfprApSwVlanPortNsOverrideInstanceId OBJECT-TYPE
    SYNTAX       CfprApManagedObjectId
    MAX-ACCESS   not-accessible
    STATUS       current
    DESCRIPTION
        "Instance identifier of the managed object."
    ::= { cfprApSwVlanPortNsOverrideEntry 1 }

cfprApSwVlanPortNsOverrideDn OBJECT-TYPE
    SYNTAX       CfprApManagedObjectDn
    MAX-ACCESS   read-only
    STATUS       current
    DESCRIPTION
        "Cisco Firepower sw:VlanPortNsOverride:dn managed object property"
    ::= { cfprApSwVlanPortNsOverrideEntry 2 }

cfprApSwVlanPortNsOverrideRn OBJECT-TYPE
    SYNTAX       SnmpAdminString
    MAX-ACCESS   read-only
    STATUS       current
    DESCRIPTION
        "Cisco Firepower sw:VlanPortNsOverride:rn managed object property"
    ::= { cfprApSwVlanPortNsOverrideEntry 3 }

cfprApSwVlanPortNsOverrideLimit OBJECT-TYPE
    SYNTAX       Gauge32
    MAX-ACCESS   read-only
    STATUS       current
    DESCRIPTION
        "Cisco Firepower sw:VlanPortNsOverride:limit managed
        object property"
    ::= { cfprApSwVlanPortNsOverrideEntry 4 }

cfprApSwVlanRefTable OBJECT-TYPE
    SYNTAX           SEQUENCE OF CfprApSwVlanRefEntry
    MAX-ACCESS       not-accessible
    STATUS           current
    DESCRIPTION
        "Cisco Firepower sw:VlanRef managed object table"
    ::= { cfprApSwObjects 96 }

cfprApSwVlanRefEntry OBJECT-TYPE
    SYNTAX           CfprApSwVlanRefEntry
    MAX-ACCESS       not-accessible
    STATUS           current
    DESCRIPTION
        "Entry for the cfprApSwVlanRefTable table."
    INDEX { cfprApSwVlanRefInstanceId }
    ::= { cfprApSwVlanRefTable 1 }

CfprApSwVlanRefEntry ::= SEQUENCE {
    cfprApSwVlanRefInstanceId                                        CfprApManagedObjectId,
    cfprApSwVlanRefDn                                                CfprApManagedObjectDn,
    cfprApSwVlanRefRn                                                SnmpAdminString,
    cfprApSwVlanRefCompressionType                                   CfprApSwVlanCompType,
    cfprApSwVlanRefConfigStatus                                      CfprApSwVlanConfigStatusType,
    cfprApSwVlanRefId                                                Gauge32,
    cfprApSwVlanRefPeerDn                                            SnmpAdminString
}

cfprApSwVlanRefInstanceId OBJECT-TYPE
    SYNTAX       CfprApManagedObjectId
    MAX-ACCESS   not-accessible
    STATUS       current
    DESCRIPTION
        "Instance identifier of the managed object."
    ::= { cfprApSwVlanRefEntry 1 }

cfprApSwVlanRefDn OBJECT-TYPE
    SYNTAX       CfprApManagedObjectDn
    MAX-ACCESS   read-only
    STATUS       current
    DESCRIPTION
        "Cisco Firepower sw:VlanRef:dn managed object property"
    ::= { cfprApSwVlanRefEntry 2 }

cfprApSwVlanRefRn OBJECT-TYPE
    SYNTAX       SnmpAdminString
    MAX-ACCESS   read-only
    STATUS       current
    DESCRIPTION
        "Cisco Firepower sw:VlanRef:rn managed object property"
    ::= { cfprApSwVlanRefEntry 3 }

cfprApSwVlanRefCompressionType OBJECT-TYPE
    SYNTAX       CfprApSwVlanCompType
    MAX-ACCESS   read-only
    STATUS       current
    DESCRIPTION
        "Cisco Firepower sw:VlanRef:compressionType managed
        object property"
    ::= { cfprApSwVlanRefEntry 4 }

cfprApSwVlanRefConfigStatus OBJECT-TYPE
    SYNTAX       CfprApSwVlanConfigStatusType
    MAX-ACCESS   read-only
    STATUS       current
    DESCRIPTION
        "Cisco Firepower sw:VlanRef:configStatus managed object property"
    ::= { cfprApSwVlanRefEntry 5 }

cfprApSwVlanRefId OBJECT-TYPE
    SYNTAX       Gauge32
    MAX-ACCESS   read-only
    STATUS       current
    DESCRIPTION
        "Cisco Firepower sw:VlanRef:id managed object property"
    ::= { cfprApSwVlanRefEntry 6 }

cfprApSwVlanRefPeerDn OBJECT-TYPE
    SYNTAX       SnmpAdminString
    MAX-ACCESS   read-only
    STATUS       current
    DESCRIPTION
        "Cisco Firepower sw:VlanRef:peerDn managed object property"
    ::= { cfprApSwVlanRefEntry 7 }

cfprApSwVsanTable OBJECT-TYPE
    SYNTAX           SEQUENCE OF CfprApSwVsanEntry
    MAX-ACCESS       not-accessible
    STATUS           current
    DESCRIPTION
        "Cisco Firepower sw:Vsan managed object table"
    ::= { cfprApSwObjects 97 }

cfprApSwVsanEntry OBJECT-TYPE
    SYNTAX           CfprApSwVsanEntry
    MAX-ACCESS       not-accessible
    STATUS           current
    DESCRIPTION
        "Entry for the cfprApSwVsanTable table."
    INDEX { cfprApSwVsanInstanceId }
    ::= { cfprApSwVsanTable 1 }

CfprApSwVsanEntry ::= SEQUENCE {
    cfprApSwVsanInstanceId                                           CfprApManagedObjectId,
    cfprApSwVsanDn                                                   CfprApManagedObjectDn,
    cfprApSwVsanRn                                                   SnmpAdminString,
    cfprApSwVsanDefaultZoning                                        CfprApFabricDefaultZoningState,
    cfprApSwVsanEpDn                                                 SnmpAdminString,
    cfprApSwVsanFcZoneSharingMode                                    CfprApFabricFcZoneSharingMode,
    cfprApSwVsanFcoeVlan                                             Gauge32,
    cfprApSwVsanFltAggr                                              Unsigned64,
    cfprApSwVsanId                                                   Gauge32,
    cfprApSwVsanIfRole                                               CfprApFabricVnetEpIfRole,
    cfprApSwVsanIfType                                               CfprApNetworkVnetEpIfType,
    cfprApSwVsanLc                                                   CfprApFsmLifecycle,
    cfprApSwVsanLocale                                               CfprApFabricVnetEpLocale,
    cfprApSwVsanMonTrafDir                                           CfprApFabricTrafficDirection,
    cfprApSwVsanName                                                 SnmpAdminString,
    cfprApSwVsanOperState                                            CfprApFabricVsanOperState,
    cfprApSwVsanPeerDn                                               SnmpAdminString,
    cfprApSwVsanPolicyOwner                                          CfprApFabricVnetEpPolicyOwner,
    cfprApSwVsanSwitchId                                             CfprApNetworkSwitchId,
    cfprApSwVsanTransport                                            CfprApFabricAVsanTransport,
    cfprApSwVsanType                                                 CfprApFabricAVsanType,
    cfprApSwVsanZoningState                                          CfprApFabricZoningState
}

cfprApSwVsanInstanceId OBJECT-TYPE
    SYNTAX       CfprApManagedObjectId
    MAX-ACCESS   not-accessible
    STATUS       current
    DESCRIPTION
        "Instance identifier of the managed object."
    ::= { cfprApSwVsanEntry 1 }

cfprApSwVsanDn OBJECT-TYPE
    SYNTAX       CfprApManagedObjectDn
    MAX-ACCESS   read-only
    STATUS       current
    DESCRIPTION
        "Cisco Firepower sw:Vsan:dn managed object property"
    ::= { cfprApSwVsanEntry 2 }

cfprApSwVsanRn OBJECT-TYPE
    SYNTAX       SnmpAdminString
    MAX-ACCESS   read-only
    STATUS       current
    DESCRIPTION
        "Cisco Firepower sw:Vsan:rn managed object property"
    ::= { cfprApSwVsanEntry 3 }

cfprApSwVsanDefaultZoning OBJECT-TYPE
    SYNTAX       CfprApFabricDefaultZoningState
    MAX-ACCESS   read-only
    STATUS       current
    DESCRIPTION
        "Cisco Firepower sw:Vsan:defaultZoning managed object property"
    ::= { cfprApSwVsanEntry 4 }

cfprApSwVsanEpDn OBJECT-TYPE
    SYNTAX       SnmpAdminString
    MAX-ACCESS   read-only
    STATUS       current
    DESCRIPTION
        "Cisco Firepower sw:Vsan:epDn managed object property"
    ::= { cfprApSwVsanEntry 5 }

cfprApSwVsanFcZoneSharingMode OBJECT-TYPE
    SYNTAX       CfprApFabricFcZoneSharingMode
    MAX-ACCESS   read-only
    STATUS       current
    DESCRIPTION
        "Cisco Firepower sw:Vsan:fcZoneSharingMode managed
        object property"
    ::= { cfprApSwVsanEntry 6 }

cfprApSwVsanFcoeVlan OBJECT-TYPE
    SYNTAX       Gauge32
    MAX-ACCESS   read-only
    STATUS       current
    DESCRIPTION
        "Cisco Firepower sw:Vsan:fcoeVlan managed object property"
    ::= { cfprApSwVsanEntry 7 }

cfprApSwVsanFltAggr OBJECT-TYPE
    SYNTAX       Unsigned64
    MAX-ACCESS   read-only
    STATUS       current
    DESCRIPTION
        "Cisco Firepower sw:Vsan:fltAggr managed object property"
    ::= { cfprApSwVsanEntry 8 }

cfprApSwVsanId OBJECT-TYPE
    SYNTAX       Gauge32
    MAX-ACCESS   read-only
    STATUS       current
    DESCRIPTION
        "Cisco Firepower sw:Vsan:id managed object property"
    ::= { cfprApSwVsanEntry 9 }

cfprApSwVsanIfRole OBJECT-TYPE
    SYNTAX       CfprApFabricVnetEpIfRole
    MAX-ACCESS   read-only
    STATUS       current
    DESCRIPTION
        "Cisco Firepower sw:Vsan:ifRole managed object property"
    ::= { cfprApSwVsanEntry 10 }

cfprApSwVsanIfType OBJECT-TYPE
    SYNTAX       CfprApNetworkVnetEpIfType
    MAX-ACCESS   read-only
    STATUS       current
    DESCRIPTION
        "Cisco Firepower sw:Vsan:ifType managed object property"
    ::= { cfprApSwVsanEntry 11 }

cfprApSwVsanLc OBJECT-TYPE
    SYNTAX       CfprApFsmLifecycle
    MAX-ACCESS   read-only
    STATUS       current
    DESCRIPTION
        "Cisco Firepower sw:Vsan:lc managed object property"
    ::= { cfprApSwVsanEntry 12 }

cfprApSwVsanLocale OBJECT-TYPE
    SYNTAX       CfprApFabricVnetEpLocale
    MAX-ACCESS   read-only
    STATUS       current
    DESCRIPTION
        "Cisco Firepower sw:Vsan:locale managed object property"
    ::= { cfprApSwVsanEntry 13 }

cfprApSwVsanMonTrafDir OBJECT-TYPE
    SYNTAX       CfprApFabricTrafficDirection
    MAX-ACCESS   read-only
    STATUS       current
    DESCRIPTION
        "Cisco Firepower sw:Vsan:monTrafDir managed object property"
    ::= { cfprApSwVsanEntry 14 }

cfprApSwVsanName OBJECT-TYPE
    SYNTAX       SnmpAdminString
    MAX-ACCESS   read-only
    STATUS       current
    DESCRIPTION
        "Cisco Firepower sw:Vsan:name managed object property"
    ::= { cfprApSwVsanEntry 15 }

cfprApSwVsanOperState OBJECT-TYPE
    SYNTAX       CfprApFabricVsanOperState
    MAX-ACCESS   read-only
    STATUS       current
    DESCRIPTION
        "Cisco Firepower sw:Vsan:operState managed object property"
    ::= { cfprApSwVsanEntry 16 }

cfprApSwVsanPeerDn OBJECT-TYPE
    SYNTAX       SnmpAdminString
    MAX-ACCESS   read-only
    STATUS       current
    DESCRIPTION
        "Cisco Firepower sw:Vsan:peerDn managed object property"
    ::= { cfprApSwVsanEntry 17 }

cfprApSwVsanPolicyOwner OBJECT-TYPE
    SYNTAX       CfprApFabricVnetEpPolicyOwner
    MAX-ACCESS   read-only
    STATUS       current
    DESCRIPTION
        "Cisco Firepower sw:Vsan:policyOwner managed object property"
    ::= { cfprApSwVsanEntry 18 }

cfprApSwVsanSwitchId OBJECT-TYPE
    SYNTAX       CfprApNetworkSwitchId
    MAX-ACCESS   read-only
    STATUS       current
    DESCRIPTION
        "Cisco Firepower sw:Vsan:switchId managed object property"
    ::= { cfprApSwVsanEntry 19 }

cfprApSwVsanTransport OBJECT-TYPE
    SYNTAX       CfprApFabricAVsanTransport
    MAX-ACCESS   read-only
    STATUS       current
    DESCRIPTION
        "Cisco Firepower sw:Vsan:transport managed object property"
    ::= { cfprApSwVsanEntry 20 }

cfprApSwVsanType OBJECT-TYPE
    SYNTAX       CfprApFabricAVsanType
    MAX-ACCESS   read-only
    STATUS       current
    DESCRIPTION
        "Cisco Firepower sw:Vsan:type managed object property"
    ::= { cfprApSwVsanEntry 21 }

cfprApSwVsanZoningState OBJECT-TYPE
    SYNTAX       CfprApFabricZoningState
    MAX-ACCESS   read-only
    STATUS       current
    DESCRIPTION
        "Cisco Firepower sw:Vsan:zoningState managed object property"
    ::= { cfprApSwVsanEntry 22 }

cfprApSwZoneInitiatorMemberTable OBJECT-TYPE
    SYNTAX           SEQUENCE OF CfprApSwZoneInitiatorMemberEntry
    MAX-ACCESS       not-accessible
    STATUS           current
    DESCRIPTION
        "Cisco Firepower sw:ZoneInitiatorMember managed object table"
    ::= { cfprApSwObjects 98 }

cfprApSwZoneInitiatorMemberEntry OBJECT-TYPE
    SYNTAX           CfprApSwZoneInitiatorMemberEntry
    MAX-ACCESS       not-accessible
    STATUS           current
    DESCRIPTION
        "Entry for the cfprApSwZoneInitiatorMemberTable table."
    INDEX { cfprApSwZoneInitiatorMemberInstanceId }
    ::= { cfprApSwZoneInitiatorMemberTable 1 }

CfprApSwZoneInitiatorMemberEntry ::= SEQUENCE {
    cfprApSwZoneInitiatorMemberInstanceId                            CfprApManagedObjectId,
    cfprApSwZoneInitiatorMemberDn                                    CfprApManagedObjectDn,
    cfprApSwZoneInitiatorMemberRn                                    SnmpAdminString,
    cfprApSwZoneInitiatorMemberEpDn                                  SnmpAdminString,
    cfprApSwZoneInitiatorMemberLc                                    CfprApSwFcZoneMemberLc,
    cfprApSwZoneInitiatorMemberName                                  SnmpAdminString,
    cfprApSwZoneInitiatorMemberPeerDn                                SnmpAdminString,
    cfprApSwZoneInitiatorMemberWwpn                                  Unsigned64
}

cfprApSwZoneInitiatorMemberInstanceId OBJECT-TYPE
    SYNTAX       CfprApManagedObjectId
    MAX-ACCESS   not-accessible
    STATUS       current
    DESCRIPTION
        "Instance identifier of the managed object."
    ::= { cfprApSwZoneInitiatorMemberEntry 1 }

cfprApSwZoneInitiatorMemberDn OBJECT-TYPE
    SYNTAX       CfprApManagedObjectDn
    MAX-ACCESS   read-only
    STATUS       current
    DESCRIPTION
        "Cisco Firepower sw:ZoneInitiatorMember:dn managed
        object property"
    ::= { cfprApSwZoneInitiatorMemberEntry 2 }

cfprApSwZoneInitiatorMemberRn OBJECT-TYPE
    SYNTAX       SnmpAdminString
    MAX-ACCESS   read-only
    STATUS       current
    DESCRIPTION
        "Cisco Firepower sw:ZoneInitiatorMember:rn managed
        object property"
    ::= { cfprApSwZoneInitiatorMemberEntry 3 }

cfprApSwZoneInitiatorMemberEpDn OBJECT-TYPE
    SYNTAX       SnmpAdminString
    MAX-ACCESS   read-only
    STATUS       current
    DESCRIPTION
        "Cisco Firepower sw:ZoneInitiatorMember:epDn managed
        object property"
    ::= { cfprApSwZoneInitiatorMemberEntry 4 }

cfprApSwZoneInitiatorMemberLc OBJECT-TYPE
    SYNTAX       CfprApSwFcZoneMemberLc
    MAX-ACCESS   read-only
    STATUS       current
    DESCRIPTION
        "Cisco Firepower sw:ZoneInitiatorMember:lc managed
        object property"
    ::= { cfprApSwZoneInitiatorMemberEntry 5 }

cfprApSwZoneInitiatorMemberName OBJECT-TYPE
    SYNTAX       SnmpAdminString
    MAX-ACCESS   read-only
    STATUS       current
    DESCRIPTION
        "Cisco Firepower sw:ZoneInitiatorMember:name managed
        object property"
    ::= { cfprApSwZoneInitiatorMemberEntry 6 }

cfprApSwZoneInitiatorMemberPeerDn OBJECT-TYPE
    SYNTAX       SnmpAdminString
    MAX-ACCESS   read-only
    STATUS       current
    DESCRIPTION
        "Cisco Firepower sw:ZoneInitiatorMember:peerDn
        managed object property"
    ::= { cfprApSwZoneInitiatorMemberEntry 7 }

cfprApSwZoneInitiatorMemberWwpn OBJECT-TYPE
    SYNTAX       Unsigned64
    MAX-ACCESS   read-only
    STATUS       current
    DESCRIPTION
        "Cisco Firepower sw:ZoneInitiatorMember:wwpn managed
        object property"
    ::= { cfprApSwZoneInitiatorMemberEntry 8 }

cfprApSwZoneTargetMemberTable OBJECT-TYPE
    SYNTAX           SEQUENCE OF CfprApSwZoneTargetMemberEntry
    MAX-ACCESS       not-accessible
    STATUS           current
    DESCRIPTION
        "Cisco Firepower sw:ZoneTargetMember managed object table"
    ::= { cfprApSwObjects 99 }

cfprApSwZoneTargetMemberEntry OBJECT-TYPE
    SYNTAX           CfprApSwZoneTargetMemberEntry
    MAX-ACCESS       not-accessible
    STATUS           current
    DESCRIPTION
        "Entry for the cfprApSwZoneTargetMemberTable table."
    INDEX { cfprApSwZoneTargetMemberInstanceId }
    ::= { cfprApSwZoneTargetMemberTable 1 }

CfprApSwZoneTargetMemberEntry ::= SEQUENCE {
    cfprApSwZoneTargetMemberInstanceId                               CfprApManagedObjectId,
    cfprApSwZoneTargetMemberDn                                       CfprApManagedObjectDn,
    cfprApSwZoneTargetMemberRn                                       SnmpAdminString,
    cfprApSwZoneTargetMemberEpDn                                     SnmpAdminString,
    cfprApSwZoneTargetMemberLc                                       CfprApSwFcZoneMemberLc,
    cfprApSwZoneTargetMemberName                                     SnmpAdminString,
    cfprApSwZoneTargetMemberPeerDn                                   SnmpAdminString,
    cfprApSwZoneTargetMemberWwpn                                     Unsigned64
}

cfprApSwZoneTargetMemberInstanceId OBJECT-TYPE
    SYNTAX       CfprApManagedObjectId
    MAX-ACCESS   not-accessible
    STATUS       current
    DESCRIPTION
        "Instance identifier of the managed object."
    ::= { cfprApSwZoneTargetMemberEntry 1 }

cfprApSwZoneTargetMemberDn OBJECT-TYPE
    SYNTAX       CfprApManagedObjectDn
    MAX-ACCESS   read-only
    STATUS       current
    DESCRIPTION
        "Cisco Firepower sw:ZoneTargetMember:dn managed object property"
    ::= { cfprApSwZoneTargetMemberEntry 2 }

cfprApSwZoneTargetMemberRn OBJECT-TYPE
    SYNTAX       SnmpAdminString
    MAX-ACCESS   read-only
    STATUS       current
    DESCRIPTION
        "Cisco Firepower sw:ZoneTargetMember:rn managed object property"
    ::= { cfprApSwZoneTargetMemberEntry 3 }

cfprApSwZoneTargetMemberEpDn OBJECT-TYPE
    SYNTAX       SnmpAdminString
    MAX-ACCESS   read-only
    STATUS       current
    DESCRIPTION
        "Cisco Firepower sw:ZoneTargetMember:epDn managed object property"
    ::= { cfprApSwZoneTargetMemberEntry 4 }

cfprApSwZoneTargetMemberLc OBJECT-TYPE
    SYNTAX       CfprApSwFcZoneMemberLc
    MAX-ACCESS   read-only
    STATUS       current
    DESCRIPTION
        "Cisco Firepower sw:ZoneTargetMember:lc managed object property"
    ::= { cfprApSwZoneTargetMemberEntry 5 }

cfprApSwZoneTargetMemberName OBJECT-TYPE
    SYNTAX       SnmpAdminString
    MAX-ACCESS   read-only
    STATUS       current
    DESCRIPTION
        "Cisco Firepower sw:ZoneTargetMember:name managed object property"
    ::= { cfprApSwZoneTargetMemberEntry 6 }

cfprApSwZoneTargetMemberPeerDn OBJECT-TYPE
    SYNTAX       SnmpAdminString
    MAX-ACCESS   read-only
    STATUS       current
    DESCRIPTION
        "Cisco Firepower sw:ZoneTargetMember:peerDn managed
        object property"
    ::= { cfprApSwZoneTargetMemberEntry 7 }

cfprApSwZoneTargetMemberWwpn OBJECT-TYPE
    SYNTAX       Unsigned64
    MAX-ACCESS   read-only
    STATUS       current
    DESCRIPTION
        "Cisco Firepower sw:ZoneTargetMember:wwpn managed object property"
    ::= { cfprApSwZoneTargetMemberEntry 8 }

END
