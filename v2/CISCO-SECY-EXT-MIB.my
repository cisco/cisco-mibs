-- *****************************************************************
-- CISCO-SECY-EXT-MIB.my
--   
-- Abhinand Chidu Velekkat
--   
-- Copyright (c) 2016-2017, 2025-2026 by cisco Systems Inc.
-- All rights reserved.
-- *****************************************************************

CISCO-SECY-EXT-MIB DEFINITIONS ::= BEGIN

IMPORTS
    MODULE-IDENTITY,
    OBJECT-TYPE,
    Counter64
        FROM SNMPv2-SMI
    MODULE-COMPLIANCE,
    OBJECT-GROUP
        FROM SNMPv2-CONF
    DisplayString
        FROM SNMPv2-TC
    secyIfInterfaceIndex,
    secyRxSAEntry,
    secyTxSAEntry
        FROM IEEE8021-SECY-MIB
    CounterBasedGauge64
        FROM HCNUM-TC
    ciscoMgmt
        FROM CISCO-SMI;


ciscoSecyExtMIB MODULE-IDENTITY
    LAST-UPDATED    "202602080000Z"
    ORGANIZATION    "Cisco Systems, Inc."
    CONTACT-INFO
            "Cisco Systems
            Customer Service

            Postal: 170 W Tasman Drive
            San Jose, CA  95134
            USA

            Tel: +1 800 553-NETS

            E-mail: cs-snmp@cisco.com"
    DESCRIPTION
        "A MIB module for extending IEEE8021-SECY-MIB."
    REVISION        "202602080000Z"
    DESCRIPTION
        "Added cseSecySessionTable for MACSEC session state monitoring.
        Provides OIDs to monitor the operational status of MACSEC sessions
        (up, down, negotiating)."
    REVISION        "202510130000Z"
    DESCRIPTION
        "Added total controlled packet counters for both RX and TX
        interfaces:
        - cseSecyIfRxControlledPkts
        - cseSecyIfTxControlledPkts"
    REVISION        "201702150000Z"
    DESCRIPTION
        "Add cseSecyRxSAStatsGroup and cseSecyTxSAStatsGroup."
    REVISION        "201612150000Z"
    DESCRIPTION
        "Initial version of this MIB module."
    ::= { ciscoMgmt 835 }


ciscoSecyExtMIBNotifs  OBJECT IDENTIFIER
    ::= { ciscoSecyExtMIB 0 }

ciscoSecyExtMIBObjects  OBJECT IDENTIFIER
    ::= { ciscoSecyExtMIB 1 }

ciscoSecyExtMIBStatsObjects  OBJECT IDENTIFIER
    ::= { ciscoSecyExtMIBObjects 1 }

ciscoSecyExtMIBConform  OBJECT IDENTIFIER
    ::= { ciscoSecyExtMIB 2 }


cseSecyStatsExtTable OBJECT-TYPE
    SYNTAX          SEQUENCE OF CseSecyStatsExtEntry 
    MAX-ACCESS      not-accessible
    STATUS          current
    DESCRIPTION
        "This table provides the additional statistics information
        of each SecY supported by the MAC security entity."
    ::= { ciscoSecyExtMIBStatsObjects 1 }

cseSecyStatsExtEntry OBJECT-TYPE
    SYNTAX          CseSecyStatsExtEntry
    MAX-ACCESS      not-accessible
    STATUS          current
    DESCRIPTION
        "An entry containing counters for statistics or diagnosis for
        a SecY."
    INDEX           { secyIfInterfaceIndex } 
    ::= { cseSecyStatsExtTable 1 }

CseSecyStatsExtEntry ::= SEQUENCE {
        cseSecyStatsRxTransformErrPkts Counter64,
        cseSecyStatsRxControlPkts      Counter64,
        cseSecyStatsRxTaggedCtrlPkts   Counter64,
        cseSecyStatsTxTransformErrPkts Counter64,
        cseSecyStatsTxControlPkts      Counter64
}

cseSecyStatsRxTransformErrPkts OBJECT-TYPE
    SYNTAX          Counter64
    MAX-ACCESS      read-only
    STATUS          current
    DESCRIPTION
        "The number of transform error packets received on this
        interface." 
    ::= { cseSecyStatsExtEntry 1 }

cseSecyStatsRxControlPkts OBJECT-TYPE
    SYNTAX          Counter64
    MAX-ACCESS      read-only
    STATUS          current
    DESCRIPTION
        "The number of control packets received on this interface." 
    ::= { cseSecyStatsExtEntry 2 }

cseSecyStatsRxTaggedCtrlPkts OBJECT-TYPE
    SYNTAX          Counter64
    MAX-ACCESS      read-only
    STATUS          current
    DESCRIPTION
        "The number of tagged control packets received on this
        interface." 
    ::= { cseSecyStatsExtEntry 3 }

cseSecyStatsTxTransformErrPkts OBJECT-TYPE
    SYNTAX          Counter64
    MAX-ACCESS      read-only
    STATUS          current
    DESCRIPTION
        "The number of tranform error packets transmitted via this
        interface." 
    ::= { cseSecyStatsExtEntry 4 }

cseSecyStatsTxControlPkts OBJECT-TYPE
    SYNTAX          Counter64
    MAX-ACCESS      read-only
    STATUS          current
    DESCRIPTION
        "The number of control packets transmitted via this interface." 
    ::= { cseSecyStatsExtEntry 5 }
 


cseSecyTxSCStatsExtTable OBJECT-TYPE
    SYNTAX          SEQUENCE OF CseSecyTxSCStatsExtEntry 
    MAX-ACCESS      not-accessible
    STATUS          current
    DESCRIPTION
        "A table contains additional statistics information for each
        transmitting SC in the MAC security entity."
    ::= { ciscoSecyExtMIBStatsObjects 2 }

cseSecyTxSCStatsExtEntry OBJECT-TYPE
    SYNTAX          CseSecyTxSCStatsExtEntry
    MAX-ACCESS      not-accessible
    STATUS          current
    DESCRIPTION
        "An entry containing statistics information of a
        transmitting SC."
    INDEX           { secyIfInterfaceIndex } 
    ::= { cseSecyTxSCStatsExtTable 1 }

CseSecyTxSCStatsExtEntry ::= SEQUENCE {
        cseSecyTxSCStatsSANotInUse Counter64
}

cseSecyTxSCStatsSANotInUse OBJECT-TYPE
    SYNTAX          Counter64
    MAX-ACCESS      read-only
    STATUS          current
    DESCRIPTION
        "The number of SA not in use for this transmitting SC." 
    ::= { cseSecyTxSCStatsExtEntry 1 }
 


cseSecyIfRxStatsTable OBJECT-TYPE
    SYNTAX          SEQUENCE OF CseSecyIfRxStatsEntry 
    MAX-ACCESS      not-accessible
    STATUS          current
    DESCRIPTION
        "A table contains the RX statistics information for each
        MAC security capable interface."
    ::= { ciscoSecyExtMIBStatsObjects 3 }

cseSecyIfRxStatsEntry OBJECT-TYPE
    SYNTAX          CseSecyIfRxStatsEntry
    MAX-ACCESS      not-accessible
    STATUS          current
    DESCRIPTION
        "An entry containing the RX statistics information of a
        MAC Security capable interface."
    INDEX           { secyIfInterfaceIndex } 
    ::= { cseSecyIfRxStatsTable 1 }

CseSecyIfRxStatsEntry ::= SEQUENCE {
        cseSecyIfRxUnicastUncontrolledPkts   Counter64,
        cseSecyIfRxMulticastUncontrolledPkts Counter64,
        cseSecyIfRxBroadcastUncontrolledPkts Counter64,
        cseSecyIfRxUncontrolledPktsDrop      Counter64,
        cseSecyIfRxUncontrolledPktsError     Counter64,
        cseSecyIfRxUnicastControlledPkts     Counter64,
        cseSecyIfRxMulticastControlledPkts   Counter64,
        cseSecyIfRxBroadcastControlledPkts   Counter64,
        cseSecyIfRxControlledPktsDrop        Counter64,
        cseSecyIfRxControlledPktsError       Counter64,
        cseSecyIfRxUncontrolledOctets        Counter64,
        cseSecyIfRxControlledOctets          Counter64,
        cseSecyIfRxUncontrolledPktRate       CounterBasedGauge64,
        cseSecyIfRxUncontrolledOctetRate     CounterBasedGauge64,
        cseSecyIfRxControlledPktRate         CounterBasedGauge64,
        cseSecyIfRxControlledOctetRate       CounterBasedGauge64,
        cseSecyIfRxControlledPkts            Counter64
}

cseSecyIfRxUnicastUncontrolledPkts OBJECT-TYPE
    SYNTAX          Counter64
    MAX-ACCESS      read-only
    STATUS          current
    DESCRIPTION
        "The number of unicast uncontrolled packets received via this
        interface." 
    ::= { cseSecyIfRxStatsEntry 1 }

cseSecyIfRxMulticastUncontrolledPkts OBJECT-TYPE
    SYNTAX          Counter64
    MAX-ACCESS      read-only
    STATUS          current
    DESCRIPTION
        "The number of multicast uncontrolled packets received via this
        interface." 
    ::= { cseSecyIfRxStatsEntry 2 }

cseSecyIfRxBroadcastUncontrolledPkts OBJECT-TYPE
    SYNTAX          Counter64
    MAX-ACCESS      read-only
    STATUS          current
    DESCRIPTION
        "The number of broadcast uncontrolled packets received via this
        interface." 
    ::= { cseSecyIfRxStatsEntry 3 }

cseSecyIfRxUncontrolledPktsDrop OBJECT-TYPE
    SYNTAX          Counter64
    MAX-ACCESS      read-only
    STATUS          current
    DESCRIPTION
        "The number of uncontrolled packets drop received via this
        interface." 
    ::= { cseSecyIfRxStatsEntry 4 }

cseSecyIfRxUncontrolledPktsError OBJECT-TYPE
    SYNTAX          Counter64
    MAX-ACCESS      read-only
    STATUS          current
    DESCRIPTION
        "The number of uncontrolled packets error received via this
        interface." 
    ::= { cseSecyIfRxStatsEntry 5 }

cseSecyIfRxUnicastControlledPkts OBJECT-TYPE
    SYNTAX          Counter64
    MAX-ACCESS      read-only
    STATUS          current
    DESCRIPTION
        "The number of unicast controlled packets received via this
        interface." 
    ::= { cseSecyIfRxStatsEntry 6 }

cseSecyIfRxMulticastControlledPkts OBJECT-TYPE
    SYNTAX          Counter64
    MAX-ACCESS      read-only
    STATUS          current
    DESCRIPTION
        "The number of multicast controlled packets received via this
        interface." 
    ::= { cseSecyIfRxStatsEntry 7 }

cseSecyIfRxBroadcastControlledPkts OBJECT-TYPE
    SYNTAX          Counter64
    MAX-ACCESS      read-only
    STATUS          current
    DESCRIPTION
        "The number of broadcast controlled packets received via this
        interface." 
    ::= { cseSecyIfRxStatsEntry 8 }

cseSecyIfRxControlledPktsDrop OBJECT-TYPE
    SYNTAX          Counter64
    MAX-ACCESS      read-only
    STATUS          current
    DESCRIPTION
        "The number of controlled packets drop received via this
        interface." 
    ::= { cseSecyIfRxStatsEntry 9 }

cseSecyIfRxControlledPktsError OBJECT-TYPE
    SYNTAX          Counter64
    MAX-ACCESS      read-only
    STATUS          current
    DESCRIPTION
        "The number of controlled packets error received via this
        interface." 
    ::= { cseSecyIfRxStatsEntry 10 }

cseSecyIfRxUncontrolledOctets OBJECT-TYPE
    SYNTAX          Counter64
    MAX-ACCESS      read-only
    STATUS          current
    DESCRIPTION
        "The number of uncontrolled octets received via this
        interface." 
    ::= { cseSecyIfRxStatsEntry 11 }

cseSecyIfRxControlledOctets OBJECT-TYPE
    SYNTAX          Counter64
    MAX-ACCESS      read-only
    STATUS          current
    DESCRIPTION
        "The number of controlled octets received via this interface." 
    ::= { cseSecyIfRxStatsEntry 12 }

cseSecyIfRxUncontrolledPktRate OBJECT-TYPE
    SYNTAX          CounterBasedGauge64
    UNITS           "Packets per second"
    MAX-ACCESS      read-only
    STATUS          current
    DESCRIPTION
        "The number of uncontrolled packets per second received via this
        interface." 
    ::= { cseSecyIfRxStatsEntry 13 }

cseSecyIfRxUncontrolledOctetRate OBJECT-TYPE
    SYNTAX          CounterBasedGauge64
    UNITS           "Bytes per second"
    MAX-ACCESS      read-only
    STATUS          current
    DESCRIPTION
        "The number of uncontrolled byte per second received via this
        interface." 
    ::= { cseSecyIfRxStatsEntry 14 }

cseSecyIfRxControlledPktRate OBJECT-TYPE
    SYNTAX          CounterBasedGauge64
    UNITS           "Packets per second"
    MAX-ACCESS      read-only
    STATUS          current
    DESCRIPTION
        "The number of controlled packets per second received via this
        interface." 
    ::= { cseSecyIfRxStatsEntry 15 }

cseSecyIfRxControlledOctetRate OBJECT-TYPE
    SYNTAX          CounterBasedGauge64
    UNITS           "Bytes per second"
    MAX-ACCESS      read-only
    STATUS          current
    DESCRIPTION
        "The number of controlled byte per second received via this
        interface." 
    ::= { cseSecyIfRxStatsEntry 16 }

cseSecyIfRxControlledPkts OBJECT-TYPE
    SYNTAX          Counter64
    MAX-ACCESS      read-only
    STATUS          current
    DESCRIPTION
        "The total number of controlled packets received via this
        interface." 
    ::= { cseSecyIfRxStatsEntry 17 }
 


cseSecyIfTxStatsTable OBJECT-TYPE
    SYNTAX          SEQUENCE OF CseSecyIfTxStatsEntry 
    MAX-ACCESS      not-accessible
    STATUS          current
    DESCRIPTION
        "A table contains the TX statistics information for each
        MAC security capable interface."
    ::= { ciscoSecyExtMIBStatsObjects 4 }

cseSecyIfTxStatsEntry OBJECT-TYPE
    SYNTAX          CseSecyIfTxStatsEntry
    MAX-ACCESS      not-accessible
    STATUS          current
    DESCRIPTION
        "An entry containing the TX statistics information of a
        MAC Security capable interface."
    INDEX           { secyIfInterfaceIndex } 
    ::= { cseSecyIfTxStatsTable 1 }

CseSecyIfTxStatsEntry ::= SEQUENCE {
        cseSecyIfTxUnicastUncontrolledPkts   Counter64,
        cseSecyIfTxMulticastUncontrolledPkts Counter64,
        cseSecyIfTxBroadcastUncontrolledPkts Counter64,
        cseSecyIfTxUncontrolledPktsDrop      Counter64,
        cseSecyIfTxUncontrolledPktsError     Counter64,
        cseSecyIfTxUnicastControlledPkts     Counter64,
        cseSecyIfTxMulticastControlledPkts   Counter64,
        cseSecyIfTxBroadcastControlledPkts   Counter64,
        cseSecyIfTxControlledPktsDrop        Counter64,
        cseSecyIfTxControlledPktsError       Counter64,
        cseSecyIfTxUncontrolledOctets        Counter64,
        cseSecyIfTxControlledOctets          Counter64,
        cseSecyIfTxCommonOctets              Counter64,
        cseSecyIfTxUncontrolledPktRate       CounterBasedGauge64,
        cseSecyIfTxUncontrolledOctetRate     CounterBasedGauge64,
        cseSecyIfTxControlledPktRate         CounterBasedGauge64,
        cseSecyIfTxControlledOctetRate       CounterBasedGauge64,
        cseSecyIfTxControlledPkts            Counter64
}

cseSecyIfTxUnicastUncontrolledPkts OBJECT-TYPE
    SYNTAX          Counter64
    MAX-ACCESS      read-only
    STATUS          current
    DESCRIPTION
        "The number of unicast uncontrolled packets transmitted via this
        interface." 
    ::= { cseSecyIfTxStatsEntry 1 }

cseSecyIfTxMulticastUncontrolledPkts OBJECT-TYPE
    SYNTAX          Counter64
    MAX-ACCESS      read-only
    STATUS          current
    DESCRIPTION
        "The number of multicast uncontrolled packets transmitted via
        this interface." 
    ::= { cseSecyIfTxStatsEntry 2 }

cseSecyIfTxBroadcastUncontrolledPkts OBJECT-TYPE
    SYNTAX          Counter64
    MAX-ACCESS      read-only
    STATUS          current
    DESCRIPTION
        "The number of broadcast uncontrolled packets transmitted via
        this interface." 
    ::= { cseSecyIfTxStatsEntry 3 }

cseSecyIfTxUncontrolledPktsDrop OBJECT-TYPE
    SYNTAX          Counter64
    MAX-ACCESS      read-only
    STATUS          current
    DESCRIPTION
        "The number of uncontrolled packets drop transmitted via this
        interface." 
    ::= { cseSecyIfTxStatsEntry 4 }

cseSecyIfTxUncontrolledPktsError OBJECT-TYPE
    SYNTAX          Counter64
    MAX-ACCESS      read-only
    STATUS          current
    DESCRIPTION
        "The number of uncontrolled packets error transmitted via this
        interface." 
    ::= { cseSecyIfTxStatsEntry 5 }

cseSecyIfTxUnicastControlledPkts OBJECT-TYPE
    SYNTAX          Counter64
    MAX-ACCESS      read-only
    STATUS          current
    DESCRIPTION
        "The number of unicast controlled packets transmitted via this
        interface." 
    ::= { cseSecyIfTxStatsEntry 6 }

cseSecyIfTxMulticastControlledPkts OBJECT-TYPE
    SYNTAX          Counter64
    MAX-ACCESS      read-only
    STATUS          current
    DESCRIPTION
        "The number of multicast controlled packets transmitted via this
        interface." 
    ::= { cseSecyIfTxStatsEntry 7 }

cseSecyIfTxBroadcastControlledPkts OBJECT-TYPE
    SYNTAX          Counter64
    MAX-ACCESS      read-only
    STATUS          current
    DESCRIPTION
        "The number of broadcast controlled packets transmitted via this
        interface." 
    ::= { cseSecyIfTxStatsEntry 8 }

cseSecyIfTxControlledPktsDrop OBJECT-TYPE
    SYNTAX          Counter64
    MAX-ACCESS      read-only
    STATUS          current
    DESCRIPTION
        "The number of controlled packets drop transmitted via this
        interface." 
    ::= { cseSecyIfTxStatsEntry 9 }

cseSecyIfTxControlledPktsError OBJECT-TYPE
    SYNTAX          Counter64
    MAX-ACCESS      read-only
    STATUS          current
    DESCRIPTION
        "The number of controlled packets error transmitted via this
        interface." 
    ::= { cseSecyIfTxStatsEntry 10 }

cseSecyIfTxUncontrolledOctets OBJECT-TYPE
    SYNTAX          Counter64
    MAX-ACCESS      read-only
    STATUS          current
    DESCRIPTION
        "The number of uncontrolled octets transmitted via this
        interface." 
    ::= { cseSecyIfTxStatsEntry 11 }

cseSecyIfTxControlledOctets OBJECT-TYPE
    SYNTAX          Counter64
    MAX-ACCESS      read-only
    STATUS          current
    DESCRIPTION
        "The number of controlled octets transmitted via
        this interface." 
    ::= { cseSecyIfTxStatsEntry 12 }

cseSecyIfTxCommonOctets OBJECT-TYPE
    SYNTAX          Counter64
    MAX-ACCESS      read-only
    STATUS          current
    DESCRIPTION
        "The number of common octets transmitted via this interface." 
    ::= { cseSecyIfTxStatsEntry 13 }

cseSecyIfTxUncontrolledPktRate OBJECT-TYPE
    SYNTAX          CounterBasedGauge64
    UNITS           "Packets per second"
    MAX-ACCESS      read-only
    STATUS          current
    DESCRIPTION
        "The number of uncontrolled packets per second transmitted via
        this interface." 
    ::= { cseSecyIfTxStatsEntry 14 }

cseSecyIfTxUncontrolledOctetRate OBJECT-TYPE
    SYNTAX          CounterBasedGauge64
    UNITS           "Bytes per second"
    MAX-ACCESS      read-only
    STATUS          current
    DESCRIPTION
        "The number of uncontrolled byte per second transmitted via this
        interface." 
    ::= { cseSecyIfTxStatsEntry 15 }

cseSecyIfTxControlledPktRate OBJECT-TYPE
    SYNTAX          CounterBasedGauge64
    UNITS           "Packets per second"
    MAX-ACCESS      read-only
    STATUS          current
    DESCRIPTION
        "The number of controlled packets per second transmitted via
        this interface." 
    ::= { cseSecyIfTxStatsEntry 16 }

cseSecyIfTxControlledOctetRate OBJECT-TYPE
    SYNTAX          CounterBasedGauge64
    UNITS           "Bytes per second"
    MAX-ACCESS      read-only
    STATUS          current
    DESCRIPTION
        "The number of controlled byte per second transmitted via this
        interface." 
    ::= { cseSecyIfTxStatsEntry 17 }

cseSecyIfTxControlledPkts OBJECT-TYPE
    SYNTAX          Counter64
    MAX-ACCESS      read-only
    STATUS          current
    DESCRIPTION
        "The total number of controlled packets transmitted via this
        interface." 
    ::= { cseSecyIfTxStatsEntry 18 }
 


cseSecyRxSAStatsTable OBJECT-TYPE
    SYNTAX          SEQUENCE OF CseSecyRxSAStatsEntry 
    MAX-ACCESS      not-accessible
    STATUS          current
    DESCRIPTION
        "The table containing the additional statistics information for
        each receiving SA in MAC security entity."
    ::= { ciscoSecyExtMIBStatsObjects 5 }

cseSecyRxSAStatsEntry OBJECT-TYPE
    SYNTAX          CseSecyRxSAStatsEntry
    MAX-ACCESS      not-accessible
    STATUS          current
    DESCRIPTION
        "An entry containing the additional statistics for
        a receiving SA."
    AUGMENTS           { secyRxSAEntry  } 
    ::= { cseSecyRxSAStatsTable 1 }

CseSecyRxSAStatsEntry ::= SEQUENCE {
        cseSecyRxSAStatsOKPkts Counter64
}

cseSecyRxSAStatsOKPkts OBJECT-TYPE
    SYNTAX          Counter64
    UNITS           "Packets"
    MAX-ACCESS      read-only
    STATUS          current
    DESCRIPTION
        "This is the counter64 version of secyRxSAStatsOKPkts, the
        number of validated packets for this SA." 
    ::= { cseSecyRxSAStatsEntry 1 }
 


cseSecyTxSAStatsTable OBJECT-TYPE
    SYNTAX          SEQUENCE OF CseSecyTxSAStatsEntry 
    MAX-ACCESS      not-accessible
    STATUS          current
    DESCRIPTION
        "The table containing the additional statistics information for
        each transmitting SA in MAC security entity."
    ::= { ciscoSecyExtMIBStatsObjects 6 }

cseSecyTxSAStatsEntry OBJECT-TYPE
    SYNTAX          CseSecyTxSAStatsEntry
    MAX-ACCESS      not-accessible
    STATUS          current
    DESCRIPTION
        "An entry containing the additional statistics for
        a transmitting SA."
    AUGMENTS           { secyTxSAEntry  } 
    ::= { cseSecyTxSAStatsTable 1 }

CseSecyTxSAStatsEntry ::= SEQUENCE {
        cseSecyTxSAStatsProtectedPkts Counter64,
        cseSecyTxSAStatsEncryptedPkts Counter64
}

cseSecyTxSAStatsProtectedPkts OBJECT-TYPE
    SYNTAX          Counter64
    UNITS           "Packets"
    MAX-ACCESS      read-only
    STATUS          current
    DESCRIPTION
        "This is the Counter64 version of secyTxSAStatsProtectedPkts,
        the number of integrity-protected but non-encrypted
        packets for this transmitting SA." 
    ::= { cseSecyTxSAStatsEntry 1 }

cseSecyTxSAStatsEncryptedPkts OBJECT-TYPE
    SYNTAX          Counter64
    UNITS           "Packets"
    MAX-ACCESS      read-only
    STATUS          current
    DESCRIPTION
        "This is the Counter64 version of secyTxSAStatsEncryptedPkts,
        the number of integrity-protected and encrypted packets
        for this transmitting SA." 
    ::= { cseSecyTxSAStatsEntry 2 }
 

-- *****************************************************************
-- cseSecySessionTable - MACSEC Session State Monitoring Table
-- *****************************************************************

cseSecySessionTable OBJECT-TYPE
    SYNTAX          SEQUENCE OF CseSecySessionEntry 
    MAX-ACCESS      not-accessible
    STATUS          current
    DESCRIPTION
        "A table containing the operational status information for
        MACSEC sessions on each MAC security capable interface.
        This table provides OIDs to monitor the operational status
        of MACSEC sessions (up, down, negotiating)."
    ::= { ciscoSecyExtMIBStatsObjects 7 }

cseSecySessionEntry OBJECT-TYPE
    SYNTAX          CseSecySessionEntry
    MAX-ACCESS      not-accessible
    STATUS          current
    DESCRIPTION
        "An entry containing the operational status of a MACSEC
        session on a MAC security capable interface."
    INDEX           { secyIfInterfaceIndex } 
    ::= { cseSecySessionTable 1 }

CseSecySessionEntry ::= SEQUENCE {
        cseSecySessionOperStatus    INTEGER,
        cseSecySessionOperStatusStr DisplayString
}

cseSecySessionOperStatus OBJECT-TYPE
    SYNTAX          INTEGER {
                        up(1),
                        down(2),
                        negotiating(3)
                    }
    MAX-ACCESS      read-only
    STATUS          current
    DESCRIPTION
        "The operational status of the MACSEC session on this interface.
        
        up(1)          - MACSEC session is secured and operational.
                         MKA has successfully negotiated keys and both
                         TX and RX secure channels are active.
        
        down(2)        - MACSEC session is not operational.
                         Either MACSEC is not enabled or MKA session
                         has not been established.
        
        negotiating(3) - MACSEC session is in the process of being
                         established. MKA has been secured but secure
                         channels are not yet fully operational." 
    ::= { cseSecySessionEntry 1 }

cseSecySessionOperStatusStr OBJECT-TYPE
    SYNTAX          DisplayString (SIZE (0..32))
    MAX-ACCESS      read-only
    STATUS          current
    DESCRIPTION
        "A textual representation of the operational status of the
        MACSEC session on this interface. Possible values are:
        'up', 'down', or 'negotiating'." 
    ::= { cseSecySessionEntry 2 }
 

ciscoSecyExtMIBCompliances  OBJECT IDENTIFIER
    ::= { ciscoSecyExtMIBConform 1 }

ciscoSecyExtMIBGroups  OBJECT IDENTIFIER
    ::= { ciscoSecyExtMIBConform 2 }


cseSecyExtMIBCompliance MODULE-COMPLIANCE
    STATUS          current
    DESCRIPTION
        "The compliance statement for CISCO-SECY-EXT-MIB.
        containing default object groups."
    MODULE          -- this module
    GROUP           cseSecyStatsExtGroup
    DESCRIPTION
        "This group is mandatory for devices which
        support the additional SecY statistics information defined
        in this group."

    GROUP           cseSecyTxSCStatsExtGroup
    DESCRIPTION
        "This group is mandatory for devices which support
        the addtional transmitting SC Statistics information defined
        in this group."

    GROUP           cseSecyIfRxStatsGroup
    DESCRIPTION
        "This group is mandatory for devices which support
        the interface RX Statistics information defined
        in this group."

    GROUP           cseSecyIfTxStatsGroup
    DESCRIPTION
        "This group is mandatory for devices which support
        the interface TX Statistics information defined
        in this group."

    GROUP           cseSecySessionGroup
    DESCRIPTION
        "This group is mandatory for devices which support
        MACSEC session state monitoring."
    ::= { ciscoSecyExtMIBCompliances 1 }

-- Units of Conformance

cseSecyStatsExtGroup OBJECT-GROUP
    OBJECTS         {
                        cseSecyStatsRxTransformErrPkts,
                        cseSecyStatsRxControlPkts,
                        cseSecyStatsRxTaggedCtrlPkts,
                        cseSecyStatsTxTransformErrPkts,
                        cseSecyStatsTxControlPkts
                    }
    STATUS          current
    DESCRIPTION
        "A collection of objects providing additional SecY
        statistics information."
    ::= { ciscoSecyExtMIBGroups 1 }

cseSecyTxSCStatsExtGroup OBJECT-GROUP
    OBJECTS         { cseSecyTxSCStatsSANotInUse }
    STATUS          current
    DESCRIPTION
        "A collection of objects providing the addtional transmitting
        SC Statistics information."
    ::= { ciscoSecyExtMIBGroups 2 }

cseSecyIfRxStatsGroup OBJECT-GROUP
    OBJECTS         {
                        cseSecyIfRxUnicastUncontrolledPkts,
                        cseSecyIfRxMulticastUncontrolledPkts,
                        cseSecyIfRxBroadcastUncontrolledPkts,
                        cseSecyIfRxUncontrolledPktsDrop,
                        cseSecyIfRxUncontrolledPktsError,
                        cseSecyIfRxUnicastControlledPkts,
                        cseSecyIfRxMulticastControlledPkts,
                        cseSecyIfRxBroadcastControlledPkts,
                        cseSecyIfRxControlledPktsDrop,
                        cseSecyIfRxControlledPktsError,
                        cseSecyIfRxUncontrolledOctets,
                        cseSecyIfRxControlledOctets,
                        cseSecyIfRxUncontrolledPktRate,
                        cseSecyIfRxUncontrolledOctetRate,
                        cseSecyIfRxControlledPktRate,
                        cseSecyIfRxControlledOctetRate,
                        cseSecyIfRxControlledPkts
                    }
    STATUS          current
    DESCRIPTION
        "A collection of objects providing the Rx statistics for
        the MAC security capable interface."
    ::= { ciscoSecyExtMIBGroups 3 }

cseSecyIfTxStatsGroup OBJECT-GROUP
    OBJECTS         {
                        cseSecyIfTxUnicastUncontrolledPkts,
                        cseSecyIfTxMulticastUncontrolledPkts,
                        cseSecyIfTxBroadcastUncontrolledPkts,
                        cseSecyIfTxUncontrolledPktsDrop,
                        cseSecyIfTxUncontrolledPktsError,
                        cseSecyIfTxUnicastControlledPkts,
                        cseSecyIfTxMulticastControlledPkts,
                        cseSecyIfTxBroadcastControlledPkts,
                        cseSecyIfTxControlledPktsDrop,
                        cseSecyIfTxControlledPktsError,
                        cseSecyIfTxUncontrolledOctets,
                        cseSecyIfTxControlledOctets,
                        cseSecyIfTxCommonOctets,
                        cseSecyIfTxUncontrolledPktRate,
                        cseSecyIfTxUncontrolledOctetRate,
                        cseSecyIfTxControlledPktRate,
                        cseSecyIfTxControlledOctetRate,
                        cseSecyIfTxControlledPkts
                    }
    STATUS          current
    DESCRIPTION
        "A collection of objects providing the Tx statistics for
        the MAC security capable interface."
    ::= { ciscoSecyExtMIBGroups 4 }

cseSecyRxSAStatsGroup OBJECT-GROUP
    OBJECTS         { cseSecyRxSAStatsOKPkts }
    STATUS          current
    DESCRIPTION
        "A collection of objects providing additional statistics
        informatio for a receiving SA."
    ::= { ciscoSecyExtMIBGroups 5 }

cseSecyTxSAStatsGroup OBJECT-GROUP
    OBJECTS         {
                        cseSecyTxSAStatsProtectedPkts,
                        cseSecyTxSAStatsEncryptedPkts
                    }
    STATUS          current
    DESCRIPTION
        "A collection of objects providing additional statistics
        information for a transmitting SA."
    ::= { ciscoSecyExtMIBGroups 6 }

cseSecySessionGroup OBJECT-GROUP
    OBJECTS         {
                        cseSecySessionOperStatus,
                        cseSecySessionOperStatusStr
                    }
    STATUS          current
    DESCRIPTION
        "A collection of objects providing MACSEC session
        operational status monitoring for MAC security
        capable interfaces."
    ::= { ciscoSecyExtMIBGroups 7 }

END


-- %DNP%  MLC -Compiled MLC
